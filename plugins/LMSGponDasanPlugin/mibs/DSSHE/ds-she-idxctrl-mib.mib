--
-- she-idxctrl-mib.mib
-- MIB generated by MG-SOFT Visual MIB Builder Version 6.0  Build 88
-- Wednesday, May 07, 2008 at 14:32:11
--

-- Start of ClearCase branch-information of current release:
-- she-idxctrl-mib.mib   /main/she_main_grf/4
-- End of ClearCase branch-information.

	DS-SHE-IDXCTRL-MIB DEFINITIONS ::= BEGIN
 
		IMPORTS
			she			
				FROM AN-MIB
			dsShe
				FROM DASAN-SMI							
			PhysicalIndex			
				FROM ENTITY-MIB			
			InterfaceIndex			
				FROM IF-MIB			
			SheControlStatusType			
				FROM DS-SHE-TC-MIB			
			OBJECT-GROUP, MODULE-COMPLIANCE			
				FROM SNMPv2-CONF			
			Unsigned32, OBJECT-TYPE, MODULE-IDENTITY			
				FROM SNMPv2-SMI			
			TEXTUAL-CONVENTION			
				FROM SNMPv2-TC;
	
	
		sheIdxCtrlMib MODULE-IDENTITY 
			LAST-UPDATED "200805070900Z"		-- May 07, 2008 at 09:00 GMT
			ORGANIZATION 
				"Nokia Siemens Networks GmbH & Co. KG"
			CONTACT-INFO 
				"COO BBA DSLAM RD SDE HW1
				Siemensallee 1
				D-17491 Greifswald
				Tel. +49 (3834) 555654
				gerd.barchmann@nsn.com"
			DESCRIPTION 
				"Since the the SNMP table indices are assigned by the NE at it's own discretion,
				the management system should not rely on the calculation formula.
				Calculation formula is subject to change.
				This MIB provides an easy way for the management system to request the calculated indices.
				
				The MIB consists of control groups (one control group for each index to be calculated).
				These control groups execute a command for index calculation.
				Write the required input parameters to the attributes of the control group.
				Write the command to the control group.
				Read the calculated index from the control group."
			REVISION "200712171009Z"		-- December 17, 2007 at 10:09 GMT
			DESCRIPTION 
				"First initial version merged from GPON system."
			REVISION "200801141310Z"		-- January 14, 2008 at 13:10 GMT
			DESCRIPTION 
				"Correct used Basis-OID."
			REVISION "200804021543Z"		-- April 02, 2008 at 15:43 GMT
			DESCRIPTION 
				"Add cardtype mainIU1GE10OSYNE.
				Modify cardtype for CXU_M."
			REVISION "200805071427Z"		-- May 07, 2008 at 14:27 GMT
			DESCRIPTION 
				"New board type IUADSL:72J:CGH supported."
			::= { dsShe 27 }

		
	
--
-- Type definitions
--
	
-- slot number of main shelf
		SheIdxCtrlSlotNrType ::= Unsigned32 (1..32)

--  interface number of OLT card
		SheIdxCtrlCardInterfaceNrType ::= Unsigned32 (1..72)

		SheIdxCtrlEntityTypeType ::= INTEGER
			{
			mainRack(1),
			mainShelf(2),
			mainSlot(3),
			mainCard(4)
			}

		SheIdxCtrlCardInterfaceTypeType ::= INTEGER
			{
			physicalInterface(1),
			internalVoipInterface(2),
			internalRouterInterface(3)
			}

		SheIdxCtrlIfIndexCtrlCardTypeType ::= INTEGER
			{
			mainCXUGE4EE(1),
			mainCXUB1GE4EE(2),
			mainCXUB2GE4E(3),
			mainCXUB22GE4E(4),
			mainCXUB3GE4E(5),
			mainCXUCGE4EE(6),
			mainCXUC2GE4E(7),
			mainIUADSL48PE(10),
			mainIUADSL72AE(11),
			mainIUADSL72BE(12),
			mainIUADSL72PIFX(13),
			mainIUADSL72IIFX(14),
			mainIUADSL72AIWC(15),
			mainIUADSL72AJWC(16),
			mainIUSHDSL48SE(20),
			mainIUSHDSL48BE(21),
			mainIUSHDSL48EE(22),
			mainIUVDSL24D2IFX(30),
			mainIUVDSL24PE(31),
			mainIUVDSL48PE(32),
			mainIUVDSL48IE(33),
			mainIUADSL72ACG(40),
			mainIUADSL72BCG(41),
			mainIUADSL72ACGH(42),
			mainIUADSL72BCGH(43),
			mainIUADSL72JCGH(44),
			mainIU1GE10OSYNE(50),
			mainVPLUS72POTSE(60),
			mainVPLU72PE(61),
			mainIU32I4E(70),
			mainIU32I2E(71),
			mainCXUMGE4E(90),
			mainSBXDSL16PE(91),
			mainSBXDSL16E(92)
			}

--  logical port related to a physical port,
-- usually the VCC number of an ADSL line
		SheIdxCtrlLogicalPortNrType ::= Unsigned32 (1..8)

	
--
-- Textual conventions
--
	
		SheIdxCtrlControlRequestType ::= TEXTUAL-CONVENTION
			STATUS current
			DESCRIPTION 
				"The control request type (user command)."
			SYNTAX INTEGER
				{
				noRequest(0),
				getEntPhysicalIndex(1),
				getIfIndex(2),
				getBridgePortIndex(3),
				getDslVccTpIndex(6)
				}

		SheIdxCtrlControlReqResultType ::= TEXTUAL-CONVENTION
			STATUS current
			DESCRIPTION 
				"The control request result type (user command)."
			SYNTAX INTEGER
				{
				noRequest(1),
				commExecStarted(30),
				paramFaulty(31),
				requestBusy(32),
				setDataFailed(34),
				aswTimeout(35),
				commandFailed(36),
				commandSucceeded(37)
				}

	
--
-- Node definitions
--
	
		sheIdxCtrlObjs OBJECT IDENTIFIER ::= { sheIdxCtrlMib 1 }

		
--  1.3.6.1.4.1.231.7.1.2.2.1.27.1.1
		sheIdxCtrlEntPhysicalIndexCtrl OBJECT IDENTIFIER ::= { sheIdxCtrlObjs 1 }

		
--  1.3.6.1.4.1.231.7.1.2.2.1.27.1.1.1
		sheIdxCtrlEntPhysicalIndexCtrlRequest OBJECT-TYPE
			SYNTAX SheIdxCtrlControlRequestType
			MAX-ACCESS read-write
			STATUS current
			DESCRIPTION
				"getEntPhysicalIndex
				sheIdxCtrlEntPhysicalIndexCtrlSlotNr
				sheIdxCtrlEntPhysicalIndexCtrlCardInterfaceNr
				sheIdxCtrlEntPhysicalIndexCtrlEntityType"
			::= { sheIdxCtrlEntPhysicalIndexCtrl 1 }

		
--  1.3.6.1.4.1.231.7.1.2.2.1.27.1.1.2
		sheIdxCtrlEntPhysicalIndexCtrlStatus OBJECT-TYPE
			SYNTAX SheControlStatusType
			MAX-ACCESS read-only
			STATUS current
			DESCRIPTION
				"The status of a user command. "
			::= { sheIdxCtrlEntPhysicalIndexCtrl 2 }

		
--  1.3.6.1.4.1.231.7.1.2.2.1.27.1.1.4
		sheIdxCtrlEntPhysicalIndexCtrlReqResult OBJECT-TYPE
			SYNTAX SheIdxCtrlControlReqResultType
			MAX-ACCESS read-only
			STATUS current
			DESCRIPTION
				"The result of the last user command. "
			::= { sheIdxCtrlEntPhysicalIndexCtrl 4 }

		
--  1.3.6.1.4.1.231.7.1.2.2.1.27.1.1.5
		sheIdxCtrlEntPhysicalIndexCtrlTimeStamp OBJECT-TYPE
			SYNTAX Unsigned32
			UNITS "sec"
			MAX-ACCESS read-only
			STATUS current
			DESCRIPTION
				"The time stamp of the last command (end of command). "
			::= { sheIdxCtrlEntPhysicalIndexCtrl 5 }

		
--  1.3.6.1.4.1.231.7.1.2.2.1.27.1.1.6
		sheIdxCtrlEntPhysicalIndexCtrlSlotNr OBJECT-TYPE
			SYNTAX SheIdxCtrlSlotNrType
			MAX-ACCESS read-write
			STATUS current
			DESCRIPTION
				"slot number of main shelf"
			::= { sheIdxCtrlEntPhysicalIndexCtrl 6 }

		
--  1.3.6.1.4.1.231.7.1.2.2.1.27.1.1.7
		sheIdxCtrlEntPhysicalIndexCtrlCardInterfaceNr OBJECT-TYPE
			SYNTAX SheIdxCtrlCardInterfaceNrType
			MAX-ACCESS read-write
			STATUS current
			DESCRIPTION
				"interface number of main shelf card"
			::= { sheIdxCtrlEntPhysicalIndexCtrl 7 }

		
--  1.3.6.1.4.1.231.7.1.2.2.1.27.1.1.10
		sheIdxCtrlEntPhysicalIndexCtrlEntityType OBJECT-TYPE
			SYNTAX SheIdxCtrlEntityTypeType
			MAX-ACCESS read-write
			STATUS current
			DESCRIPTION
				"entity type:
				rack(1), shelf(2), slot(3), card(4)"
			::= { sheIdxCtrlEntPhysicalIndexCtrl 10 }

		
--  1.3.6.1.4.1.231.7.1.2.2.1.27.1.1.11
		sheIdxCtrlEntPhysicalIndexCtrlEntPhysicalIndex OBJECT-TYPE
			SYNTAX PhysicalIndex
			MAX-ACCESS read-only
			STATUS current
			DESCRIPTION
				"calculated entPhysicalIndex"
			::= { sheIdxCtrlEntPhysicalIndexCtrl 11 }

		
--  1.3.6.1.4.1.231.7.1.2.2.1.27.1.2
		sheIdxCtrlIfIndexCtrl OBJECT IDENTIFIER ::= { sheIdxCtrlObjs 2 }

		
--  1.3.6.1.4.1.231.7.1.2.2.1.27.1.2.1
		sheIdxCtrlIfIndexCtrlRequest OBJECT-TYPE
			SYNTAX SheIdxCtrlControlRequestType
			MAX-ACCESS read-write
			STATUS current
			DESCRIPTION
				"getIfIndex
				sheIdxCtrlIfIndexCtrlSlotNr
				sheIdxCtrlIfIndexCtrlCardInterfaceNr
				sheIdxCtrlIfIndexCtrlIfType
				sheIdxCtrlIfIndexCtrlCardType"
			::= { sheIdxCtrlIfIndexCtrl 1 }

		
--  1.3.6.1.4.1.231.7.1.2.2.1.27.1.2.2
		sheIdxCtrlIfIndexCtrlStatus OBJECT-TYPE
			SYNTAX SheControlStatusType
			MAX-ACCESS read-only
			STATUS current
			DESCRIPTION
				"The status of a user command. "
			::= { sheIdxCtrlIfIndexCtrl 2 }

		
--  1.3.6.1.4.1.231.7.1.2.2.1.27.1.2.4
		sheIdxCtrlIfIndexCtrlReqResult OBJECT-TYPE
			SYNTAX SheIdxCtrlControlReqResultType
			MAX-ACCESS read-only
			STATUS current
			DESCRIPTION
				"The result of the last user command. "
			::= { sheIdxCtrlIfIndexCtrl 4 }

		
--  1.3.6.1.4.1.231.7.1.2.2.1.27.1.2.5
		sheIdxCtrlIfIndexCtrlTimeStamp OBJECT-TYPE
			SYNTAX Unsigned32
			UNITS "sec"
			MAX-ACCESS read-only
			STATUS current
			DESCRIPTION
				"The time stamp of the last command (end of command). "
			::= { sheIdxCtrlIfIndexCtrl 5 }

		
--  1.3.6.1.4.1.231.7.1.2.2.1.27.1.2.6
		sheIdxCtrlIfIndexCtrlSlotNr OBJECT-TYPE
			SYNTAX SheIdxCtrlSlotNrType
			MAX-ACCESS read-write
			STATUS current
			DESCRIPTION
				"slot number of main shelf"
			::= { sheIdxCtrlIfIndexCtrl 6 }

		
--  1.3.6.1.4.1.231.7.1.2.2.1.27.1.2.7
		sheIdxCtrlIfIndexCtrlCardInterfaceNr OBJECT-TYPE
			SYNTAX SheIdxCtrlCardInterfaceNrType
			MAX-ACCESS read-write
			STATUS current
			DESCRIPTION
				"interface number of card"
			::= { sheIdxCtrlIfIndexCtrl 7 }

		
--  1.3.6.1.4.1.231.7.1.2.2.1.27.1.2.8
		sheIdxCtrlIfIndexCtrlIfType OBJECT-TYPE
			SYNTAX SheIdxCtrlCardInterfaceTypeType
			MAX-ACCESS read-write
			STATUS current
			DESCRIPTION
				"interface type
				physicalInterface(1),
				internalVoipInterface(2),
				internalRouterInterface(3)"
			::= { sheIdxCtrlIfIndexCtrl 8 }

		
--  1.3.6.1.4.1.231.7.1.2.2.1.27.1.2.9
		sheIdxCtrlIfIndexCtrlCardType OBJECT-TYPE
			SYNTAX SheIdxCtrlIfIndexCtrlCardTypeType
			MAX-ACCESS read-write
			STATUS current
			DESCRIPTION
				"type of the card type of main shelf
				mainCXUGE4EE(1)      -> Central unit, 4x 1 GigE uplink
				mainCXUB1GE4EE(2)    -> Central unit, 4x 1 GigE uplink
				mainCXUB2GE4E(3)     -> Central unit, 4x 1 GigE uplink
				mainCXUB22GE4E(4)    -> Central unit, 4x 1 GigE uplink
				mainCXUB3GE4E(5)     -> Central unit, 4x 1 GigE uplink, virtual routing
				mainCXUCGE4EE(6)     -> Central unit, 4x 1 GigE uplink
				mainCXUC2GE4E(7)     -> Central unit, 4x 1 GigE uplink
				mainIUADSL48PE(10)   -> Interface unit 48 ADSL2+ AnnexA
				mainIUADSL72AE(11)   -> Interface unit 72 ADSL2+ AnnexA
				mainIUADSL72BE(12)   -> Interface unit 72 ADSL2+ AnnexB
				mainIUADSL72PIFX(13) -> Interface unit 72 ADSL2+ AnnexA
				mainIUADSL72IIFX(14) -> Interface unit 72 ADSL2+ AnnexB
				mainIUADSL72AIWC(15) -> Interface unit 72 ADSL2+ ADM
				mainIUADSL72AJWC(16) -> Interface unit 72 ADSL2+ ADM
				mainIUSHDSL48SE(20)  -> Interface unit 48 SHDSL
				mainIUSHDSL48BE(21)  -> Interface unit 48 SHDSL
				mainIUSHDSL48EE(22)  -> Interface unit 48 SHDSL
				mainIUVDSL24D2IFX(30)-> Interface unit 24 VDSL2 AnnexB, ADSL2+ backward compatible
				mainIUVDSL24PE(31)   -> Interface unit 24 VDSL2 AnnexA, ADSL2+ backward compatible
				mainIUVDSL48PE(32)   -> Interface unit 48 VDSL2 AnnexA, ADSL2+ backward compatible
				mainIUVDSL48IE(33)   -> Interface unit 48 VDSL2 AnnexA, ADSL2+ backward compatible
				mainIUADSL72ACG(40)  -> Interface unit 72 ADSL2+ AnnexA
				mainIUADSL72BCG(41)  -> Interface unit 72 ADSL2+ AnnexB
				mainIUADSL72ACGH(42) -> Interface unit 72 ADSL2+ AnnexA
				mainIUADSL72BCGH(43) -> Interface unit 72 ADSL2+ AnnexB
				mainIUADSL72JCGH(44) -> Interface unit 72 ADSL2+ AnnexJ
				mainIU1GE10OSYNE(50) -> Interface unit 10x 1 GigE with sync
				mainVPLUS72POTSE(60) -> Interface unit 72 POTS, VOIP
				mainVPLU72PE(61)     -> Interface unit 72 POTS, VOIP
				mainIU32I4E(70)      -> Interface unit 22 ISDN, VOIP, 4B3T
				mainIU32I2E(71)      -> Interface unit 22 ISDN, VOIP, 2B1Q
				mainCXUMGE4E(90)     -> Central unit 4x 1GigE
				mainSBXDSL16PE(91)   -> Interface unit 16 VDSL2 AnnexA, ADSL2+ backward compatible
				mainSBXDSL16E(92)    -> Interface unit 16 VDSL2 AnnexB, ADSL2+ backward compatible"
			::= { sheIdxCtrlIfIndexCtrl 9 }

		
--  1.3.6.1.4.1.231.7.1.2.2.1.27.1.2.11
		sheIdxCtrlIfIndexCtrlIfIndex OBJECT-TYPE
			SYNTAX InterfaceIndex
			MAX-ACCESS read-only
			STATUS current
			DESCRIPTION
				"calculated ifIndex"
			::= { sheIdxCtrlIfIndexCtrl 11 }

		
--  1.3.6.1.4.1.231.7.1.2.2.1.27.1.3
		sheIdxCtrlBridgePortIndexCtrl OBJECT IDENTIFIER ::= { sheIdxCtrlObjs 3 }

		
--  1.3.6.1.4.1.231.7.1.2.2.1.27.1.3.1
		sheIdxCtrlBridgePortIndexCtrlRequest OBJECT-TYPE
			SYNTAX SheIdxCtrlControlRequestType
			MAX-ACCESS read-write
			STATUS current
			DESCRIPTION
				"getBridgePortIndex
				sheIdxCtrlBridgePortIndexCtrlSlotNr
				sheIdxCtrlBridgePortIndexCtrlCardInterfaceNr
				sheIdxCtrlBridgePortIndexCtrlLogicalPortNr"
			::= { sheIdxCtrlBridgePortIndexCtrl 1 }

		
--  1.3.6.1.4.1.231.7.1.2.2.1.27.1.3.2
		sheIdxCtrlBridgePortIndexCtrlStatus OBJECT-TYPE
			SYNTAX SheControlStatusType
			MAX-ACCESS read-only
			STATUS current
			DESCRIPTION
				"The status of a user command. "
			::= { sheIdxCtrlBridgePortIndexCtrl 2 }

		
--  1.3.6.1.4.1.231.7.1.2.2.1.27.1.3.4
		sheIdxCtrlBridgePortIndexCtrlReqResult OBJECT-TYPE
			SYNTAX SheIdxCtrlControlReqResultType
			MAX-ACCESS read-only
			STATUS current
			DESCRIPTION
				"The result of the last user command. "
			::= { sheIdxCtrlBridgePortIndexCtrl 4 }

		
--  1.3.6.1.4.1.231.7.1.2.2.1.27.1.3.5
		sheIdxCtrlBridgePortIndexCtrlTimeStamp OBJECT-TYPE
			SYNTAX Unsigned32
			UNITS "sec"
			MAX-ACCESS read-only
			STATUS current
			DESCRIPTION
				"The time stamp of the last command (end of command). "
			::= { sheIdxCtrlBridgePortIndexCtrl 5 }

		
--  1.3.6.1.4.1.231.7.1.2.2.1.27.1.3.6
		sheIdxCtrlBridgePortIndexCtrlSlotNr OBJECT-TYPE
			SYNTAX SheIdxCtrlSlotNrType
			MAX-ACCESS read-write
			STATUS current
			DESCRIPTION
				"slot number of main shelf"
			::= { sheIdxCtrlBridgePortIndexCtrl 6 }

		
--  1.3.6.1.4.1.231.7.1.2.2.1.27.1.3.7
		sheIdxCtrlBridgePortIndexCtrlCardInterfaceNr OBJECT-TYPE
			SYNTAX SheIdxCtrlCardInterfaceNrType
			MAX-ACCESS read-write
			STATUS current
			DESCRIPTION
				"interface number of card"
			::= { sheIdxCtrlBridgePortIndexCtrl 7 }

		
--  1.3.6.1.4.1.231.7.1.2.2.1.27.1.3.11
		sheIdxCtrlBridgePortIndexCtrlLogicalPortNr OBJECT-TYPE
			SYNTAX SheIdxCtrlLogicalPortNrType
			MAX-ACCESS read-write
			STATUS current
			DESCRIPTION
				"logical port related to a physical port,
				usually the VCC number of an DSL line"
			::= { sheIdxCtrlBridgePortIndexCtrl 11 }

		
--  1.3.6.1.4.1.231.7.1.2.2.1.27.1.3.12
		sheIdxCtrlBridgePortIndexCtrlCardInterfaceType OBJECT-TYPE
			SYNTAX SheIdxCtrlCardInterfaceTypeType
			MAX-ACCESS read-write
			STATUS current
			DESCRIPTION
				"valid settings are
				physicalInterface(1),
				internalVoipInterface(2),
				
				In case of internalVoipInterface the object sheIdxCtrlBridgePortIndexCtrlLogicalPortNr is don't care."
			::= { sheIdxCtrlBridgePortIndexCtrl 12 }

		
--  1.3.6.1.4.1.231.7.1.2.2.1.27.1.3.13
		sheIdxCtrlBridgePortIndexCtrlBridgePortIndex OBJECT-TYPE
			SYNTAX Unsigned32
			MAX-ACCESS read-only
			STATUS current
			DESCRIPTION
				"calculated BridgePortIndex"
			::= { sheIdxCtrlBridgePortIndexCtrl 13 }

		
--  1.3.6.1.4.1.231.7.1.2.2.1.27.1.6
		sheIdxCtrlDslVccTpIndexCtrl OBJECT IDENTIFIER ::= { sheIdxCtrlObjs 6 }

		
--  1.3.6.1.4.1.231.7.1.2.2.1.27.1.6.1
		sheIdxCtrlDslVccTpIndexCtrlRequest OBJECT-TYPE
			SYNTAX SheIdxCtrlControlRequestType
			MAX-ACCESS read-write
			STATUS current
			DESCRIPTION
				"getDslVccTpIndex
				sheIdxCtrlDslVccTpIndexCtrlSlotNr
				sheIdxCtrlDslVccTpIndexCtrlCardInterfaceNr
				sheIdxCtrlDslVccTpIndexCtrlLogicalPortNr"
			::= { sheIdxCtrlDslVccTpIndexCtrl 1 }

		
--  1.3.6.1.4.1.231.7.1.2.2.1.27.1.6.2
		sheIdxCtrlDslVccTpIndexCtrlStatus OBJECT-TYPE
			SYNTAX SheControlStatusType
			MAX-ACCESS read-only
			STATUS current
			DESCRIPTION
				"The status of a user command. "
			::= { sheIdxCtrlDslVccTpIndexCtrl 2 }

		
--  1.3.6.1.4.1.231.7.1.2.2.1.27.1.6.4
		sheIdxCtrlDslVccTpIndexCtrlReqResult OBJECT-TYPE
			SYNTAX SheIdxCtrlControlReqResultType
			MAX-ACCESS read-only
			STATUS current
			DESCRIPTION
				"The result of the last user command. "
			::= { sheIdxCtrlDslVccTpIndexCtrl 4 }

		
--  1.3.6.1.4.1.231.7.1.2.2.1.27.1.6.5
		sheIdxCtrlDslVccTpIndexCtrlTimeStamp OBJECT-TYPE
			SYNTAX Unsigned32
			UNITS "sec"
			MAX-ACCESS read-only
			STATUS current
			DESCRIPTION
				"The time stamp of the last command (end of command). "
			::= { sheIdxCtrlDslVccTpIndexCtrl 5 }

		
--  1.3.6.1.4.1.231.7.1.2.2.1.27.1.6.6
		sheIdxCtrlDslVccTpIndexCtrlSlotNr OBJECT-TYPE
			SYNTAX SheIdxCtrlSlotNrType
			MAX-ACCESS read-write
			STATUS current
			DESCRIPTION
				"slot number of main shelf"
			::= { sheIdxCtrlDslVccTpIndexCtrl 6 }

		
--  1.3.6.1.4.1.231.7.1.2.2.1.27.1.6.7
		sheIdxCtrlDslVccTpIndexCtrlCardInterfaceNr OBJECT-TYPE
			SYNTAX SheIdxCtrlCardInterfaceNrType
			MAX-ACCESS read-write
			STATUS current
			DESCRIPTION
				"interface number of card"
			::= { sheIdxCtrlDslVccTpIndexCtrl 7 }

		
--  1.3.6.1.4.1.231.7.1.2.2.1.27.1.6.11
		sheIdxCtrlDslVccTpIndexCtrlLogicalPortNr OBJECT-TYPE
			SYNTAX SheIdxCtrlLogicalPortNrType
			MAX-ACCESS read-write
			STATUS current
			DESCRIPTION
				"logical port related to a physical port,
				usually the VCC number of an DSL line"
			::= { sheIdxCtrlDslVccTpIndexCtrl 11 }

		
--  1.3.6.1.4.1.231.7.1.2.2.1.27.1.6.12
		sheIdxCtrlDslVccTpIndexCtrlDslVccTpIndex OBJECT-TYPE
			SYNTAX Unsigned32
			MAX-ACCESS read-only
			STATUS current
			DESCRIPTION
				"calculated DslVccTpIndex"
			::= { sheIdxCtrlDslVccTpIndexCtrl 12 }

		
--  1.3.6.1.4.1.231.7.1.2.2.2.27.2
		sheIdxCtrlConf OBJECT IDENTIFIER ::= { sheIdxCtrlMib 2 }

		
--  1.3.6.1.4.1.231.7.1.2.2.2.27.2.1
		sheIdxCtrlGroups OBJECT IDENTIFIER ::= { sheIdxCtrlConf 1 }

		
--  1.3.6.1.4.1.231.7.1.2.2.2.27.2.1.1
		sheIdxCtrlObjectGroup OBJECT-GROUP
			OBJECTS { sheIdxCtrlEntPhysicalIndexCtrlRequest, sheIdxCtrlEntPhysicalIndexCtrlStatus, sheIdxCtrlEntPhysicalIndexCtrlReqResult, sheIdxCtrlEntPhysicalIndexCtrlTimeStamp, sheIdxCtrlEntPhysicalIndexCtrlEntityType, 
				sheIdxCtrlEntPhysicalIndexCtrlEntPhysicalIndex, sheIdxCtrlIfIndexCtrlRequest, sheIdxCtrlIfIndexCtrlStatus, sheIdxCtrlIfIndexCtrlReqResult, sheIdxCtrlIfIndexCtrlTimeStamp, 
				sheIdxCtrlIfIndexCtrlIfIndex, sheIdxCtrlBridgePortIndexCtrlRequest, sheIdxCtrlBridgePortIndexCtrlStatus, sheIdxCtrlBridgePortIndexCtrlReqResult, sheIdxCtrlBridgePortIndexCtrlTimeStamp, 
				sheIdxCtrlBridgePortIndexCtrlLogicalPortNr, sheIdxCtrlBridgePortIndexCtrlBridgePortIndex, sheIdxCtrlDslVccTpIndexCtrlRequest, sheIdxCtrlDslVccTpIndexCtrlStatus, sheIdxCtrlDslVccTpIndexCtrlReqResult, 
				sheIdxCtrlDslVccTpIndexCtrlTimeStamp, sheIdxCtrlDslVccTpIndexCtrlLogicalPortNr, sheIdxCtrlIfIndexCtrlIfType, sheIdxCtrlDslVccTpIndexCtrlDslVccTpIndex, sheIdxCtrlBridgePortIndexCtrlCardInterfaceType, 
				sheIdxCtrlIfIndexCtrlCardType, sheIdxCtrlEntPhysicalIndexCtrlSlotNr, sheIdxCtrlEntPhysicalIndexCtrlCardInterfaceNr, sheIdxCtrlIfIndexCtrlSlotNr, sheIdxCtrlIfIndexCtrlCardInterfaceNr, 
				sheIdxCtrlBridgePortIndexCtrlSlotNr, sheIdxCtrlBridgePortIndexCtrlCardInterfaceNr, sheIdxCtrlDslVccTpIndexCtrlSlotNr, sheIdxCtrlDslVccTpIndexCtrlCardInterfaceNr }
			STATUS current
			DESCRIPTION 
				"Description."
			::= { sheIdxCtrlGroups 1 }

		
--  1.3.6.1.4.1.231.7.1.2.2.2.27.2.2
		sheIdxCtrlCompls OBJECT IDENTIFIER ::= { sheIdxCtrlConf 2 }

		
-- 1.3.6.1.4.1.231.7.1.2.2.2.27.2.2.1
		sheIdxCtrlCompliance MODULE-COMPLIANCE
			STATUS current
			DESCRIPTION 
				"Description."
			MODULE -- this module
				MANDATORY-GROUPS { sheIdxCtrlObjectGroup }
			::= { sheIdxCtrlCompls 1 }

		
	
	END

--
-- she-idxctrl-mib.mib
--
