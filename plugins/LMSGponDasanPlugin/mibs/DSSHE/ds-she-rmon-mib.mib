--
-- she-rmon-mib.mib
-- MIB generated by MG-SOFT Visual MIB Builder Version 6.0  Build 88
-- Tuesday, November 20, 2007 at 14:09:10
--

	DS-SHE-RMON-MIB DEFINITIONS ::= BEGIN
 
		IMPORTS
			she			
				FROM AN-MIB
			dsShe
				FROM DASAN-SMI							
			DisplayString			
				FROM RFC1213-MIB			
			alarmVariable, alarmRisingThreshold, alarmFallingThreshold, OwnerString			
				FROM RMON-MIB			
			SheControlStatusType			
				FROM DS-SHE-TC-MIB			
			OBJECT-GROUP, MODULE-COMPLIANCE, NOTIFICATION-GROUP			
				FROM SNMPv2-CONF			
			Unsigned32, OBJECT-TYPE, MODULE-IDENTITY, NOTIFICATION-TYPE			
				FROM SNMPv2-SMI			
			TEXTUAL-CONVENTION			
				FROM SNMPv2-TC;
	
	
		sheRmon MODULE-IDENTITY 
			LAST-UPDATED "200711201000Z"		-- November 20, 2007 at 10:00 GMT
			ORGANIZATION 
				"Nokia Siemens Networks"
			CONTACT-INFO 
				"Gerd Barchmann
				Nokia Siemens Networks GmbH & Co. KG
				COO BBA DSLAM RD SDE
				phone +49 3834 555 654
				gerd.barchmann@nsn.com"
			DESCRIPTION 
				"The MIB module is the proprietary extension of RMON-MIB defining control groups for configuration."
			REVISION "200410270000Z"		-- October 27, 2004 at 00:00 GMT
			DESCRIPTION 
				"First Release"
			REVISION "200501071340Z"		-- January 07, 2005 at 13:40 GMT
			DESCRIPTION 
				"Strip ControlRequestType and ControlRequestResultType.
				Each of this types should only contain Request's or Result's.
				Add Compliance-Groups."
			REVISION "200501261241Z"		-- January 26, 2005 at 12:41 GMT
			DESCRIPTION 
				"Add ControlRequest and Notification for clearing one entry
				in the EtherStatsTable of the Rmon-Mib."
			REVISION "200504211623Z"		-- April 21, 2005 at 16:23 GMT
			DESCRIPTION 
				"Change syntax for all ControlTimeStamp to U32 and unit sec."
			REVISION "200608141200Z"		-- August 14, 2006 at 12:00 GMT
			DESCRIPTION 
				"Take over by Gerd Barchmann for R2.5."
			REVISION "200611071511Z"		-- November 07, 2006 at 15:11 GMT
			DESCRIPTION 
				"Syntax corrections for backward compatibility."
			REVISION "200711201402Z"		-- November 20, 2007 at 14:02 GMT
			DESCRIPTION 
				"Correct parameter list for alarm and event created traps."
			::= { dsShe 8 }

		
	
	
--
-- Textual conventions
--
	
		SheRmonControlRequestType ::= TEXTUAL-CONVENTION
			STATUS current
			DESCRIPTION 
				"The type for SHE-RMON control commands."
			SYNTAX INTEGER
				{
				createSample(1),
				deleteSample(2),
				resetStatisticCounters(3)
				}

--   GENERAL VALUES FOR USER COMMAND HANDLING
-- RETURN VALUES
		SheRmonControlRequestResultType ::= TEXTUAL-CONVENTION
			STATUS current
			DESCRIPTION 
				"The result type for RMON control commands."
			SYNTAX INTEGER
				{
				commExecStarted(30),
				paramFaulty(31),
				requestBusy(32),
				setDataFailed(34),
				aswTimeout(35),
				commandFailed(36),
				commandSucceeded(37)
				}

		SheRmonAlarmSampleType ::= TEXTUAL-CONVENTION
			STATUS current
			DESCRIPTION 
				"The type for SHE-RMON alarm sample."
			SYNTAX INTEGER
				{
				absoluteValue(1),
				deltaValue(2)
				}

		SheRmonAlarmStartupAlarm ::= TEXTUAL-CONVENTION
			STATUS current
			DESCRIPTION 
				"The type for SHE-RMON alarm startup."
			SYNTAX INTEGER
				{
				risingAlarm(1),
				fallingAlarm(2),
				risingOrFallingAlarm(3)
				}

		SheRmonEventType ::= TEXTUAL-CONVENTION
			STATUS current
			DESCRIPTION 
				"The type for SHE-RMON events."
			SYNTAX INTEGER
				{
				none(1),
				log(2),
				snmpTrap(3),
				logAndTrap(4)
				}

--   -----------------------------------------------------------------
-- Textual Conventions
-- -----------------------------------------------------------------
		SheRmonSevProfileIndex ::= TEXTUAL-CONVENTION
			STATUS current
			DESCRIPTION 
				" The type for the alarm severity profile index."
			SYNTAX INTEGER (1..100)

	
--
-- Node definitions
--
	
-- MIB contains the following groups
-- 1.3.6.1.4.1.231.7.1.2.2.1.8.1
		sheRmonConfigurationObjects OBJECT IDENTIFIER ::= { sheRmon 1 }

		
--   GENERAL VALUES FOR USER COMMAND HANDLING
-- RETURN VALUES
-- -----------------------------------------------------------------
-- SHE RMON Control group
-- -----------------------------------------------------------------   
-- 1.3.6.1.4.1.231.7.1.2.2.1.8.1.1
		sheRmonControl OBJECT IDENTIFIER ::= { sheRmonConfigurationObjects 1 }

		
--  1.3.6.1.4.1.231.7.1.2.2.1.8.1.1.1
		sheRmonControlRequest OBJECT-TYPE
			SYNTAX SheRmonControlRequestType
			MAX-ACCESS read-write
			STATUS current
			DESCRIPTION
				" This attribute identifies the control commands.
				createSample:
				     this command starts periodical data sampling at a specific data source object.
				     An entry in the table historyControlTable is created.
				
				deleteSample: 
				    to stop a sampling. The entry in the historyControlTable is selected. 
				    This entry is deleted and also all associated entries in the EtherHistoryTable
				    are also deleted. 
				
				resetStatisticCounters:
				    to clear one entry in the etherStatsTable of the rmon-Mib.
				 
				Notifications : sampleCreated / sampleDeleted , sheEtherStatsCountersCleared"
			::= { sheRmonControl 1 }

		
--  1.3.6.1.4.1.231.7.1.2.2.1.8.1.1.2
		sheRmonControlStatus OBJECT-TYPE
			SYNTAX SheControlStatusType
			MAX-ACCESS read-only
			STATUS current
			DESCRIPTION
				" The status of a control request. "
			::= { sheRmonControl 2 }

		
--  1.3.6.1.4.1.231.7.1.2.2.1.8.1.1.3
		sheRmonControlTimer OBJECT-TYPE
			SYNTAX Unsigned32
			MAX-ACCESS read-only
			STATUS current
			DESCRIPTION
				" The maximum wait time for the manager for command ending.
				For long running commands.
				The manager reads this value from the DSLAM. "
			::= { sheRmonControl 3 }

		
--  1.3.6.1.4.1.231.7.1.2.2.1.8.1.1.4
		sheRmonControlControlReqResult OBJECT-TYPE
			SYNTAX SheRmonControlRequestResultType
			MAX-ACCESS read-only
			STATUS current
			DESCRIPTION
				" The result of the last user command. "
			::= { sheRmonControl 4 }

		
--  1.3.6.1.4.1.231.7.1.2.2.1.8.1.1.5
		sheRmonControlTimeStamp OBJECT-TYPE
			SYNTAX Unsigned32
			UNITS "sec"
			MAX-ACCESS read-only
			STATUS current
			DESCRIPTION
				" The time stamp of the last command (end of command). "
			::= { sheRmonControl 5 }

		
--  1.3.6.1.4.1.231.7.1.2.2.1.8.1.1.6
		sheRmonControlDataSource OBJECT-TYPE
			SYNTAX OBJECT IDENTIFIER
			MAX-ACCESS read-write
			STATUS current
			DESCRIPTION
				"This object identifies the data source for
				which historical data shall be collected.
				Possible sources can be 
				- any Ethernet interface on this device.  
				  For example, if an entry were to receive
				  data from interface #1, this object would be set
				  to ifIndex.1.
				- any subscriber side bridgePort of the device
				"
			::= { sheRmonControl 6 }

		
--   number of history samples
-- 1.3.6.1.4.1.231.7.1.2.2.1.8.1.1.7
		sheRmonControlBucketsRequested OBJECT-TYPE
			SYNTAX INTEGER (1..65535)
			MAX-ACCESS read-write
			STATUS current
			DESCRIPTION
				" The requested number of discrete time intervals
				over which data is to be saved in the part of the
				media-specific table associated with this
				historyControlEntry.
				
				When this object is created or modified, the probe
				should set historyControlBucketsGranted as closely to
				this object as is possible for the particular probe
				implementation and available resources."
			DEFVAL { 50 }
			::= { sheRmonControl 7 }

		
--   type of counter : 15min or day counter sampling
-- 1.3.6.1.4.1.231.7.1.2.2.1.8.1.1.8
		sheRmonControlInterval OBJECT-TYPE
			SYNTAX INTEGER (1..3600)
			MAX-ACCESS read-write
			STATUS current
			DESCRIPTION
				"The interval in seconds over which the data is
				sampled for each bucket in the part of the
				media-specific table associated with this
				historyControlEntry.  This interval can
				be set to any number of seconds between 1 and
				3600 (1 hour).
				
				Because the counters in a bucket may overflow at their
				maximum value with no indication, a prudent manager
				will take into account the possibility of overflow
				in any of the associated counters.  It is important
				to consider the minimum time in which any counter
				could overflow on a particular media type and set
				the historyControlInterval object to a value less
				than this interval.  This is typically most
				important for the 'octets' counter in any
				media-specific table.  For example, on an Ethernet
				network, the etherHistoryOctets counter could
				overflow in about one hour at the Ethernet's maximum
				utilization. "
			DEFVAL { 1800 }
			::= { sheRmonControl 8 }

		
--  1.3.6.1.4.1.231.7.1.2.2.1.8.1.1.9
		sheRmonControlOwner OBJECT-TYPE
			SYNTAX OwnerString
			MAX-ACCESS read-write
			STATUS current
			DESCRIPTION
				"The entity that configured this entry and is
				therefore using the resources assigned to it."
			::= { sheRmonControl 9 }

		
--  1.3.6.1.4.1.231.7.1.2.2.1.8.1.1.10
		sheRmonControlIndex OBJECT-TYPE
			SYNTAX INTEGER (1..65535)
			MAX-ACCESS read-write
			STATUS current
			DESCRIPTION
				" An index that uniquely identifies an entry in the
				historyControl table.  Each such entry defines a
				set of samples at a particular interval for an
				interface on the device. 
				This is used to delete a sample.."
			::= { sheRmonControl 10 }

		
--  1.3.6.1.4.1.231.7.1.2.2.1.8.1.2
		sheRmonNotifications OBJECT IDENTIFIER ::= { sheRmonConfigurationObjects 2 }

		
--  1.3.6.1.4.1.231.7.1.2.2.1.8.1.2.1
		sheSampleCreated NOTIFICATION-TYPE
			OBJECTS { sheRmonControlTimeStamp, sheRmonControlIndex, sheRmonControlDataSource }
			STATUS current
			DESCRIPTION 
				"Notification for command execution."
			::= { sheRmonNotifications 1 }

		
--  1.3.6.1.4.1.231.7.1.2.2.1.8.1.2.2
		sheSampleDeleted NOTIFICATION-TYPE
			OBJECTS { sheRmonControlTimeStamp, sheRmonControlIndex, sheRmonControlDataSource }
			STATUS current
			DESCRIPTION 
				"Notification for command execution."
			::= { sheRmonNotifications 2 }

		
--  1.3.6.1.4.1.231.7.1.2.2.1.8.1.2.3
		sheEtherStatsCountersCleared NOTIFICATION-TYPE
			OBJECTS { sheRmonControlIndex, sheRmonControlTimeStamp }
			STATUS current
			DESCRIPTION 
				"One entry in the EtherStatsTable of the Rmon-Mib was cleared."
			::= { sheRmonNotifications 3 }

		
--  1.3.6.1.4.1.231.7.1.2.2.1.8.1.2.4
		sheAlarmSampleCreated NOTIFICATION-TYPE
			OBJECTS { sheRmonAlarmControlTimeStamp, sheRmonAlarmControlIndex, sheRmonAlarmControlInterval, sheRmonAlarmControlVariable, sheRmonAlarmControlSampleType, 
				sheRmonAlarmControlStartupAlarm, sheRmonAlarmControlRisingThreshold, sheRmonAlarmControlFallingThreshold, sheRmonAlarmControlRisingEventIndex, sheRmonAlarmControlFallingEventIndex, 
				sheRmonAlarmControlOwner }
			STATUS current
			DESCRIPTION 
				"Notification for command execution."
			::= { sheRmonNotifications 4 }

		
--  1.3.6.1.4.1.231.7.1.2.2.1.8.1.2.5
		sheAlarmSampleDeleted NOTIFICATION-TYPE
			OBJECTS { sheRmonAlarmControlTimeStamp, sheRmonAlarmControlIndex }
			STATUS current
			DESCRIPTION 
				"Notification for command execution."
			::= { sheRmonNotifications 5 }

		
--  1.3.6.1.4.1.231.7.1.2.2.1.8.1.2.6
		sheEventSampleCreated NOTIFICATION-TYPE
			OBJECTS { sheRmonEventControlTimeStamp, sheRmonEventControlIndex, sheRmonEventControlDescription, sheRmonEventControlType, sheRmonEventControlCommunity, 
				sheRmonEventControlOwner }
			STATUS current
			DESCRIPTION 
				"Notification for command execution."
			::= { sheRmonNotifications 6 }

		
--  1.3.6.1.4.1.231.7.1.2.2.1.8.1.2.7
		sheEventSampleDeleted NOTIFICATION-TYPE
			OBJECTS { sheRmonEventControlTimeStamp, sheRmonEventControlIndex }
			STATUS current
			DESCRIPTION 
				"Notification for command execution."
			::= { sheRmonNotifications 7 }

		
--  1.3.6.1.4.1.231.7.1.2.2.1.8.1.2.8
		sheRmonRisingThreshold NOTIFICATION-TYPE
			OBJECTS { alarmVariable, alarmRisingThreshold }
			STATUS current
			DESCRIPTION 
				"Notification for command execution."
			::= { sheRmonNotifications 8 }

		
--  1.3.6.1.4.1.231.7.1.2.2.1.8.1.2.9
		sheRmonFallingThreshold NOTIFICATION-TYPE
			OBJECTS { alarmVariable, alarmFallingThreshold }
			STATUS current
			DESCRIPTION 
				"Notification for command execution."
			::= { sheRmonNotifications 9 }

		
--  1.3.6.1.4.1.231.7.1.2.2.1.8.1.3
		sheRmonConformance OBJECT IDENTIFIER ::= { sheRmonConfigurationObjects 3 }

		
--  1.3.6.1.4.1.231.7.1.2.2.1.8.1.3.1
		sheRmonCompliances OBJECT IDENTIFIER ::= { sheRmonConformance 1 }

		
--  1.3.6.1.4.1.231.7.1.2.2.1.8.1.3.1.1
-- this module
		sheRmonCompliance MODULE-COMPLIANCE
			STATUS current
			DESCRIPTION 
				"Description."
			MODULE -- this module
				MANDATORY-GROUPS { sheRmonControlGroup, sheRmonNotificationGroup }
			::= { sheRmonCompliances 1 }

		
--  1.3.6.1.4.1.231.7.1.2.2.1.8.1.3.2
		sheRmonGroups OBJECT IDENTIFIER ::= { sheRmonConformance 2 }

		
--  1.3.6.1.4.1.231.7.1.2.2.1.8.1.3.2.1
		sheRmonControlGroup OBJECT-GROUP
			OBJECTS { sheRmonAlarmControlRequest, sheRmonAlarmControlStatus, sheRmonAlarmControlTimer, sheRmonAlarmControlReqResult, sheRmonAlarmControlTimeStamp, 
				sheRmonAlarmControlIndex, sheRmonAlarmControlInterval, sheRmonAlarmControlVariable, sheRmonAlarmControlSampleType, sheRmonAlarmControlStartupAlarm, 
				sheRmonAlarmControlRisingThreshold, sheRmonAlarmControlFallingThreshold, sheRmonAlarmControlRisingEventIndex, sheRmonAlarmControlFallingEventIndex, sheRmonAlarmControlOwner, 
				sheRmonEventControlRequest, sheRmonEventControlStatus, sheRmonEventControlTimer, sheRmonEventControlReqResult, sheRmonEventControlTimeStamp, 
				sheRmonEventControlIndex, sheRmonEventControlDescription, sheRmonEventControlType, sheRmonEventControlCommunity, sheRmonEventControlOwner, 
				sheRmonControlIndex, sheRmonControlRequest, sheRmonControlStatus, sheRmonControlTimer, sheRmonControlControlReqResult, 
				sheRmonControlTimeStamp, sheRmonControlDataSource, sheRmonControlBucketsRequested, sheRmonControlInterval, sheRmonControlOwner
				 }
			STATUS current
			DESCRIPTION 
				"Description."
			::= { sheRmonGroups 1 }

		
--  1.3.6.1.4.1.231.7.1.2.2.1.8.1.3.2.2
		sheRmonNotificationGroup NOTIFICATION-GROUP
			NOTIFICATIONS { sheSampleCreated, sheSampleDeleted, sheEtherStatsCountersCleared, sheAlarmSampleCreated, sheAlarmSampleDeleted, 
				sheEventSampleCreated, sheEventSampleDeleted, sheRmonRisingThreshold, sheRmonFallingThreshold }
			STATUS current
			DESCRIPTION 
				"Description."
			::= { sheRmonGroups 2 }

		
--  1.3.6.1.4.1.231.7.1.2.2.1.8.1.4
		sheRmonAlarmControl OBJECT IDENTIFIER ::= { sheRmonConfigurationObjects 4 }

		
--  1.3.6.1.4.1.231.7.1.2.2.1.8.1.4.1
		sheRmonAlarmControlRequest OBJECT-TYPE
			SYNTAX SheRmonControlRequestType
			MAX-ACCESS read-write
			STATUS current
			DESCRIPTION
				"Specifies the user command. 
				
				createSample:
				     this command create an entry is RMON alarmTable.
				
				deleteSample: 
				     this command delete an entry is RMON alarmTable."
			::= { sheRmonAlarmControl 1 }

		
--  1.3.6.1.4.1.231.7.1.2.2.1.8.1.4.2
		sheRmonAlarmControlStatus OBJECT-TYPE
			SYNTAX SheControlStatusType
			MAX-ACCESS read-only
			STATUS current
			DESCRIPTION
				"The status of a control request"
			::= { sheRmonAlarmControl 2 }

		
--  1.3.6.1.4.1.231.7.1.2.2.1.8.1.4.3
		sheRmonAlarmControlTimer OBJECT-TYPE
			SYNTAX Unsigned32
			MAX-ACCESS read-only
			STATUS current
			DESCRIPTION
				"The maximum wait time for the manager for command ending. For long running commands. 
				The manager reads this value from the DSLAM."
			::= { sheRmonAlarmControl 3 }

		
--  1.3.6.1.4.1.231.7.1.2.2.1.8.1.4.4
		sheRmonAlarmControlReqResult OBJECT-TYPE
			SYNTAX SheRmonControlRequestResultType
			MAX-ACCESS read-only
			STATUS current
			DESCRIPTION
				"The result of the last user command."
			::= { sheRmonAlarmControl 4 }

		
--  1.3.6.1.4.1.231.7.1.2.2.1.8.1.4.5
		sheRmonAlarmControlTimeStamp OBJECT-TYPE
			SYNTAX Unsigned32
			MAX-ACCESS read-only
			STATUS current
			DESCRIPTION
				"The time stamp of the last command (end of command)."
			::= { sheRmonAlarmControl 5 }

		
--  1.3.6.1.4.1.231.7.1.2.2.1.8.1.4.6
		sheRmonAlarmControlIndex OBJECT-TYPE
			SYNTAX INTEGER (1..65535)
			MAX-ACCESS read-write
			STATUS current
			DESCRIPTION
				"Index of sampling"
			::= { sheRmonAlarmControl 6 }

		
--  1.3.6.1.4.1.231.7.1.2.2.1.8.1.4.7
		sheRmonAlarmControlInterval OBJECT-TYPE
			SYNTAX INTEGER
			MAX-ACCESS read-write
			STATUS current
			DESCRIPTION
				"To specify the sampling interval"
			::= { sheRmonAlarmControl 7 }

		
--  1.3.6.1.4.1.231.7.1.2.2.1.8.1.4.8
		sheRmonAlarmControlVariable OBJECT-TYPE
			SYNTAX OBJECT IDENTIFIER
			MAX-ACCESS read-write
			STATUS current
			DESCRIPTION
				"The object identifier of the particular variable to be sampled."
			::= { sheRmonAlarmControl 8 }

		
--  1.3.6.1.4.1.231.7.1.2.2.1.8.1.4.9
		sheRmonAlarmControlSampleType OBJECT-TYPE
			SYNTAX SheRmonAlarmSampleType
			MAX-ACCESS read-write
			STATUS current
			DESCRIPTION
				"The method of sampling the selected variable and calculating the value to be compared against the thresholds."
			::= { sheRmonAlarmControl 9 }

		
--  1.3.6.1.4.1.231.7.1.2.2.1.8.1.4.10
		sheRmonAlarmControlStartupAlarm OBJECT-TYPE
			SYNTAX SheRmonAlarmStartupAlarm
			MAX-ACCESS read-write
			STATUS current
			DESCRIPTION
				"The alarm that may be sent when this entry is first set to valid."
			::= { sheRmonAlarmControl 10 }

		
--  1.3.6.1.4.1.231.7.1.2.2.1.8.1.4.11
		sheRmonAlarmControlRisingThreshold OBJECT-TYPE
			SYNTAX INTEGER
			MAX-ACCESS read-write
			STATUS current
			DESCRIPTION
				"A threshold for the sampled statistic."
			::= { sheRmonAlarmControl 11 }

		
--  1.3.6.1.4.1.231.7.1.2.2.1.8.1.4.12
		sheRmonAlarmControlFallingThreshold OBJECT-TYPE
			SYNTAX INTEGER
			MAX-ACCESS read-write
			STATUS current
			DESCRIPTION
				"A threshold for the sampled statistic."
			::= { sheRmonAlarmControl 12 }

		
--  1.3.6.1.4.1.231.7.1.2.2.1.8.1.4.13
		sheRmonAlarmControlRisingEventIndex OBJECT-TYPE
			SYNTAX INTEGER
			MAX-ACCESS read-write
			STATUS current
			DESCRIPTION
				"The index of the eventEntry that is used when a rising threshold is crossed."
			::= { sheRmonAlarmControl 13 }

		
--  1.3.6.1.4.1.231.7.1.2.2.1.8.1.4.14
		sheRmonAlarmControlFallingEventIndex OBJECT-TYPE
			SYNTAX INTEGER
			MAX-ACCESS read-write
			STATUS current
			DESCRIPTION
				"The index of the eventEntry that is used when a falling threshold is crossed."
			::= { sheRmonAlarmControl 14 }

		
--  1.3.6.1.4.1.231.7.1.2.2.1.8.1.4.15                                    
		sheRmonAlarmControlOwner OBJECT-TYPE
			SYNTAX OwnerString
			MAX-ACCESS read-write
			STATUS current
			DESCRIPTION
				"The entity that configured this entry and is therefore using the resources assigned to it."
			::= { sheRmonAlarmControl 15 }

		
--  1.3.6.1.4.1.231.7.1.2.2.1.8.1.5
		sheRmonEventControl OBJECT IDENTIFIER ::= { sheRmonConfigurationObjects 5 }

		
--  1.3.6.1.4.1.231.7.1.2.2.1.8.1.5.1
		sheRmonEventControlRequest OBJECT-TYPE
			SYNTAX SheRmonControlRequestType
			MAX-ACCESS read-write
			STATUS current
			DESCRIPTION
				"Specifies the user command. 
				
				createSample:
				     this command create an entry is RMON eventTable.
				
				deleteSample: 
				     this command delete an entry is RMON eventTable."
			::= { sheRmonEventControl 1 }

		
--  1.3.6.1.4.1.231.7.1.2.2.1.8.1.5.2
		sheRmonEventControlStatus OBJECT-TYPE
			SYNTAX SheControlStatusType
			MAX-ACCESS read-only
			STATUS current
			DESCRIPTION
				"The status of a control request"
			::= { sheRmonEventControl 2 }

		
--  1.3.6.1.4.1.231.7.1.2.2.1.8.1.5.3
		sheRmonEventControlTimer OBJECT-TYPE
			SYNTAX Unsigned32
			MAX-ACCESS read-only
			STATUS current
			DESCRIPTION
				"The maximum wait time for the manager for command ending. 
				For long running commands. The manager reads this value from the DSLAM."
			::= { sheRmonEventControl 3 }

		
--  1.3.6.1.4.1.231.7.1.2.2.1.8.1.5.4
		sheRmonEventControlReqResult OBJECT-TYPE
			SYNTAX SheRmonControlRequestResultType
			MAX-ACCESS read-only
			STATUS current
			DESCRIPTION
				"The result of the last user command"
			::= { sheRmonEventControl 4 }

		
--  1.3.6.1.4.1.231.7.1.2.2.1.8.1.5.5
		sheRmonEventControlTimeStamp OBJECT-TYPE
			SYNTAX Unsigned32
			MAX-ACCESS read-only
			STATUS current
			DESCRIPTION
				"The time stamp of the last command (end of command)"
			::= { sheRmonEventControl 5 }

		
--  1.3.6.1.4.1.231.7.1.2.2.1.8.1.5.6
		sheRmonEventControlIndex OBJECT-TYPE
			SYNTAX INTEGER (1..65535)
			MAX-ACCESS read-write
			STATUS current
			DESCRIPTION
				"Index of sampling"
			::= { sheRmonEventControl 6 }

		
--  1.3.6.1.4.1.231.7.1.2.2.1.8.1.5.7
		sheRmonEventControlDescription OBJECT-TYPE
			SYNTAX DisplayString
			MAX-ACCESS read-write
			STATUS current
			DESCRIPTION
				"A comment describing this event entry"
			::= { sheRmonEventControl 7 }

		
--  1.3.6.1.4.1.231.7.1.2.2.1.8.1.5.8
		sheRmonEventControlType OBJECT-TYPE
			SYNTAX SheRmonEventType
			MAX-ACCESS read-write
			STATUS current
			DESCRIPTION
				"The type of notification that the probe will make about this event"
			::= { sheRmonEventControl 8 }

		
--  1.3.6.1.4.1.231.7.1.2.2.1.8.1.5.9
		sheRmonEventControlCommunity OBJECT-TYPE
			SYNTAX OCTET STRING
			MAX-ACCESS read-write
			STATUS current
			DESCRIPTION
				"If an SNMP trap is to be sent, it will be sent to the SNMP community specified by this octet string."
			::= { sheRmonEventControl 9 }

		
--  1.3.6.1.4.1.231.7.1.2.2.1.8.1.5.10
		sheRmonEventControlOwner OBJECT-TYPE
			SYNTAX OwnerString
			MAX-ACCESS read-write
			STATUS current
			DESCRIPTION
				"The entity that configured this entry and is therefore using the resources assigned to it."
			::= { sheRmonEventControl 10 }

		
	
	END

--
-- she-rmon-mib.mib
--
