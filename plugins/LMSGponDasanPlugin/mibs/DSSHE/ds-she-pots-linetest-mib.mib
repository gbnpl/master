--
-- she-pots-linetest-mib.mib
-- MIB generated by MG-SOFT Visual MIB Builder Version 6.0  Build 88
-- Wednesday, April 02, 2008 at 11:42:31
--

	DS-SHE-POTS-LINETEST-MIB DEFINITIONS ::= BEGIN
 
		IMPORTS
			entPhysicalIndex, PhysicalIndex			
				FROM ENTITY-MIB			
			ifIndex, InterfaceIndex			
				FROM IF-MIB			
			sheAlarmTimeAndDate, sheAlarmReportingSource, sheAlarmReportingSourceType, sheAlarmSeverity			
				FROM DS-SHE-ALARMING-MIB			
			shePotsMib, shePotsCompliances, shePotsGroups			
				FROM DS-SHE-POTS-MIB			
			SheControlStatusType			
				FROM DS-SHE-TC-MIB			
			OBJECT-GROUP, MODULE-COMPLIANCE, NOTIFICATION-GROUP			
				FROM SNMPv2-CONF			
			Unsigned32, Gauge32, Counter64, OBJECT-TYPE, MODULE-IDENTITY, 
			NOTIFICATION-TYPE			
				FROM SNMPv2-SMI			
			DateAndTime, TruthValue			
				FROM SNMPv2-TC;
	
	
		shePotsLineTest MODULE-IDENTITY 
			LAST-UPDATED "200804021251Z"		-- April 02, 2008 at 12:51 GMT
			ORGANIZATION 
				"Nokia Siemens Network"
			CONTACT-INFO 
				"Li Jinxin,
				SNLB CD/FN RDC NI(BJ)
				jinxin.li@nsn.com
				+86 (10) 58671467
				
				Gerd Barchmann
				COO BBA DSLAM RD SDE HW1
				gerd.barchmann@nsn.com
				+49 3834 555654"
			DESCRIPTION 
				"Extention for she-pots-mib to support ILTF linetest. "
			REVISION "200710241410Z"		-- October 24, 2007 at 14:10 GMT
			DESCRIPTION 
				"Initial version for R2.8 for advanced linetest feature support on pots lines."
			REVISION "200711141122Z"		-- November 14, 2007 at 11:22 GMT
			DESCRIPTION 
				"Correct controlrequest and trap for autoMeasureSwitch."
			REVISION "200711261042Z"		-- November 26, 2007 at 10:42 GMT
			DESCRIPTION 
				"Move PATStarttime to PATthreshold group, since it is a system-level parameter.
				Remove shePotsLineTestDistanceToOpenTestMeasuredCap (according to AGLU change)"
			REVISION "200801311742Z"		-- January 31, 2008 at 17:42 GMT
			DESCRIPTION 
				"1.Revise MibSwtich Description
				2.Add test list limitation into the description of AutoMeasure and Deploy and define default test list for them.
				3.Revise PAT thresholds about range, defval and  unit
				4.Revise PAT pollingtime  about range, defval
				5.Add comments that Calibration is cancelled now
				6.Add comments for ILTF and their traps
				7.Revise ILTF range, defval and  unit
				"
			REVISION "200803201137Z"		-- March 20, 2008 at 11:37 GMT
			DESCRIPTION 
				"Correct Alarm notification object list to common format."
			REVISION "200804021009Z"		-- April 02, 2008 at 10:09 GMT
			DESCRIPTION 
				"Correct Traps notification object list - remove alarmID and give correct descriptions.
				Reversal test are excluded from Deploy testlist.
				Correct parameter range for ToneGenerationTestControlTestFreqX."
			::= { shePotsMib 10 }

		
	
--
-- Type definitions
--
	
		ShePotsLineTestSwitchType ::= INTEGER
			{
			disable(0),
			enable(1)
			}

--                         
		ShePotsLineTestControlRequestType ::= INTEGER
			{
			none(0),
			noRequest(1),
			setAutoMeasureSwitch(2),
			setsetCalibrationSwitch(3),
			setPatThreshold(4),
			setPatSwitch(5),
			setVptlTidOnOffHookSelfTest(6),
			setDCFeedSelfTest(7),
			setRingingSelfTest(8),
			setTransmitionSelfTest(9),
			setTransHybridLossTest(10),
			setNoiseMeasurementTest(11),
			setForeignDCVoltage(12),
			setForeignACVoltageTest(13),
			setDcLoopResistanceTest(14),
			set3ElementInsulationResistanceTest(15),
			set3ElementInsulationCapacitanceTest(16),
			setReceiverOffHookTest(17),
			setDistanceToOpenTest(18),
			setRingerEquivalencyNumberTest(19),
			setDTMFandPulseDigitMeasurementTest(20),
			setToneGenerationTest(21),
			setReadLoopandBatteryConditionsTest(22),
			setMeteringSelfTest(23),
			setForeignACcurrentsTest(24),
			setHowlerTest(25),
			setReversalTest(26),
			setRingingMonitorTest(27),
			setMibSwitch(28),
			setAutoMeasureTestList(29),
			setDeployTestList(30),
			setDeployTest(31)
			}

--                      
		ShePotsLineTestControlRequestResultType ::= INTEGER
			{
			noRequest(1),
			failed(2),
			voipNotInitialized(3),
			memoryAllocFailure(4),
			defProfilesCreationFailure(5),
			exceedMaxProfileNum(6),
			exceedMaxVgwNum(7),
			exceedMaxSlotNum(8),
			invalidParameter(9),
			vgwMemberListNotEmpty(10),
			profileIsInUse(11),
			duplicatedIndex(12),
			duplicatedPort(13),
			duplicatedName(14),
			tooLongName(15),
			profileEntryNotFound(16),
			cannotDeleteDefProfile(17),
			cannotModifyDefProfileName(18),
			tableIsEmpty(19),
			tableEntryNotFound(20),
			memberBelongsToOtherVgw(21),
			testOnGoing(22),
			porNotInTestStatus(23),
			maxLessThanMin(24),
			duplicatedIpAddress(25),
			duplicatedSlotIpHost(26),
			ipHostGatewayFailed(27),
			adminNotInTestStatus(28),
			comExecStarted(30),
			paramFaulty(31),
			requestBusy(32),
			setDataFailed(34),
			aswTimeout(35),
			commandFailed(36),
			commandSucceeded(37),
			ipHostProtection(38),
			hlminSmallthanHkmin(39),
			exceedMaxHighfeedPortNum(40),
			highfeedPortIdInvalid(41),
			highfeedPortsNumInvalid(42),
			portNotInDisableStatus(43),
			lineTestMibError(44),
			autoSlotOn(45),
			patStarttimeNotSet(46),
			patTestOnGoing(47),
			deployTestOnGoing(48),
			deployTestListNotSet(49),
			eRESInvalidIP(201),
			eRESInvalidPort(202),
			eRESInvalidMac(203),
			eRESInvalidToneIDX(204),
			eRESErrInVapi(205),
			eRESUnknownToneType(206),
			eRESInvalidRtpScheme(207),
			eRESChCrteErr(208),
			eRESChOptErr(209),
			eRESChAttErr(210),
			eRESChDelErr(211),
			eRESIdlePots(212),
			eRESInvalidCmd(213),
			eRESInvalidPTime(214),
			eRESAlreadyOpened(215),
			eRESAlreadyClosed(216),
			eRESOutOfResourceDB(217),
			eRESInvalidConfID(218),
			eRESInvalidPartID(219),
			eRESErrInVcp(220),
			eRESInitVcpErr(221),
			eRESInvalidNosName(222),
			eRESAlreadyProgress(223),
			eRESErrNosSize(224),
			eRESFailNosDnld(225),
			eRESInvalidConn(226),
			eRESInvalidTermType(227),
			eRESInvalidSwchdNogagMsgType(228),
			eRESReleaseCallDBFailed(229),
			eRESReleasePotsChnlFailed(230),
			eRESIltfTestDone(231),
			eRESIltfTestRunning(232),
			eRESIltfNoOutput(233),
			eRESIltfOutputError(234),
			eRESIltfTestBusy(235),
			eRESIltfCallBusy(236),
			eRESIltfInvalidParam(237),
			eRESIltfVcpBusy(238),
			eRESReverseError(239),
			eRESIltfOndemandRunning(240),
			eRESInvalidAutoTestFlag(241),
			eRESInvalidInput(242),
			eRESInvalidPointer(243),
			eRESInvalidTestID(244),
			eRESAutoTestSwitchFlagON(245),
			eRESAutoTestForbidden(246),
			eRESAutoTestFinished(247)
			}

		ShePotsLineTestAlarmType ::= INTEGER
			{
			null(0),
			shePotsLineTestpat3EleResFltAlm(1),
			shePotsLineTestpat3eleCapFltAlm(2),
			shePotsLineTestpatNoiseFltAlm(3),
			shePotsLineTestpatDcFeedFltAlm(4),
			shePotsLineTestAcAlarms(5),
			shePotsLineTestDcAlarms(6),
			shePotsLineTestGkAlarms(7),
			shePotsLineTestThermAlalarms(8)
			}

		ShePotsLineTestVptlOnOffHookSelfTestStatusType ::= INTEGER
			{
			unknown(0),
			aborted(1),
			hwFault(2),
			passed(3)
			}

		ShePotsLineTestTriggerType ::= INTEGER
			{
			null(0),
			autoMeasurementAcTest(1),
			autoMeasurementDcTest(2),
			autoMeasurementGkTest(3),
			deployTest(4),
			onDemandTest(5),
			patTest(6)
			}

		ShePotsLineTestNoiseMeasurementTestControlVpTestFilterType ::= INTEGER
			{
			vPFilterNone(0),
			vPFilter3kHz(1),
			vPFilterCMsg(2),
			vPFilter15kHz(3),
			vPFilter3p4kHz(4),
			vPFilterD(5)
			}

		ShePotsLineTestRingerEquivalencyNumberTestControlRentestType ::= INTEGER
			{
			vPTLRenRegularPhoneTest(0),
			vPTLRenElectronicPhoneTest(1)
			}

		ShePotsLineTestDTMFandPulseDigitMeasureTestkTestResultType ::= INTEGER
			{
			vPKtDtmfDet(0),
			vPKtDtmfMes(1),
			vPKtPulse(2),
			vPKtThreshDet(3)
			}

		ShePotsLineTestVpDigitType ::= INTEGER
			{
			null(0),
			vpDIG1(1),
			vpDIG2(2),
			vpDIG3(3),
			vpDIG4(4),
			vpDIG5(5),
			vpDIG6(6),
			vpDIG7(7),
			vpDIG8(8),
			vpDIG9(9),
			vDIGZero(10),
			vpDIGAster(11),
			vpDIGPound(12),
			vDIGA(13),
			vDIGB(14),
			vDIGC(15),
			vDIGD(16),
			vDIGNone(17)
			}

		ShePotsLineTestDTMFandPulseDigitMeasureTestControlTestType ::= INTEGER
			{
			vPTLKeyDtmfTest(0),
			vPTLKeyPulseTest(1),
			vPTLKeyBoth(2)
			}

		ShePotsLineTestHowlerTestControlToneType ::= INTEGER { vPTLNorthAmericanHowlerTone(0) }

	
	
--
-- Node definitions
--
	
-- 1.3.6.1.4.1.231.7.1.2.2.1.38.10.1
		shePotsLineTestMibSwitchGroup OBJECT IDENTIFIER ::= { shePotsLineTest 1 }

		
--         1.3.6.1.4.1.231.7.1.2.2.1.38.10.1.1
		shePotsLineTestMibSwitch OBJECT-TYPE
			SYNTAX ShePotsLineTestSwitchType
			MAX-ACCESS read-only
			STATUS current
			DESCRIPTION
				"Switch for MIB version control.
				When it is set to 1, the new line  test solution is activated 
				which can be controlled by new line test solution ACI. When it is set to 0,
				 the old line test solution is activated which can be controlled by old ACI."
			::= { shePotsLineTestMibSwitchGroup 1 }

		
--         1.3.6.1.4.1.231.7.1.2.2.1.38.10.2
		shePotsLineTestMibSwitchControl OBJECT IDENTIFIER ::= { shePotsLineTest 2 }

		
--         1.3.6.1.4.1.231.7.1.2.2.1.38.10.2.1
		shePotsLineTestMibSwitchControlRequest OBJECT-TYPE
			SYNTAX ShePotsLineTestControlRequestType
			MAX-ACCESS read-write
			STATUS current
			DESCRIPTION
				"setMibSwitch:
				shePotsLineTestMibSwitch"
			::= { shePotsLineTestMibSwitchControl 1 }

		
--         1.3.6.1.4.1.231.7.1.2.2.1.38.10.2.2
		shePotsLineTestMibSwitchControlStatus OBJECT-TYPE
			SYNTAX SheControlStatusType
			MAX-ACCESS read-only
			STATUS current
			DESCRIPTION
				"The status of a user command."
			::= { shePotsLineTestMibSwitchControl 2 }

		
--         1.3.6.1.4.1.231.7.1.2.2.1.38.10.2.3
		shePotsLineTestMibSwitchControlTimer OBJECT-TYPE
			SYNTAX Gauge32
			MAX-ACCESS read-only
			STATUS current
			DESCRIPTION
				"The maximum wait time for the manager for a long running user command."
			::= { shePotsLineTestMibSwitchControl 3 }

		
--         1.3.6.1.4.1.231.7.1.2.2.1.38.10.2.4
		shePotsLineTestMibSwitchControlTimeStamp OBJECT-TYPE
			SYNTAX Unsigned32
			MAX-ACCESS read-only
			STATUS current
			DESCRIPTION
				"The time stamp of the last command (end of command)."
			::= { shePotsLineTestMibSwitchControl 4 }

		
--         1.3.6.1.4.1.231.7.1.2.2.1.38.10.2.5
		shePotsLineTestMibSwitchControlControlReqResult OBJECT-TYPE
			SYNTAX ShePotsLineTestControlRequestResultType
			MAX-ACCESS read-only
			STATUS current
			DESCRIPTION
				"The result of the last user command."
			::= { shePotsLineTestMibSwitchControl 5 }

		
--         1.3.6.1.4.1.231.7.1.2.2.1.38.10.2.6
		shePotsLineTestMibSwitchControlSwitch OBJECT-TYPE
			SYNTAX ShePotsLineTestSwitchType
			MAX-ACCESS read-write
			STATUS current
			DESCRIPTION
				"Switch for MIB version control. Default value is 0 disable
				When it is set to 1, the new line  test solution is activated 
				which can be controlled by new line test solution ACI. When it is set to 0,
				 the old line test solution is activated which can be controlled by old ACI.
				the default value is disable."
			DEFVAL { disable }
			::= { shePotsLineTestMibSwitchControl 6 }

		
--         1.3.6.1.4.1.231.7.1.2.2.1.38.10.3
		shePotsLineTestAlarmDefinitionGroup OBJECT IDENTIFIER ::= { shePotsLineTest 3 }

		
--         1.3.6.1.4.1.231.7.1.2.2.1.38.10.3.1
		shePotsLineTestAlarmDefinition OBJECT IDENTIFIER ::= { shePotsLineTestAlarmDefinitionGroup 1 }

		
--         1.3.6.1.4.1.231.7.1.2.2.1.38.10.3.1.1
		shePotsLineTestAlarmID OBJECT-TYPE
			SYNTAX Counter64
			MAX-ACCESS read-only
			STATUS current
			DESCRIPTION
				"Alarm ID which indicates alarms uniquely in the system."
			::= { shePotsLineTestAlarmDefinition 1 }

		
--         1.3.6.1.4.1.231.7.1.2.2.1.38.10.3.1.2
		shePotsLineTestAlarm OBJECT-TYPE
			SYNTAX ShePotsLineTestAlarmType
			MAX-ACCESS read-only
			STATUS current
			DESCRIPTION
				"Indicates the alarm types in the system.
				1: null(0) 
				2: shePotsLineTestpat3EleResFltAlm(1) 
				3: shePotsLineTestpat3eleCapFltAlm(2) 
				4: shePotsLineTestpatNoiseFltAlm(3) 
				5: shePotsLineTestpatDcFeedFltAlm(4) 
				6: shePotsLineTestAcAlarms(5) 
				7: shePotsLineTestDcAlarms(6) 
				8: shePotsLineTestGkAlarms(7) 
				9: shePotsLineTestThermAlalarms(8) "
			::= { shePotsLineTestAlarmDefinition 2 }

		
--         1.3.6.1.4.1.231.7.1.2.2.1.38.10.4
		shePotsLineTestAutoMeasureGroup OBJECT IDENTIFIER ::= { shePotsLineTest 4 }

		
--         1.3.6.1.4.1.231.7.1.2.2.1.38.10.4.1
		shePotsLineTestAutoMeasureTestListGroup OBJECT IDENTIFIER ::= { shePotsLineTestAutoMeasureGroup 1 }

		
--         1.3.6.1.4.1.231.7.1.2.2.1.38.10.4.1.1
		shePotsLineTestAutoMeasureTestListAcTestList OBJECT-TYPE
			SYNTAX OCTET STRING (SIZE (0..31))
			MAX-ACCESS read-only
			STATUS current
			DESCRIPTION
				"AC Test list. Includes testID of ILTF items 
				and every byte stands for an ID(0~21), -1 means the end of the list.
				shePotsLineTestVptlTidOnOffHookSelfTest(7),
				shePotsLineTestDCFeedSelfTest(6),
				shePotsLineTestRingingSelfTest(8),
				shePotsLineTestTransmitionSelfTest(9),
				shePotsLineTestTransHybridLossTest(13),
				shePotsLineTestNoiseMeasurementTest(5),
				shePotsLineTestForeignDCVoltage(0),//
				shePotsLineTestForeignACVoltageTest(1),
				shePotsLineTestDcLoopResistanceTest(2),
				shePotsLineTest3ElementInsulationResistanceTest(3),
				shePotsLineTest3ElementInsulationCapacitanceTest(12),
				shePotsLineTestReceiverOffHookTest(4),
				shePotsLineTestDistanceToOpenTest(14),
				shePotsLineTestRingerEquivalencyNumberTest(11),
				shePotsLineTestDTMFandPulseDigitMeasurementTest(15),
				shePotsLineTestToneGenerationTest(16),
				shePotsLineTestReadLoopandBatteryConditionsTest(10),
				shePotsLineTestMeteringSelfTest(17),
				shePotsLineTestForeignACcurrentsTest(18),
				shePotsLineTestHowlerTest(19),
				shePotsLineTestReversalTest(21)
				
				In AutoMeasure test following test items should be excluded
				tonegen, howler, reverse, dtmf"
			::= { shePotsLineTestAutoMeasureTestListGroup 1 }

		
--         1.3.6.1.4.1.231.7.1.2.2.1.38.10.4.1.2
		shePotsLineTestAutoMeasureTestListDcTestList OBJECT-TYPE
			SYNTAX OCTET STRING (SIZE (0..31))
			MAX-ACCESS read-only
			STATUS current
			DESCRIPTION
				"DC Test list. Includes testID of ILTF items 
				and every byte stands for an ID(0~21), -1 means the end of the list.
				shePotsLineTestVptlTidOnOffHookSelfTest(7),
				shePotsLineTestDCFeedSelfTest(6),
				shePotsLineTestRingingSelfTest(8),
				shePotsLineTestTransmitionSelfTest(9),
				shePotsLineTestTransHybridLossTest(13),
				shePotsLineTestNoiseMeasurementTest(5),
				shePotsLineTestForeignDCVoltage(0),//
				shePotsLineTestForeignACVoltageTest(1),
				shePotsLineTestDcLoopResistanceTest(2),
				shePotsLineTest3ElementInsulationResistanceTest(3),
				shePotsLineTest3ElementInsulationCapacitanceTest(12),
				shePotsLineTestReceiverOffHookTest(4),
				shePotsLineTestDistanceToOpenTest(14),
				shePotsLineTestRingerEquivalencyNumberTest(11),
				shePotsLineTestDTMFandPulseDigitMeasurementTest(15),
				shePotsLineTestToneGenerationTest(16),
				shePotsLineTestReadLoopandBatteryConditionsTest(10),
				shePotsLineTestMeteringSelfTest(17),
				shePotsLineTestForeignACcurrentsTest(18),
				shePotsLineTestHowlerTest(19),
				shePotsLineTestReversalTest(21)
				
				In AutoMeasure test following test items should be excluded
				tonegen, howler, reverse, dtmf"
			::= { shePotsLineTestAutoMeasureTestListGroup 2 }

		
--         1.3.6.1.4.1.231.7.1.2.2.1.38.10.4.1.3
		shePotsLineTestAutoMeasureTestListGkTestList OBJECT-TYPE
			SYNTAX OCTET STRING (SIZE (0..31))
			MAX-ACCESS read-only
			STATUS current
			DESCRIPTION
				"GK Test list. Includes testID of ILTF items 
				and every byte stands for an ID(0~21), -1 means the end of the list.
				shePotsLineTestVptlTidOnOffHookSelfTest(7),
				shePotsLineTestDCFeedSelfTest(6),
				shePotsLineTestRingingSelfTest(8),
				shePotsLineTestTransmitionSelfTest(9),
				shePotsLineTestTransHybridLossTest(13),
				shePotsLineTestNoiseMeasurementTest(5),
				shePotsLineTestForeignDCVoltage(0),//
				shePotsLineTestForeignACVoltageTest(1),
				shePotsLineTestDcLoopResistanceTest(2),
				shePotsLineTest3ElementInsulationResistanceTest(3),
				shePotsLineTest3ElementInsulationCapacitanceTest(12),
				shePotsLineTestReceiverOffHookTest(4),
				shePotsLineTestDistanceToOpenTest(14),
				shePotsLineTestRingerEquivalencyNumberTest(11),
				shePotsLineTestDTMFandPulseDigitMeasurementTest(15),
				shePotsLineTestToneGenerationTest(16),
				shePotsLineTestReadLoopandBatteryConditionsTest(10),
				shePotsLineTestMeteringSelfTest(17),
				shePotsLineTestForeignACcurrentsTest(18),
				shePotsLineTestHowlerTest(19),
				shePotsLineTestReversalTest(21)
				
				In AutoMeasure test following test items should be excluded
				tonegen, howler, reverse, dtmf"
			::= { shePotsLineTestAutoMeasureTestListGroup 3 }

		
-- 1.3.6.1.4.1.231.7.1.2.2.1.38.10.4.1.4
		shePotsLineTestAutoMeasureAlarmTimeRange OBJECT-TYPE
			SYNTAX INTEGER (600..36400)
			UNITS "sec"
			MAX-ACCESS read-only
			STATUS current
			DESCRIPTION
				"The parameter is used to control ILTF automatic test
				when an vcp alarm is received. During the configured 
				time only the first alarm invokes automatic test.
				Range:
				From 10*60s to 24*60*60s.
				Default value: 30*60s"
			::= { shePotsLineTestAutoMeasureTestListGroup 4 }

		
--         1.3.6.1.4.1.231.7.1.2.2.1.38.10.4.2
		shePotsLineTestAutoMeasureTestListControl OBJECT IDENTIFIER ::= { shePotsLineTestAutoMeasureGroup 2 }

		
--         1.3.6.1.4.1.231.7.1.2.2.1.38.10.4.2.1
		shePotsLineTestAutoMeasureTestListControlRequest OBJECT-TYPE
			SYNTAX ShePotsLineTestControlRequestType
			MAX-ACCESS read-write
			STATUS current
			DESCRIPTION
				"setAutoMeasureTestList
				shePotsLineTestAutoMeasureTestListControlAcTestList
				shePotsLineTestAutoMeasureTestListControlDcTestList
				shePotsLineTestAutoMeasureTestListControlGkTestList
				shePotsLineTestAutoMeasureControlAlarmTimeRange
				
				A request of user commands.
				When AutoMeasure is ongoing, changing testlist will be forbidden with ReqResponse--autoMeasureOngoing"
			::= { shePotsLineTestAutoMeasureTestListControl 1 }

		
--         1.3.6.1.4.1.231.7.1.2.2.1.38.10.4.2.2
		shePotsLineTestAutoMeasureTestListControlStatus OBJECT-TYPE
			SYNTAX SheControlStatusType
			MAX-ACCESS read-only
			STATUS current
			DESCRIPTION
				"The status of a user command."
			::= { shePotsLineTestAutoMeasureTestListControl 2 }

		
--         1.3.6.1.4.1.231.7.1.2.2.1.38.10.4.2.3
		shePotsLineTestAutoMeasureTestListControlTimer OBJECT-TYPE
			SYNTAX Gauge32
			MAX-ACCESS read-only
			STATUS current
			DESCRIPTION
				"The maximum wait time for the manager for a long running user command."
			::= { shePotsLineTestAutoMeasureTestListControl 3 }

		
--         1.3.6.1.4.1.231.7.1.2.2.1.38.10.4.2.4
		shePotsLineTestAutoMeasureTestListControlTimeStamp OBJECT-TYPE
			SYNTAX Unsigned32
			MAX-ACCESS read-only
			STATUS current
			DESCRIPTION
				"The time stamp of the last command (end of command)."
			::= { shePotsLineTestAutoMeasureTestListControl 4 }

		
--         1.3.6.1.4.1.231.7.1.2.2.1.38.10.4.2.5
		shePotsLineTestAutoMeasureTestListControlReqResult OBJECT-TYPE
			SYNTAX ShePotsLineTestControlRequestResultType
			MAX-ACCESS read-only
			STATUS current
			DESCRIPTION
				"The result of the last user command."
			::= { shePotsLineTestAutoMeasureTestListControl 5 }

		
--         1.3.6.1.4.1.231.7.1.2.2.1.38.10.4.2.6
		shePotsLineTestAutoMeasureTestListControlAcTestList OBJECT-TYPE
			SYNTAX OCTET STRING (SIZE (0..31))
			MAX-ACCESS read-write
			STATUS current
			DESCRIPTION
				"AC Test list. Includes testID of ILTF items 
				and every byte stands for an ID(0~21), -1 means the end of the list.
				shePotsLineTestVptlTidOnOffHookSelfTest(7),
				shePotsLineTestDCFeedSelfTest(6),
				shePotsLineTestRingingSelfTest(8),
				shePotsLineTestTransmitionSelfTest(9),
				shePotsLineTestTransHybridLossTest(13),
				shePotsLineTestNoiseMeasurementTest(5),
				shePotsLineTestForeignDCVoltage(0),
				shePotsLineTestForeignACVoltageTest(1),
				shePotsLineTestDcLoopResistanceTest(2),
				shePotsLineTest3ElementInsulationResistanceTest(3),
				shePotsLineTest3ElementInsulationCapacitanceTest(12),
				shePotsLineTestReceiverOffHookTest(4),
				shePotsLineTestDistanceToOpenTest(14),
				shePotsLineTestRingerEquivalencyNumberTest(11),
				shePotsLineTestDTMFandPulseDigitMeasurementTest(15),
				shePotsLineTestToneGenerationTest(16),
				shePotsLineTestReadLoopandBatteryConditionsTest(10),
				shePotsLineTestMeteringSelfTest(17),
				shePotsLineTestForeignACcurrentsTest(18),
				shePotsLineTestHowlerTest(19),
				shePotsLineTestReversalTest(21)
				
				In AutoMeasure test following test items should be excluded
				tonegen, howler, reverse, dtmf
				
				The default value is shePotsLineTestForeignACVoltageTest(1)"
			DEFVAL { "shePotsLineTestForeignACVoltageTest(1)" }
			::= { shePotsLineTestAutoMeasureTestListControl 6 }

		
--         1.3.6.1.4.1.231.7.1.2.2.1.38.10.4.2.7
		shePotsLineTestAutoMeasureTestListControlDcTestList OBJECT-TYPE
			SYNTAX OCTET STRING (SIZE (0..31))
			MAX-ACCESS read-write
			STATUS current
			DESCRIPTION
				"DC Test list. Includes testID of ILTF items 
				and every byte stands for an ID(0~21), -1 means the end of the list.
				shePotsLineTestVptlTidOnOffHookSelfTest(7),
				shePotsLineTestDCFeedSelfTest(6),
				shePotsLineTestRingingSelfTest(8),
				shePotsLineTestTransmitionSelfTest(9),
				shePotsLineTestTransHybridLossTest(13),
				shePotsLineTestNoiseMeasurementTest(5),
				shePotsLineTestForeignDCVoltage(0),
				shePotsLineTestForeignACVoltageTest(1),
				shePotsLineTestDcLoopResistanceTest(2),
				shePotsLineTest3ElementInsulationResistanceTest(3),
				shePotsLineTest3ElementInsulationCapacitanceTest(12),
				shePotsLineTestReceiverOffHookTest(4),
				shePotsLineTestDistanceToOpenTest(14),
				shePotsLineTestRingerEquivalencyNumberTest(11),
				shePotsLineTestDTMFandPulseDigitMeasurementTest(15),
				shePotsLineTestToneGenerationTest(16),
				shePotsLineTestReadLoopandBatteryConditionsTest(10),
				shePotsLineTestMeteringSelfTest(17),
				shePotsLineTestForeignACcurrentsTest(18),
				shePotsLineTestHowlerTest(19),
				shePotsLineTestReversalTest(21)
				
				In AutoMeasure test following test items should be excluded
				tonegen, howler, reverse, dtmf
				
				shePotsLineTestForeignDCVoltageTest(0),"
			DEFVAL { "shePotsLineTestForeignDCVoltageTest(0)" }
			::= { shePotsLineTestAutoMeasureTestListControl 7 }

		
--         1.3.6.1.4.1.231.7.1.2.2.1.38.10.4.2.8
		shePotsLineTestAutoMeasureTestListControlGkTestList OBJECT-TYPE
			SYNTAX OCTET STRING (SIZE (0..31))
			MAX-ACCESS read-write
			STATUS current
			DESCRIPTION
				"GK Test list. Includes testID of ILTF items 
				and every byte stands for an ID(0~21), -1 means the end of the list.
				shePotsLineTestVptlTidOnOffHookSelfTest(7),
				shePotsLineTestDCFeedSelfTest(6),
				shePotsLineTestRingingSelfTest(8),
				shePotsLineTestTransmitionSelfTest(9),
				shePotsLineTestTransHybridLossTest(13),
				shePotsLineTestNoiseMeasurementTest(5),
				shePotsLineTestForeignDCVoltage(0),
				shePotsLineTestForeignACVoltageTest(1),
				shePotsLineTestDcLoopResistanceTest(2),
				shePotsLineTest3ElementInsulationResistanceTest(3),
				shePotsLineTest3ElementInsulationCapacitanceTest(12),
				shePotsLineTestReceiverOffHookTest(4),
				shePotsLineTestDistanceToOpenTest(14),
				shePotsLineTestRingerEquivalencyNumberTest(11),
				shePotsLineTestDTMFandPulseDigitMeasurementTest(15),
				shePotsLineTestToneGenerationTest(16),
				shePotsLineTestReadLoopandBatteryConditionsTest(10),
				shePotsLineTestMeteringSelfTest(17),
				shePotsLineTestForeignACcurrentsTest(18),
				shePotsLineTestHowlerTest(19),
				shePotsLineTestReversalTest(21)
				
				In AutoMeasure test following test items should be excluded
				tonegen, howler, reverse, dtmf
				
				The defualt value is shePotsLineTest3ElementInsulationResistanceTest(3)"
			DEFVAL { "shePotsLineTest3ElementInsulationResistanceTest(3)" }
			::= { shePotsLineTestAutoMeasureTestListControl 8 }

		
--         1.3.6.1.4.1.231.7.1.2.2.1.38.10.4.2.8
		shePotsLineTestAutoMeasureControlAlarmTimeRange OBJECT-TYPE
			SYNTAX INTEGER (600..86400)
			UNITS "sec"
			MAX-ACCESS read-write
			STATUS current
			DESCRIPTION
				"The parameter is used to control ILTF automatic test 
				when an vcp alarm is received. During the configured 
				time only the first alarm invokes automatic test.
				Range:
				From 10*60s to 24*60*60s.
				Default value: 30*60s"
			DEFVAL { 1800 }
			::= { shePotsLineTestAutoMeasureTestListControl 9 }

		
--         1.3.6.1.4.1.231.7.1.2.2.1.38.10.4.3
		shePotsLineTestAutoMeasureTable OBJECT-TYPE
			SYNTAX SEQUENCE OF ShePotsLineTestAutoMeasureEntry
			MAX-ACCESS not-accessible
			STATUS current
			DESCRIPTION
				"Auto Measurement Table"
			::= { shePotsLineTestAutoMeasureGroup 3 }

		
--         1.3.6.1.4.1.231.7.1.2.2.1.38.10.4.3.1
		shePotsLineTestAutoMeasureEntry OBJECT-TYPE
			SYNTAX ShePotsLineTestAutoMeasureEntry
			MAX-ACCESS not-accessible
			STATUS current
			DESCRIPTION
				"Entry of shePotsLineTestAutoMeasureTable,
				Each entry is used to represent a card which execute the test."
			INDEX { entPhysicalIndex }
			::= { shePotsLineTestAutoMeasureTable 1 }

		
		ShePotsLineTestAutoMeasureEntry ::=
			SEQUENCE { 
				shePotsLineTestAutoMeasureSwitch
					ShePotsLineTestSwitchType
			 }

--         1.3.6.1.4.1.231.7.1.2.2.1.38.10.4.3.1.1
		shePotsLineTestAutoMeasureSwitch OBJECT-TYPE
			SYNTAX ShePotsLineTestSwitchType
			MAX-ACCESS read-only
			STATUS current
			DESCRIPTION
				"Current status of AutoTest, can be set to either Enable or Disable: (1) Enable  (0) Disable"
			DEFVAL { 1 }
			::= { shePotsLineTestAutoMeasureEntry 1 }

		
--         1.3.6.1.4.1.231.7.1.2.2.1.38.10.4.4
		shePotsLineTestAutoMeasureControl OBJECT IDENTIFIER ::= { shePotsLineTestAutoMeasureGroup 4 }

		
--         1.3.6.1.4.1.231.7.1.2.2.1.38.10.4.4.1
		shePotsLineTestAutoMeasureControlRequest OBJECT-TYPE
			SYNTAX ShePotsLineTestControlRequestType
			MAX-ACCESS read-write
			STATUS current
			DESCRIPTION
				"setAutoMeasureSwitch:
				shePotsLineTestAutoMeasureSwitch
				shePotsLineTestAutoMeasureControlIndex
				
				A request of user commands."
			::= { shePotsLineTestAutoMeasureControl 1 }

		
--         1.3.6.1.4.1.231.7.1.2.2.1.38.10.4.4.2
		shePotsLineTestAutoMeasureControlIndex OBJECT-TYPE
			SYNTAX PhysicalIndex
			MAX-ACCESS read-write
			STATUS current
			DESCRIPTION
				"The entPhysicalIndex of the card which test shall be executed."
			::= { shePotsLineTestAutoMeasureControl 2 }

		
--         1.3.6.1.4.1.231.7.1.2.2.1.38.10.4.4.3
		shePotsLineTestAutoMeasureControlStatus OBJECT-TYPE
			SYNTAX SheControlStatusType
			MAX-ACCESS read-only
			STATUS current
			DESCRIPTION
				"The status of a user command."
			::= { shePotsLineTestAutoMeasureControl 3 }

		
--         1.3.6.1.4.1.231.7.1.2.2.1.38.10.4.4.4
		shePotsLineTestAutoMeasureControlTimer OBJECT-TYPE
			SYNTAX Gauge32
			MAX-ACCESS read-only
			STATUS current
			DESCRIPTION
				"The maximum wait time for the manager for a long running user command."
			::= { shePotsLineTestAutoMeasureControl 4 }

		
--         1.3.6.1.4.1.231.7.1.2.2.1.38.10.4.4.5
		shePotsLineTestAutoMeasureControlTimeStamp OBJECT-TYPE
			SYNTAX Unsigned32
			MAX-ACCESS read-only
			STATUS current
			DESCRIPTION
				"The time stamp of the last command (end of command)."
			::= { shePotsLineTestAutoMeasureControl 5 }

		
--         1.3.6.1.4.1.231.7.1.2.2.1.38.10.4.4.6
		shePotsLineTestAutoMeasureControlReqResult OBJECT-TYPE
			SYNTAX ShePotsLineTestControlRequestResultType
			MAX-ACCESS read-only
			STATUS current
			DESCRIPTION
				"The result of the last user command."
			::= { shePotsLineTestAutoMeasureControl 6 }

		
--         1.3.6.1.4.1.231.7.1.2.2.1.38.10.4.4.7
		shePotsLineTestAutoMeasureControlSwitch OBJECT-TYPE
			SYNTAX ShePotsLineTestSwitchType
			MAX-ACCESS read-write
			STATUS current
			DESCRIPTION
				"Set AutoTest, can be set to either Enable or Disable: (1) Enable  (0) Disable"
			::= { shePotsLineTestAutoMeasureControl 7 }

		
--         1.3.6.1.4.1.231.7.1.2.2.1.38.10.5
		shePotsLineTestPatGroup OBJECT IDENTIFIER ::= { shePotsLineTest 5 }

		
--         1.3.6.1.4.1.231.7.1.2.2.1.38.10.5.1
		shePotsLineTestPatThreshold OBJECT IDENTIFIER ::= { shePotsLineTestPatGroup 1 }

		
--         1.3.6.1.4.1.231.7.1.2.2.1.38.10.5.1.1
		shePotsLineTestPatThresholdNoiseThreshold OBJECT-TYPE
			SYNTAX INTEGER (-40..0)
			UNITS "dBm0"
			MAX-ACCESS read-only
			STATUS current
			DESCRIPTION
				"Threshold of Noise PAT test"
			::= { shePotsLineTestPatThreshold 1 }

		
--         1.3.6.1.4.1.231.7.1.2.2.1.38.10.5.1.2
		shePotsLineTestPatThreshold3EleResistancertgThreshold OBJECT-TYPE
			SYNTAX INTEGER (10..200)
			UNITS "Ohms"
			MAX-ACCESS read-only
			STATUS current
			DESCRIPTION
				"Threshold of 3EleResistancertg PAT test"
			::= { shePotsLineTestPatThreshold 2 }

		
--         1.3.6.1.4.1.231.7.1.2.2.1.38.10.5.1.3
		shePotsLineTestPatThreshold3EleResistancettgThreshold OBJECT-TYPE
			SYNTAX INTEGER (10..200)
			UNITS "Ohms"
			MAX-ACCESS read-only
			STATUS current
			DESCRIPTION
				"Threshold of 3EleResistancettg PAT test"
			::= { shePotsLineTestPatThreshold 3 }

		
--         1.3.6.1.4.1.231.7.1.2.2.1.38.10.5.1.4
		shePotsLineTestPatThreshold3EleResistancertrThreshold OBJECT-TYPE
			SYNTAX INTEGER (10..200)
			UNITS "Ohms"
			MAX-ACCESS read-only
			STATUS current
			DESCRIPTION
				"Threshold of 3EleResistancertr PAT test"
			::= { shePotsLineTestPatThreshold 4 }

		
--         1.3.6.1.4.1.231.7.1.2.2.1.38.10.5.1.5
		shePotsLineTestPatThreshold3EleCapacitancectgThreshold OBJECT-TYPE
			SYNTAX INTEGER (100..20000)
			UNITS "nF"
			MAX-ACCESS read-only
			STATUS current
			DESCRIPTION
				"Threshold of Capacitance ctg PAT test"
			::= { shePotsLineTestPatThreshold 5 }

		
--         1.3.6.1.4.1.231.7.1.2.2.1.38.10.5.1.6
		shePotsLineTestPatThreshold3EleCapacitancecrgThreshold OBJECT-TYPE
			SYNTAX INTEGER (100..20000)
			UNITS "nF"
			MAX-ACCESS read-only
			STATUS current
			DESCRIPTION
				"Threshold of Capacitance crg PAT test"
			::= { shePotsLineTestPatThreshold 6 }

		
--         1.3.6.1.4.1.231.7.1.2.2.1.38.10.5.1.7
		shePotsLineTestPatThreshold3EleCapacitancectrThreshold OBJECT-TYPE
			SYNTAX INTEGER (100..20000)
			UNITS "nF"
			MAX-ACCESS read-only
			STATUS current
			DESCRIPTION
				"Threshold of Capacitance ctr PAT test"
			::= { shePotsLineTestPatThreshold 7 }

		
--         1.3.6.1.4.1.231.7.1.2.2.1.38.10.5.1.8
		shePotsLineTestPatThresholdDcFeedimtHighBatNormalFeedThreshold OBJECT-TYPE
			SYNTAX INTEGER (1..15)
			UNITS "mA"
			MAX-ACCESS read-only
			STATUS current
			DESCRIPTION
				"Threshold of DcFeedimtHighBatNormalFeed PAT test"
			::= { shePotsLineTestPatThreshold 8 }

		
--         1.3.6.1.4.1.231.7.1.2.2.1.38.10.5.1.9
		shePotsLineTestPatThresholdDcFeedimtHighBatReverseFeedThreshold OBJECT-TYPE
			SYNTAX INTEGER (1..15)
			UNITS "mA"
			MAX-ACCESS read-only
			STATUS current
			DESCRIPTION
				"Threshold of DcFeedimtHighBatReverseFeed PAT test"
			::= { shePotsLineTestPatThreshold 9 }

		
--         1.3.6.1.4.1.231.7.1.2.2.1.38.10.5.1.10
		shePotsLineTestPatThresholdDcFeedimtLowBatNormalFeedThreshold OBJECT-TYPE
			SYNTAX INTEGER (1..15)
			UNITS "mA"
			MAX-ACCESS read-only
			STATUS current
			DESCRIPTION
				"Threshold of DcFeedimtLowBatNormalFeed PAT test"
			::= { shePotsLineTestPatThreshold 10 }

		
--        1.3.6.1.4.1.231.7.1.2.2.1.38.10.5.1.11
		shePotsLineTestPatStartTime OBJECT-TYPE
			SYNTAX DateAndTime
			MAX-ACCESS read-only
			STATUS current
			DESCRIPTION
				"Start time of PAT for entire system.
				
				Date and time should be desplayed as: 
					2d-1d-1d,1d:1d:1d.1d,1a1d:1d
					field  octets  contents                  range
					-----  ------  --------                  -----
					1      1-2   year                      0..65536
					2       3    month                     1..12
					3       4    day                       1..31
					4       5    hour                      0..23
					5       6    minutes                   0..59
					6       7    seconds                   0..60
					           (use 60 for leap-second)
					7       8    deci-seconds              0..9
					8       9    direction from UTC        '+' / '-'
					9      10    hours from UTC            0..11
					10      11    minutes from UTC          0..59
					
					For example, Tuesday May 26, 1992 at 1:30:15 PM EDT would be
					displayed as:
					
					            1992-5-26,13:30:15.0,-4:0
					
					Note that if only local time is known, then timezone
					information (fields 8-10) is not present. "
			::= { shePotsLineTestPatThreshold 11 }

		
--         1.3.6.1.4.1.231.7.1.2.2.1.38.10.5.2
		shePotsLineTestPatThresholdControl OBJECT IDENTIFIER ::= { shePotsLineTestPatGroup 2 }

		
--         1.3.6.1.4.1.231.7.1.2.2.1.38.10.5.2.1
		shePotsLineTestPatThControlRequest OBJECT-TYPE
			SYNTAX ShePotsLineTestControlRequestType
			MAX-ACCESS read-write
			STATUS current
			DESCRIPTION
				"User command:
				setPatThreshold:
				
				must:
				     shePotsLineTestPatControlStartTime
				optional:
				shePotsLineTestPatThresholdControlNoiseThreshold
				shePotsLineTestPat3EleResistancertgThreshold
				shePotsLineTestPat3EleResistancettgThreshold
				shePotsLineTestPat3EleResistancertrThreshold
				shePotsLineTestPatControl3EleCapacitancectgThreshold
				shePotsLineTestPatControl3EleCapacitancecrgThreshold
				shePotsLineTestPatControl3EleCapacitancectrThreshold
				shePotsLineTestPatControlDcFeedimtHighBatNormalFeedThreshold
				shePotsLineTestPatControlDcFeedimtHighBatReverseFeedThreshold
				shePotsLineTestPatControlDcFeedimtLowBatNormalFeedThreshold
				"
			::= { shePotsLineTestPatThresholdControl 1 }

		
--         1.3.6.1.4.1.231.7.1.2.2.1.38.10.5.2.2
		shePotsLineTestPatThControlStatus OBJECT-TYPE
			SYNTAX SheControlStatusType
			MAX-ACCESS read-only
			STATUS current
			DESCRIPTION
				"The status of a user command."
			::= { shePotsLineTestPatThresholdControl 2 }

		
--         1.3.6.1.4.1.231.7.1.2.2.1.38.10.5.2.3
		shePotsLineTestPatThControlTimer OBJECT-TYPE
			SYNTAX Gauge32
			MAX-ACCESS read-only
			STATUS current
			DESCRIPTION
				"The maximum wait time for the manager for a long running user command."
			::= { shePotsLineTestPatThresholdControl 3 }

		
--         1.3.6.1.4.1.231.7.1.2.2.1.38.10.5.2.4
		shePotsLineTestPatThControlTimeStamp OBJECT-TYPE
			SYNTAX Unsigned32
			MAX-ACCESS read-only
			STATUS current
			DESCRIPTION
				"The time stamp of the last command (end of command)."
			::= { shePotsLineTestPatThresholdControl 4 }

		
--         1.3.6.1.4.1.231.7.1.2.2.1.38.10.5.2.5
		shePotsLineTestPatThControlReqResult OBJECT-TYPE
			SYNTAX ShePotsLineTestControlRequestResultType
			MAX-ACCESS read-only
			STATUS current
			DESCRIPTION
				"The result of the last user command."
			::= { shePotsLineTestPatThresholdControl 5 }

		
--         1.3.6.1.4.1.231.7.1.2.2.1.38.10.5.2.6
		shePotsLineTestPatThControlNoiseThreshold OBJECT-TYPE
			SYNTAX INTEGER (-30..0)
			UNITS "dBm0"
			MAX-ACCESS read-write
			STATUS current
			DESCRIPTION
				"Threshold of Noise PAT test"
			DEFVAL { -10 }
			::= { shePotsLineTestPatThresholdControl 6 }

		
--         1.3.6.1.4.1.231.7.1.2.2.1.38.10.5.2.7
		shePotsLineTestPatThControl3EleResistancertgThreshold OBJECT-TYPE
			SYNTAX INTEGER (10..200)
			UNITS "Ohms"
			MAX-ACCESS read-write
			STATUS current
			DESCRIPTION
				"Threshold of 3EleResistancertg PAT test"
			DEFVAL { 100 }
			::= { shePotsLineTestPatThresholdControl 7 }

		
--         1.3.6.1.4.1.231.7.1.2.2.1.38.10.5.2.8
		shePotsLineTestPatThControl3EleResistancettgThreshold OBJECT-TYPE
			SYNTAX INTEGER (10..200)
			UNITS "Ohms"
			MAX-ACCESS read-write
			STATUS current
			DESCRIPTION
				"Threshold of 3EleResistancettg PAT test"
			DEFVAL { 100 }
			::= { shePotsLineTestPatThresholdControl 8 }

		
--         1.3.6.1.4.1.231.7.1.2.2.1.38.10.5.2.9
		shePotsLineTestPatThControl3EleResistancertrThreshold OBJECT-TYPE
			SYNTAX INTEGER (10..200)
			UNITS "Ohms"
			MAX-ACCESS read-write
			STATUS current
			DESCRIPTION
				"Threshold of 3EleResistancertr PAT test"
			DEFVAL { 100 }
			::= { shePotsLineTestPatThresholdControl 9 }

		
--         1.3.6.1.4.1.231.7.1.2.2.1.38.10.5.2.10
		shePotsLineTestPatThControl3EleCapacitancectgThreshold OBJECT-TYPE
			SYNTAX INTEGER (100..20000)
			UNITS "nF"
			MAX-ACCESS read-write
			STATUS current
			DESCRIPTION
				"Threshold of Tip-to-Ground Capacitance for PAT test"
			DEFVAL { 500 }
			::= { shePotsLineTestPatThresholdControl 10 }

		
--         1.3.6.1.4.1.231.7.1.2.2.1.38.10.5.2.11
		shePotsLineTestPatThControl3EleCapacitancecrgThreshold OBJECT-TYPE
			SYNTAX INTEGER (100..20000)
			UNITS "nF"
			MAX-ACCESS read-write
			STATUS current
			DESCRIPTION
				"Threshold of Ring-to-Ground Capacitance for PAT test"
			DEFVAL { 500 }
			::= { shePotsLineTestPatThresholdControl 11 }

		
--         1.3.6.1.4.1.231.7.1.2.2.1.38.10.5.2.12
		shePotsLineTestPatThControl3EleCapacitancectrThreshold OBJECT-TYPE
			SYNTAX INTEGER (100..20000)
			UNITS "nF"
			MAX-ACCESS read-write
			STATUS current
			DESCRIPTION
				"Threshold of Tip-to-Ring Capacitance  ctr for PAT test"
			DEFVAL { 500 }
			::= { shePotsLineTestPatThresholdControl 12 }

		
--         1.3.6.1.4.1.231.7.1.2.2.1.38.10.5.2.13
		shePotsLineTestPatThControlDcFeedimtHighBatNormalFeedThreshold OBJECT-TYPE
			SYNTAX INTEGER (1..15)
			UNITS "mA"
			MAX-ACCESS read-write
			STATUS current
			DESCRIPTION
				"Threshold of DcFeedimtHighBatNormalFeed PAT test
				the measured tip-to-ring (metallic) current through a test load under various battery/polarity arrangements"
			DEFVAL { 10 }
			::= { shePotsLineTestPatThresholdControl 13 }

		
--         1.3.6.1.4.1.231.7.1.2.2.1.38.10.5.2.14
		shePotsLineTestPatThControlDcFeedimtHighBatReverseFeedThreshold OBJECT-TYPE
			SYNTAX INTEGER (1..15)
			UNITS "mA"
			MAX-ACCESS read-write
			STATUS current
			DESCRIPTION
				"Threshold of DcFeedimtHighBatReverseFeed PAT test
				the measured tip-to-ring (metallic) current through a test load under various battery/polarity arrangements"
			DEFVAL { 10 }
			::= { shePotsLineTestPatThresholdControl 14 }

		
--         1.3.6.1.4.1.231.7.1.2.2.1.38.10.5.2.15
		shePotsLineTestPatThControlDcFeedimtLowBatNormalFeedThreshold OBJECT-TYPE
			SYNTAX INTEGER (1..15)
			UNITS "mA"
			MAX-ACCESS read-write
			STATUS current
			DESCRIPTION
				"Threshold of DcFeedimtLowBatNormalFeed PAT test
				the measured tip-to-ring (metallic) current through a test load under various battery/polarity arrangements"
			DEFVAL { 10 }
			::= { shePotsLineTestPatThresholdControl 15 }

		
--        1.3.6.1.4.1.231.7.1.2.2.1.38.10.5.2.16
		shePotsLineTestPatControlStartTime OBJECT-TYPE
			SYNTAX DateAndTime
			MAX-ACCESS read-write
			STATUS current
			DESCRIPTION
				"Start time of PAT for entire system.
				
				
				
				Date and time should be desplayed as: 
								2d-1d-1d,1d:1d:1d.1d,1a1d:1d
								field  octets  contents                  range
								-----  ------  --------                  -----
								1      1-2   year                      0..65536
								2       3    month                     1..12
								3       4    day                       1..31
								4       5    hour                      0..23
								5       6    minutes                   0..59
								6       7    seconds                   0..60
								           (use 60 for leap-second)
								7       8    deci-seconds              0..9
								8       9    direction from UTC        '+' / '-'
								9      10    hours from UTC            0..11
								10      11    minutes from UTC          0..59
								
								For example, Tuesday May 26, 1992 at 1:30:15 PM EDT would be
								displayed as:
								
								            1992-5-26,13:30:15.0,-4:0
								
								Note that if only local time is known, then timezone
								information (fields 8-10) is not present. "
			::= { shePotsLineTestPatThresholdControl 16 }

		
--         1.3.6.1.4.1.231.7.1.2.2.1.38.10.5.3
		shePotsLineTestPatTable OBJECT-TYPE
			SYNTAX SEQUENCE OF ShePotsLineTestPatEntry
			MAX-ACCESS not-accessible
			STATUS current
			DESCRIPTION
				"This is the table control the PAT test"
			::= { shePotsLineTestPatGroup 3 }

		
--         1.3.6.1.4.1.231.7.1.2.2.1.38.10.5.3.1
		shePotsLineTestPatEntry OBJECT-TYPE
			SYNTAX ShePotsLineTestPatEntry
			MAX-ACCESS not-accessible
			STATUS current
			DESCRIPTION
				"Entry of shePotsLineTestPatTable,
				Each entry is used to represent a card which executess the test."
			INDEX { entPhysicalIndex }
			::= { shePotsLineTestPatTable 1 }

		
		ShePotsLineTestPatEntry ::=
			SEQUENCE { 
				shePotsLineTestPatSwitch
					ShePotsLineTestSwitchType,
				shePotsLineTestPatPollingTime
					INTEGER
			 }

--         1.3.6.1.4.1.231.7.1.2.2.1.38.10.5.3.1.1
		shePotsLineTestPatSwitch OBJECT-TYPE
			SYNTAX ShePotsLineTestSwitchType
			MAX-ACCESS read-only
			STATUS current
			DESCRIPTION
				"Switch for PAT test. Can be set to either Enable or Disable: 
				(1) Enable  (0) Disable"
			DEFVAL { disable }
			::= { shePotsLineTestPatEntry 1 }

		
--         1.3.6.1.4.1.231.7.1.2.2.1.38.10.5.3.1.2
		shePotsLineTestPatPollingTime OBJECT-TYPE
			SYNTAX INTEGER (1..24)
			UNITS "hour"
			MAX-ACCESS read-only
			STATUS current
			DESCRIPTION
				"Pollingtime for PAT test."
			DEFVAL { 24 }
			::= { shePotsLineTestPatEntry 2 }

		
--         1.3.6.1.4.1.231.7.1.2.2.1.38.10.5.4
		shePotsLineTestPatControl OBJECT IDENTIFIER ::= { shePotsLineTestPatGroup 4 }

		
--         1.3.6.1.4.1.231.7.1.2.2.1.38.10.5.4.1
		shePotsLineTestPatControlRequest OBJECT-TYPE
			SYNTAX ShePotsLineTestControlRequestType
			MAX-ACCESS read-write
			STATUS current
			DESCRIPTION
				"User command.
				setPatSwitch:
				shePotsLineTestPatControlIndex
				shePotsLineTestPatControlSwitch
				shePotsLineTestPatControlPollingTime"
			::= { shePotsLineTestPatControl 1 }

		
--         shePotsLineTestPatControlIndex
		shePotsLineTestPatControlIndex OBJECT-TYPE
			SYNTAX PhysicalIndex
			MAX-ACCESS read-write
			STATUS current
			DESCRIPTION
				"Slot index for PAT test(entPhysicalIndex)
				This is needed for setting in Entry"
			::= { shePotsLineTestPatControl 2 }

		
--         1.3.6.1.4.1.231.7.1.2.2.1.38.10.5.4.3
		shePotsLineTestPatControlStatus OBJECT-TYPE
			SYNTAX SheControlStatusType
			MAX-ACCESS read-only
			STATUS current
			DESCRIPTION
				"The status of a user command."
			::= { shePotsLineTestPatControl 3 }

		
--         1.3.6.1.4.1.231.7.1.2.2.1.38.10.5.4.4
		shePotsLineTestPatControlTimer OBJECT-TYPE
			SYNTAX Gauge32
			MAX-ACCESS read-only
			STATUS current
			DESCRIPTION
				"The maximum wait time for the manager for a long running user command."
			::= { shePotsLineTestPatControl 4 }

		
--         1.3.6.1.4.1.231.7.1.2.2.1.38.10.5.4.5
		shePotsLineTestPatControlTimeStamp OBJECT-TYPE
			SYNTAX Unsigned32
			MAX-ACCESS read-only
			STATUS current
			DESCRIPTION
				"The time stamp of the last command (end of command)."
			::= { shePotsLineTestPatControl 5 }

		
--         1.3.6.1.4.1.231.7.1.2.2.1.38.10.5.4.6
		shePotsLineTestPatControlReqResult OBJECT-TYPE
			SYNTAX ShePotsLineTestControlRequestResultType
			MAX-ACCESS read-only
			STATUS current
			DESCRIPTION
				"The result of the last user command."
			::= { shePotsLineTestPatControl 6 }

		
--         1.3.6.1.4.1.231.7.1.2.2.1.38.10.5.4.7
		shePotsLineTestPatControlSwitch OBJECT-TYPE
			SYNTAX ShePotsLineTestSwitchType
			MAX-ACCESS read-write
			STATUS current
			DESCRIPTION
				"Switch for PAT test.
				, can be set to either Enable or Disable:
				 (1) Enable  (0) Disable"
			DEFVAL { disable }
			::= { shePotsLineTestPatControl 7 }

		
--         1.3.6.1.4.1.231.7.1.2.2.1.38.10.5.4.8
		shePotsLineTestPatControlPollingTime OBJECT-TYPE
			SYNTAX INTEGER (1..24)
			UNITS "hour"
			MAX-ACCESS read-write
			STATUS current
			DESCRIPTION
				"Pollingtime for PAT test."
			DEFVAL { 24 }
			::= { shePotsLineTestPatControl 8 }

		
--         1.3.6.1.4.1.231.7.1.2.2.1.38.10.6
		shePotsLineTestDeployTestGroup OBJECT IDENTIFIER ::= { shePotsLineTest 6 }

		
--         1.3.6.1.4.1.231.7.1.2.2.1.38.10.6.1
		shePotsLineTestDeployTestListGroup OBJECT IDENTIFIER ::= { shePotsLineTestDeployTestGroup 1 }

		
--         1.3.6.1.4.1.231.7.1.2.2.1.38.10.6.1.1
		shePotsLineTestDeployTestList OBJECT-TYPE
			SYNTAX OCTET STRING (SIZE (0..31))
			MAX-ACCESS read-only
			STATUS current
			DESCRIPTION
				"Deploy Test list. Includes testID of ILTF items 
				and every byte stands for an ID(0~21), 0 means the end of the list.
				shePotsLineTestVptlTidOnOffHookSelfTest(7),
				shePotsLineTestDCFeedSelfTest(6),
				shePotsLineTestRingingSelfTest(8),
				shePotsLineTestTransmitionSelfTest(9),
				shePotsLineTestTransHybridLossTest(13),
				shePotsLineTestNoiseMeasurementTest(5),
				shePotsLineTestForeignDCVoltage(0),
				shePotsLineTestForeignACVoltageTest(1),
				shePotsLineTestDcLoopResistanceTest(2),
				shePotsLineTest3ElementInsulationResistanceTest(3),
				shePotsLineTest3ElementInsulationCapacitanceTest(12),
				shePotsLineTestReceiverOffHookTest(4),
				shePotsLineTestDistanceToOpenTest(14),
				shePotsLineTestRingerEquivalencyNumberTest(11),
				shePotsLineTestDTMFandPulseDigitMeasurementTest(15),
				shePotsLineTestToneGenerationTest(16),
				shePotsLineTestReadLoopandBatteryConditionsTest(10),
				shePotsLineTestMeteringSelfTest(17),
				shePotsLineTestForeignACcurrentsTest(18),
				shePotsLineTestHowlerTest(19),
				shePotsLineTestReversalTest(21)
				
				In deploy test following test items should be excluded
				tonegen, howler, dtmf and reversal."
			::= { shePotsLineTestDeployTestListGroup 1 }

		
--         1.3.6.1.4.1.231.7.1.2.2.1.38.10.6.2
		shePotsLineTestDeployTestListControl OBJECT IDENTIFIER ::= { shePotsLineTestDeployTestGroup 2 }

		
--         1.3.6.1.4.1.231.7.1.2.2.1.38.10.6.2.1
		shePotsLineTestDeployTestListControlRequest OBJECT-TYPE
			SYNTAX ShePotsLineTestControlRequestType
			MAX-ACCESS read-write
			STATUS current
			DESCRIPTION
				"setDeployTestList:
				shePotsLineTestDeployTestListControlDeployTestList
				
				A request of user commands."
			::= { shePotsLineTestDeployTestListControl 1 }

		
--         1.3.6.1.4.1.231.7.1.2.2.1.38.10.6.2.2
		shePotsLineTestDeployTestListControlStatus OBJECT-TYPE
			SYNTAX SheControlStatusType
			MAX-ACCESS read-only
			STATUS current
			DESCRIPTION
				"The status of a user command."
			::= { shePotsLineTestDeployTestListControl 2 }

		
--         1.3.6.1.4.1.231.7.1.2.2.1.38.10.6.2.3
		shePotsLineTestDeployTestListControlTimer OBJECT-TYPE
			SYNTAX Gauge32
			MAX-ACCESS read-only
			STATUS current
			DESCRIPTION
				"The maximum wait time for the manager for a long running user command."
			::= { shePotsLineTestDeployTestListControl 3 }

		
--         1.3.6.1.4.1.231.7.1.2.2.1.38.10.6.2.4
		shePotsLineTestDeployTestListControlTimeStamp OBJECT-TYPE
			SYNTAX Unsigned32
			MAX-ACCESS read-only
			STATUS current
			DESCRIPTION
				"The time stamp of the last command (end of command)."
			::= { shePotsLineTestDeployTestListControl 4 }

		
--         1.3.6.1.4.1.231.7.1.2.2.1.38.10.6.2.5
		shePotsLineTestDeployTestListControlReqResult OBJECT-TYPE
			SYNTAX ShePotsLineTestControlRequestResultType
			MAX-ACCESS read-only
			STATUS current
			DESCRIPTION
				"The result of the last user command."
			::= { shePotsLineTestDeployTestListControl 5 }

		
-- 1.3.6.1.4.1.231.7.1.2.2.1.38.10.6.2.6
		shePotsLineTestDeployTestListControlDeployTestList OBJECT-TYPE
			SYNTAX OCTET STRING (SIZE (0..31))
			MAX-ACCESS read-write
			STATUS current
			DESCRIPTION
				"Deploy Test list. Includes testID of ILTF items 
				and every byte stands for an ID(0~21), 0 means the end of the list.
				shePotsLineTestVptlTidOnOffHookSelfTest(7),
				shePotsLineTestDCFeedSelfTest(6),
				shePotsLineTestRingingSelfTest(8),
				shePotsLineTestTransmitionSelfTest(9),
				shePotsLineTestTransHybridLossTest(13),
				shePotsLineTestNoiseMeasurementTest(5),
				shePotsLineTestForeignDCVoltage(0),
				shePotsLineTestForeignACVoltageTest(1),
				shePotsLineTestDcLoopResistanceTest(2),
				shePotsLineTest3ElementInsulationResistanceTest(3),
				shePotsLineTest3ElementInsulationCapacitanceTest(12),
				shePotsLineTestReceiverOffHookTest(4),
				shePotsLineTestDistanceToOpenTest(14),
				shePotsLineTestRingerEquivalencyNumberTest(11),
				shePotsLineTestDTMFandPulseDigitMeasurementTest(15),
				shePotsLineTestToneGenerationTest(16),
				shePotsLineTestReadLoopandBatteryConditionsTest(10),
				shePotsLineTestMeteringSelfTest(17),
				shePotsLineTestForeignACcurrentsTest(18),
				shePotsLineTestHowlerTest(19),
				shePotsLineTestReversalTest(21)
				
				In deploy test following test items should be excluded
				tonegen, howler, dtmf and reversal."
			::= { shePotsLineTestDeployTestListControl 6 }

		
--         1.3.6.1.4.1.231.7.1.2.2.1.38.10.6.3
		shePotsLineTestCalibrationTestTable OBJECT-TYPE
			SYNTAX SEQUENCE OF ShePotsLineTestCalibrationTestEntry
			MAX-ACCESS not-accessible
			STATUS current
			DESCRIPTION
				"This is the table control the calibration test"
			::= { shePotsLineTestDeployTestGroup 3 }

		
--         1.3.6.1.4.1.231.7.1.2.2.1.38.10.6.3.1
		shePotsLineTestCalibrationTestEntry OBJECT-TYPE
			SYNTAX ShePotsLineTestCalibrationTestEntry
			MAX-ACCESS not-accessible
			STATUS current
			DESCRIPTION
				"Entry of shePotsLineTestCalibrationTestTable,
				Each entry is used to represent a card which executess the test."
			INDEX { entPhysicalIndex }
			::= { shePotsLineTestCalibrationTestTable 1 }

		
		ShePotsLineTestCalibrationTestEntry ::=
			SEQUENCE { 
				shePotsLineTestCalibrationTestSwitch
					ShePotsLineTestSwitchType
			 }

--         1.3.6.1.4.1.231.7.1.2.2.1.38.10.6.3.1.1
		shePotsLineTestCalibrationTestSwitch OBJECT-TYPE
			SYNTAX ShePotsLineTestSwitchType
			MAX-ACCESS read-only
			STATUS current
			DESCRIPTION
				"Switch for Deploy and Calibration. Test Current status of Calibration, 
				can be set to either Enable or Disable:
				(1) Enable  (0) Disable"
			::= { shePotsLineTestCalibrationTestEntry 1 }

		
--         1.3.6.1.4.1.231.7.1.2.2.1.38.10.6.4
		shePotsLineTestDeployTestControl OBJECT IDENTIFIER ::= { shePotsLineTestDeployTestGroup 4 }

		
--         Very important!!!
-- 1.3.6.1.4.1.231.7.1.2.2.1.38.10.6.4.1
		shePotsLineTestDeployTestControlRequest OBJECT-TYPE
			SYNTAX ShePotsLineTestControlRequestType
			MAX-ACCESS read-write
			STATUS current
			DESCRIPTION
				" This request is uesed to start Deploy test and
				use CalibrationSwithc as a parameter.  
				
				setDeployTest
				shePotsLineTestDeployTestControlIndex
				shePotsLineTestCalibrationTestControlSwitch
				
				However, Calibration Test is not available now."
			::= { shePotsLineTestDeployTestControl 1 }

		
--         1.3.6.1.4.1.231.7.1.2.2.1.38.10.6.4.2
		shePotsLineTestDeployTestControlIndex OBJECT-TYPE
			SYNTAX PhysicalIndex
			MAX-ACCESS read-write
			STATUS current
			DESCRIPTION
				"The IfIndex of the card which test shall be executed"
			::= { shePotsLineTestDeployTestControl 2 }

		
--         1.3.6.1.4.1.231.7.1.2.2.1.38.10.6.4.3
		shePotsLineTestDeployTestControlStatus OBJECT-TYPE
			SYNTAX SheControlStatusType
			MAX-ACCESS read-only
			STATUS current
			DESCRIPTION
				"The status of a user command."
			::= { shePotsLineTestDeployTestControl 3 }

		
--         1.3.6.1.4.1.231.7.1.2.2.1.38.10.6.4.4
		shePotsLineTestDeployTestControlTimer OBJECT-TYPE
			SYNTAX Gauge32
			MAX-ACCESS read-only
			STATUS current
			DESCRIPTION
				"The maximum wait time for the manager for a long running user command."
			::= { shePotsLineTestDeployTestControl 4 }

		
--         1.3.6.1.4.1.231.7.1.2.2.1.38.10.6.4.5
		shePotsLineTestDeployTestControlTimeStamp OBJECT-TYPE
			SYNTAX Unsigned32
			MAX-ACCESS read-only
			STATUS current
			DESCRIPTION
				"The result of the last user command."
			::= { shePotsLineTestDeployTestControl 5 }

		
--         1.3.6.1.4.1.231.7.1.2.2.1.38.10.6.4.6
		shePotsLineTestDeployTestControlReqResult OBJECT-TYPE
			SYNTAX ShePotsLineTestControlRequestResultType
			MAX-ACCESS read-only
			STATUS current
			DESCRIPTION
				"The time stamp of the last command (end of command)."
			::= { shePotsLineTestDeployTestControl 6 }

		
--         1.3.6.1.4.1.231.7.1.2.2.1.38.10.6.4.7
		shePotsLineTestCalibrationTestControlSwitch OBJECT-TYPE
			SYNTAX ShePotsLineTestSwitchType
			MAX-ACCESS read-write
			STATUS current
			DESCRIPTION
				"Switch for Calibration Test
				Current status of Calibration, 
				can be set to either Enable or Disable:
				(1) Enable  (0) Disable"
			::= { shePotsLineTestDeployTestControl 7 }

		
--         1.3.6.1.4.1.231.7.1.2.2.1.38.10.7
		shePotsLineTestIltfTestGroup OBJECT IDENTIFIER ::= { shePotsLineTest 7 }

		
--         1.3.6.1.4.1.231.7.1.2.2.1.38.10.7.1
		shePotsLineTestVptlTidOnOffHookSelfTestGroup OBJECT IDENTIFIER ::= { shePotsLineTestIltfTestGroup 1 }

		
--         1.3.6.1.4.1.231.7.1.2.2.1.38.10.7.1.1
		shePotsLineTestVptlTidOnOffHookSelfTestTable OBJECT-TYPE
			SYNTAX SEQUENCE OF ShePotsLineTestVptlTidOnOffHookSelfTestEntry
			MAX-ACCESS not-accessible
			STATUS current
			DESCRIPTION
				"This procedure verifies that the line circuit can detect on-hook and off-hook events"
			::= { shePotsLineTestVptlTidOnOffHookSelfTestGroup 1 }

		
--         1.3.6.1.4.1.231.7.1.2.2.1.38.10.7.1.1.1
		shePotsLineTestVptlTidOnOffHookSelfTestEntry OBJECT-TYPE
			SYNTAX ShePotsLineTestVptlTidOnOffHookSelfTestEntry
			MAX-ACCESS not-accessible
			STATUS current
			DESCRIPTION
				"Entry of shePotsLineTestVptlTidOnOffHookSelfTestTable,
				Each entry is used to represent a line which execute the test."
			INDEX { ifIndex }
			::= { shePotsLineTestVptlTidOnOffHookSelfTestTable 1 }

		
		ShePotsLineTestVptlTidOnOffHookSelfTestEntry ::=
			SEQUENCE { 
				shePotsLineTestVptlOnOffHookSelfTestStatus
					ShePotsLineTestVptlOnOffHookSelfTestStatusType,
				shePotsLineTestVptlOnOffHookSelfTestTriggerSource
					ShePotsLineTestTriggerType
			 }

--         1.3.6.1.4.1.231.7.1.2.2.1.38.10.7.1.1.1.1
		shePotsLineTestVptlOnOffHookSelfTestStatus OBJECT-TYPE
			SYNTAX ShePotsLineTestVptlOnOffHookSelfTestStatusType
			MAX-ACCESS read-only
			STATUS current
			DESCRIPTION
				"unknown(0)    /* some unexpected error occured, debug. */
				aborted(1)    /* test aborted because line off-hook. */
				hwFault(2)   /* test failed because of hardware fault. */
				passed(3)     /* test passed. */
				"
			::= { shePotsLineTestVptlTidOnOffHookSelfTestEntry 1 }

		
--         1.3.6.1.4.1.231.7.1.2.2.1.38.10.7.1.1.1.2
		shePotsLineTestVptlOnOffHookSelfTestTriggerSource OBJECT-TYPE
			SYNTAX ShePotsLineTestTriggerType
			MAX-ACCESS read-only
			STATUS current
			DESCRIPTION
				"Trigger source of the test"
			::= { shePotsLineTestVptlTidOnOffHookSelfTestEntry 2 }

		
--         1.3.6.1.4.1.231.7.1.2.2.1.38.10.7.1.2
		shePotsLineTestVptlTidOnOffHookSelfTestControl OBJECT IDENTIFIER ::= { shePotsLineTestVptlTidOnOffHookSelfTestGroup 2 }

		
--         1.3.6.1.4.1.231.7.1.2.2.1.38.10.7.1.2.1
		shePotsLineTestVptlTidOnOffHookSelfTestControlRequest OBJECT-TYPE
			SYNTAX ShePotsLineTestControlRequestType
			MAX-ACCESS read-write
			STATUS current
			DESCRIPTION
				"setVptlTidOnOffHookSelfTest:
				shePotsLineTestVptlTidOnOffHookSelfTestControlIndex
				
				Long-running Command
				"
			::= { shePotsLineTestVptlTidOnOffHookSelfTestControl 1 }

		
--         1.3.6.1.4.1.231.7.1.2.2.1.38.10.7.1.2.2
		shePotsLineTestVptlTidOnOffHookSelfTestControlIndex OBJECT-TYPE
			SYNTAX InterfaceIndex
			MAX-ACCESS read-write
			STATUS current
			DESCRIPTION
				"The IfIndex of the card which test shall be executed."
			::= { shePotsLineTestVptlTidOnOffHookSelfTestControl 2 }

		
--         1.3.6.1.4.1.231.7.1.2.2.1.38.10.7.1.2.3
		shePotsLineTestVptlTidOnOffHookSelfTestControlStatus OBJECT-TYPE
			SYNTAX SheControlStatusType
			MAX-ACCESS read-only
			STATUS current
			DESCRIPTION
				"The status of a user command"
			::= { shePotsLineTestVptlTidOnOffHookSelfTestControl 3 }

		
--         1.3.6.1.4.1.231.7.1.2.2.1.38.10.7.1.2.4
		shePotsLineTestVptlTidOnOffHookSelfTestControlTimer OBJECT-TYPE
			SYNTAX Gauge32
			MAX-ACCESS read-only
			STATUS current
			DESCRIPTION
				"The maximum wait time for the manager for a long running user command"
			::= { shePotsLineTestVptlTidOnOffHookSelfTestControl 4 }

		
--         1.3.6.1.4.1.231.7.1.2.2.1.38.10.7.1.2.5
		shePotsLineTestVptlTidOnOffHookSelfTestControlTimeStamp OBJECT-TYPE
			SYNTAX Unsigned32
			UNITS "sec"
			MAX-ACCESS read-only
			STATUS current
			DESCRIPTION
				"The time stamp of the last command (end of command)"
			::= { shePotsLineTestVptlTidOnOffHookSelfTestControl 5 }

		
--         1.3.6.1.4.1.231.7.1.2.2.1.38.10.7.1.2.6
		shePotsLineTestVptlTidOnOffHookSelfTestControlReqResult OBJECT-TYPE
			SYNTAX ShePotsLineTestControlRequestResultType
			MAX-ACCESS read-only
			STATUS current
			DESCRIPTION
				"The result of the last user command."
			::= { shePotsLineTestVptlTidOnOffHookSelfTestControl 6 }

		
--         1.3.6.1.4.1.231.7.1.2.2.1.38.10.7.2
		shePotsLineTestDcFeedSelfTestGroup OBJECT IDENTIFIER ::= { shePotsLineTestIltfTestGroup 2 }

		
--         1.3.6.1.4.1.231.7.1.2.2.1.38.10.7.2.1
		shePotsLineTestLineTestDcFeedSelfTestTable OBJECT-TYPE
			SYNTAX SEQUENCE OF ShePotsLineTestLineTestDcFeedSelfTestEntry
			MAX-ACCESS not-accessible
			STATUS current
			DESCRIPTION
				"This procedure verifies that the SLIC can drive currents into a load and measure the voltage
				across a   load.It also verifies the proper operation of the DC feed control algorithm
				programmed into the QISLAC."
			::= { shePotsLineTestDcFeedSelfTestGroup 1 }

		
--         1.3.6.1.4.1.231.7.1.2.2.1.38.10.7.2.1.1
		shePotsLineTestLineTestDcFeedSelfTestEntry OBJECT-TYPE
			SYNTAX ShePotsLineTestLineTestDcFeedSelfTestEntry
			MAX-ACCESS not-accessible
			STATUS current
			DESCRIPTION
				"Entry of shePotsLineTestLineTestDcFeedSelfTestTable
				Each entry is used to represent a line which execute the test."
			INDEX { ifIndex }
			::= { shePotsLineTestLineTestDcFeedSelfTestTable 1 }

		
		ShePotsLineTestLineTestDcFeedSelfTestEntry ::=
			SEQUENCE { 
				shePotsLineTestDcFeedSelfTestImtHighBatNormalFeed
					INTEGER,
				shePotsLineTestDcFeedSelfTestImtHighBatReverseFeed
					INTEGER,
				shePotsLineTestDcFeedSelfTestImtLowBatNormalFeed
					INTEGER,
				shePotsLineTestDcFeedSelfTestImtBoostBatNormalFeed
					INTEGER,
				shePotsLineTestDcFeedSelfTestRloadMsrd
					INTEGER,
				shePotsLineTestDcFeedSelfTestvBat
					INTEGER,
				shePotsLineTestDcFeedSelfTestvTr
					INTEGER,
				shePotsLineTestDcFeedSelfTestPassed
					TruthValue,
				shePotsLineTestDcFeedSelfTestTriggerSource
					ShePotsLineTestTriggerType
			 }

--         1.3.6.1.4.1.231.7.1.2.2.1.38.10.7.2.1.1.1
		shePotsLineTestDcFeedSelfTestImtHighBatNormalFeed OBJECT-TYPE
			SYNTAX INTEGER
			UNITS "mA"
			MAX-ACCESS read-only
			STATUS current
			DESCRIPTION
				"High battery normal feed
				However, this output should not be shown to users."
			::= { shePotsLineTestLineTestDcFeedSelfTestEntry 1 }

		
--         1.3.6.1.4.1.231.7.1.2.2.1.38.10.7.2.1.1.2
		shePotsLineTestDcFeedSelfTestImtHighBatReverseFeed OBJECT-TYPE
			SYNTAX INTEGER
			UNITS "mA"
			MAX-ACCESS read-only
			STATUS current
			DESCRIPTION
				"High battery reverse feed
				However, this output should not be shown to users."
			::= { shePotsLineTestLineTestDcFeedSelfTestEntry 2 }

		
--         1.3.6.1.4.1.231.7.1.2.2.1.38.10.7.2.1.1.3
		shePotsLineTestDcFeedSelfTestImtLowBatNormalFeed OBJECT-TYPE
			SYNTAX INTEGER
			UNITS "mA"
			MAX-ACCESS read-only
			STATUS current
			DESCRIPTION
				"Low battery normal feed
				However, this output should not be shown to users."
			::= { shePotsLineTestLineTestDcFeedSelfTestEntry 3 }

		
--         1.3.6.1.4.1.231.7.1.2.2.1.38.10.7.2.1.1.4
		shePotsLineTestDcFeedSelfTestImtBoostBatNormalFeed OBJECT-TYPE
			SYNTAX INTEGER
			UNITS "mA"
			MAX-ACCESS read-only
			STATUS current
			DESCRIPTION
				"Boost battery normal feed
				However, this output should not be shown to users."
			::= { shePotsLineTestLineTestDcFeedSelfTestEntry 4 }

		
--         1.3.6.1.4.1.231.7.1.2.2.1.38.10.7.2.1.1.5
		shePotsLineTestDcFeedSelfTestRloadMsrd OBJECT-TYPE
			SYNTAX INTEGER
			UNITS "Ohm"
			MAX-ACCESS read-only
			STATUS current
			DESCRIPTION
				"Measured test load (in Ohms)
				However, this output should not be shown to users."
			::= { shePotsLineTestLineTestDcFeedSelfTestEntry 5 }

		
--         1.3.6.1.4.1.231.7.1.2.2.1.38.10.7.2.1.1.6
		shePotsLineTestDcFeedSelfTestvBat OBJECT-TYPE
			SYNTAX INTEGER
			UNITS "V"
			MAX-ACCESS read-only
			STATUS current
			DESCRIPTION
				"Measured high battery (in Volts)
				However, this output should not be shown to users."
			::= { shePotsLineTestLineTestDcFeedSelfTestEntry 6 }

		
--         1.3.6.1.4.1.231.7.1.2.2.1.38.10.7.2.1.1.7
		shePotsLineTestDcFeedSelfTestvTr OBJECT-TYPE
			SYNTAX INTEGER
			UNITS "V"
			MAX-ACCESS read-only
			STATUS current
			DESCRIPTION
				"Measured tip/ring Volts x100 when high current is driven
				should display as vTr/100 V"
			::= { shePotsLineTestLineTestDcFeedSelfTestEntry 7 }

		
--         1.3.6.1.4.1.231.7.1.2.2.1.38.10.7.2.1.1.8
		shePotsLineTestDcFeedSelfTestPassed OBJECT-TYPE
			SYNTAX TruthValue
			MAX-ACCESS read-only
			STATUS current
			DESCRIPTION
				"Test pass flag.
				testpassed=1 test passed
				testpassed=0 test failed
				"
			::= { shePotsLineTestLineTestDcFeedSelfTestEntry 8 }

		
--         1.3.6.1.4.1.231.7.1.2.2.1.38.10.7.2.1.1.9
		shePotsLineTestDcFeedSelfTestTriggerSource OBJECT-TYPE
			SYNTAX ShePotsLineTestTriggerType
			MAX-ACCESS read-only
			STATUS current
			DESCRIPTION
				"Trigger source of the test."
			::= { shePotsLineTestLineTestDcFeedSelfTestEntry 9 }

		
--         1.3.6.1.4.1.231.7.1.2.2.1.38.10.7.2.2
		shePotsLineTestLineTestDcFeedSelfTestControl OBJECT IDENTIFIER ::= { shePotsLineTestDcFeedSelfTestGroup 2 }

		
--         1.3.6.1.4.1.231.7.1.2.2.1.38.10.7.2.2.1
		shePotsLineTestLineTestDcFeedSelfTestControlRequest OBJECT-TYPE
			SYNTAX ShePotsLineTestControlRequestType
			MAX-ACCESS read-write
			STATUS current
			DESCRIPTION
				"UserCommand
				setDcFeedSelfTest:
				shePotsLineTestLineTestDcFeedSelfTestControlIndex
				
				Long-running Command"
			::= { shePotsLineTestLineTestDcFeedSelfTestControl 1 }

		
--         1.3.6.1.4.1.231.7.1.2.2.1.38.10.7.2.2.2
		shePotsLineTestLineTestDcFeedSelfTestControlIndex OBJECT-TYPE
			SYNTAX InterfaceIndex
			MAX-ACCESS read-write
			STATUS current
			DESCRIPTION
				"The IfIndex of the line which test shall be executed"
			::= { shePotsLineTestLineTestDcFeedSelfTestControl 2 }

		
--         1.3.6.1.4.1.231.7.1.2.2.1.38.10.7.2.2.3
		shePotsLineTestLineTestDcFeedSelfTestControlStatus OBJECT-TYPE
			SYNTAX SheControlStatusType
			MAX-ACCESS read-only
			STATUS current
			DESCRIPTION
				"The status of a user command"
			::= { shePotsLineTestLineTestDcFeedSelfTestControl 3 }

		
--         1.3.6.1.4.1.231.7.1.2.2.1.38.10.7.2.2.4
		shePotsLineTestLineTestDcFeedSelfTestControlTimer OBJECT-TYPE
			SYNTAX Gauge32
			MAX-ACCESS read-only
			STATUS current
			DESCRIPTION
				"The maximum wait time for the manager for a long running user command."
			::= { shePotsLineTestLineTestDcFeedSelfTestControl 4 }

		
--         1.3.6.1.4.1.231.7.1.2.2.1.38.10.7.2.2.5
		shePotsLineTestLineTestDcFeedSelfTestControlTimeStamp OBJECT-TYPE
			SYNTAX Unsigned32
			MAX-ACCESS read-only
			STATUS current
			DESCRIPTION
				"The time stamp of the last command (end of command)."
			::= { shePotsLineTestLineTestDcFeedSelfTestControl 5 }

		
--         1.3.6.1.4.1.231.7.1.2.2.1.38.10.7.2.2.6
		shePotsLineTestLineTestDcFeedSelfTestControlReqResult OBJECT-TYPE
			SYNTAX ShePotsLineTestControlRequestResultType
			MAX-ACCESS read-only
			STATUS current
			DESCRIPTION
				"The result of the last user command."
			::= { shePotsLineTestLineTestDcFeedSelfTestControl 6 }

		
--         1.3.6.1.4.1.231.7.1.2.2.1.38.10.7.3
		shePotsLineTestRingingSelfTestGroup OBJECT IDENTIFIER ::= { shePotsLineTestIltfTestGroup 3 }

		
--         1.3.6.1.4.1.231.7.1.2.2.1.38.10.7.3.1
		shePotsLineTestRingingSelfTestTable OBJECT-TYPE
			SYNTAX SEQUENCE OF ShePotsLineTestRingingSelfTestEntry
			MAX-ACCESS not-accessible
			STATUS current
			DESCRIPTION
				"this procedure verifies that the line circuit can generate a ringing voltage at the desired
				amplitude. It  generates a sinusoidal waveform with the requested amplitude and drives this
				and confirms that automatic ring trip is working"
			::= { shePotsLineTestRingingSelfTestGroup 1 }

		
--         1.3.6.1.4.1.231.7.1.2.2.1.38.10.7.3.1.1
		shePotsLineTestRingingSelfTestEntry OBJECT-TYPE
			SYNTAX ShePotsLineTestRingingSelfTestEntry
			MAX-ACCESS not-accessible
			STATUS current
			DESCRIPTION
				"Entry of shePotsLineTestRingingSelfTestTable,
				Each entry is used to represent a line which execute the test."
			INDEX { ifIndex }
			::= { shePotsLineTestRingingSelfTestTable 1 }

		
		ShePotsLineTestRingingSelfTestEntry ::=
			SEQUENCE { 
				shePotsLineTestRingingSelfTestOnOffHookChangeDetected
					TruthValue,
				shePotsLineTestRingingSelfTestTestPassed
					TruthValue,
				shePotsLineTestRingingSelfTestTriggerSource
					ShePotsLineTestTriggerType
			 }

--         1.3.6.1.4.1.231.7.1.2.2.1.38.10.7.3.1.1.2
		shePotsLineTestRingingSelfTestOnOffHookChangeDetected OBJECT-TYPE
			SYNTAX TruthValue
			MAX-ACCESS read-only
			STATUS current
			DESCRIPTION
				"Test detected ON hook to OFF hook state transition.
				1: the ring trip occured;
				0: the ring trip failed.    
				
				"
			::= { shePotsLineTestRingingSelfTestEntry 1 }

		
--         1.3.6.1.4.1.231.7.1.2.2.1.38.10.7.3.1.1.3
		shePotsLineTestRingingSelfTestTestPassed OBJECT-TYPE
			SYNTAX TruthValue
			MAX-ACCESS read-only
			STATUS current
			DESCRIPTION
				"If set to TRUE indicates test passed
				1: the test passed;
				0: the test failed.    "
			::= { shePotsLineTestRingingSelfTestEntry 2 }

		
--         1.3.6.1.4.1.231.7.1.2.2.1.38.10.7.3.1.1.4
		shePotsLineTestRingingSelfTestTriggerSource OBJECT-TYPE
			SYNTAX ShePotsLineTestTriggerType
			MAX-ACCESS read-only
			STATUS current
			DESCRIPTION
				"Test Trigger Source."
			::= { shePotsLineTestRingingSelfTestEntry 3 }

		
--         1.3.6.1.4.1.231.7.1.2.2.1.38.10.7.3.2
		shePotsLineTestRingingSelfTestControl OBJECT IDENTIFIER ::= { shePotsLineTestRingingSelfTestGroup 2 }

		
--         1.3.6.1.4.1.231.7.1.2.2.1.38.10.7.3.2.1
		shePotsLineTestRingingSelfTestControlRequest OBJECT-TYPE
			SYNTAX ShePotsLineTestControlRequestType
			MAX-ACCESS read-write
			STATUS current
			DESCRIPTION
				"User command.
				setRingingSelfTest:
				shePotsLineTestRingingSelfTestControlIndex
				
				
				Long-running Command"
			::= { shePotsLineTestRingingSelfTestControl 1 }

		
--         1.3.6.1.4.1.231.7.1.2.2.1.38.10.7.3.2.2
		shePotsLineTestRingingSelfTestControlIndex OBJECT-TYPE
			SYNTAX InterfaceIndex
			MAX-ACCESS read-write
			STATUS current
			DESCRIPTION
				"The IfIndex of the line which test shall be executed"
			::= { shePotsLineTestRingingSelfTestControl 2 }

		
--         1.3.6.1.4.1.231.7.1.2.2.1.38.10.7.3.2.3
		shePotsLineTestRingingSelfTestControlStatus OBJECT-TYPE
			SYNTAX SheControlStatusType
			MAX-ACCESS read-only
			STATUS current
			DESCRIPTION
				"The status of a user command"
			::= { shePotsLineTestRingingSelfTestControl 3 }

		
--         1.3.6.1.4.1.231.7.1.2.2.1.38.10.7.3.2.4
		shePotsLineTestRingingSelfTestControlTimer OBJECT-TYPE
			SYNTAX Gauge32
			MAX-ACCESS read-only
			STATUS current
			DESCRIPTION
				"The maximum wait time for the manager for a long running user command."
			::= { shePotsLineTestRingingSelfTestControl 4 }

		
--         1.3.6.1.4.1.231.7.1.2.2.1.38.10.7.3.2.5
		shePotsLineTestRingingSelfTestControlTimeStamp OBJECT-TYPE
			SYNTAX Unsigned32
			MAX-ACCESS read-only
			STATUS current
			DESCRIPTION
				"The time stamp of the last command (end of command)."
			::= { shePotsLineTestRingingSelfTestControl 5 }

		
--         1.3.6.1.4.1.231.7.1.2.2.1.38.10.7.3.2.6
		shePotsLineTestRingingSelfTestControlReqResult OBJECT-TYPE
			SYNTAX ShePotsLineTestControlRequestResultType
			MAX-ACCESS read-only
			STATUS current
			DESCRIPTION
				"The result of the last user command."
			::= { shePotsLineTestRingingSelfTestControl 6 }

		
--         1.3.6.1.4.1.231.7.1.2.2.1.38.10.7.4
		shePotsLineTestTransmissionSelfTestGroup OBJECT IDENTIFIER ::= { shePotsLineTestIltfTestGroup 4 }

		
--         1.3.6.1.4.1.231.7.1.2.2.1.38.10.7.4.1
		shePotsLineTestTransmissionSelfTestTable OBJECT-TYPE
			SYNTAX SEQUENCE OF ShePotsLineTestTransmissionSelfTestEntry
			MAX-ACCESS not-accessible
			STATUS current
			DESCRIPTION
				"This procedure verifies that the line card can pass signals in the digital to analog and analog 
				to digital directions. It measures trans-hybrid loss with open-circuit and a load impedance
				applied to the line. These trans-hybrid loss results are checked against expected values to
				generate a pass/fail result."
			::= { shePotsLineTestTransmissionSelfTestGroup 1 }

		
--         1.3.6.1.4.1.231.7.1.2.2.1.38.10.7.4.1.1
		shePotsLineTestTransmissionSelfTestEntry OBJECT-TYPE
			SYNTAX ShePotsLineTestTransmissionSelfTestEntry
			MAX-ACCESS not-accessible
			STATUS current
			DESCRIPTION
				"Entry of shePotsLineTestTransmitionSelfTestTable,
				Each entry is used to represent a line which execute the test."
			INDEX { ifIndex }
			::= { shePotsLineTestTransmissionSelfTestTable 1 }

		
		ShePotsLineTestTransmissionSelfTestEntry ::=
			SEQUENCE { 
				shePotsLineTestTransmissionSelfTestThlOpen
					INTEGER,
				shePotsLineTestTransmissionSelfTestThlRload
					INTEGER,
				shePotsLineTestTransmissionSelfTestThlExpectedLL
					INTEGER,
				shePotsLineTestTransmissionSelfTestThlExpectedUL
					INTEGER,
				shePotsLineTestTransmissionSelfTestAbortedDueToOffHook
					TruthValue,
				shePotsLineTestTransmissionSelfTestPassed
					TruthValue,
				shePotsLineTestTransmissionSelfTestTriggerSource
					ShePotsLineTestTriggerType
			 }

--         1.3.6.1.4.1.231.7.1.2.2.1.38.10.7.4.1.1.1
		shePotsLineTestTransmissionSelfTestThlOpen OBJECT-TYPE
			SYNTAX INTEGER
			UNITS "dBm0"
			MAX-ACCESS read-only
			STATUS current
			DESCRIPTION
				"Measured open circuit transhybrid loss dBm0 x100.
				However, this output should not be shown to users."
			::= { shePotsLineTestTransmissionSelfTestEntry 1 }

		
--         1.3.6.1.4.1.231.7.1.2.2.1.38.10.7.4.1.1.2
		shePotsLineTestTransmissionSelfTestThlRload OBJECT-TYPE
			SYNTAX INTEGER
			UNITS "dBm0"
			MAX-ACCESS read-only
			STATUS current
			DESCRIPTION
				"Measured transhybrid loss test load dBm0 x100.
				However, this output should not be shown to users."
			::= { shePotsLineTestTransmissionSelfTestEntry 2 }

		
--         1.3.6.1.4.1.231.7.1.2.2.1.38.10.7.4.1.1.3
		shePotsLineTestTransmissionSelfTestThlExpectedLL OBJECT-TYPE
			SYNTAX INTEGER
			UNITS "dBm0"
			MAX-ACCESS read-only
			STATUS current
			DESCRIPTION
				"Lower limit for the expected transhybrid loss for test load dBm0 x100.
				However, this output should not be shown to users."
			::= { shePotsLineTestTransmissionSelfTestEntry 3 }

		
--         1.3.6.1.4.1.231.7.1.2.2.1.38.10.7.4.1.1.4
		shePotsLineTestTransmissionSelfTestThlExpectedUL OBJECT-TYPE
			SYNTAX INTEGER
			UNITS "dBm0"
			MAX-ACCESS read-only
			STATUS current
			DESCRIPTION
				"Upper limit for the expected transhybrid loss for test load dBm0 x100.
				However, this output should not be shown to users."
			::= { shePotsLineTestTransmissionSelfTestEntry 4 }

		
--         1.3.6.1.4.1.231.7.1.2.2.1.38.10.7.4.1.1.5
		shePotsLineTestTransmissionSelfTestAbortedDueToOffHook OBJECT-TYPE
			SYNTAX TruthValue
			MAX-ACCESS read-only
			STATUS current
			DESCRIPTION
				"If set to TRUE indicates test was aborted due to detection on OFF hook.
				However, this output should not be shown to users."
			::= { shePotsLineTestTransmissionSelfTestEntry 5 }

		
--         1.3.6.1.4.1.231.7.1.2.2.1.38.10.7.4.1.1.6
		shePotsLineTestTransmissionSelfTestPassed OBJECT-TYPE
			SYNTAX TruthValue
			MAX-ACCESS read-only
			STATUS current
			DESCRIPTION
				"1: the test passed;
				0: the test failed.    "
			::= { shePotsLineTestTransmissionSelfTestEntry 6 }

		
--         1.3.6.1.4.1.231.7.1.2.2.1.38.10.7.4.1.1.7
		shePotsLineTestTransmissionSelfTestTriggerSource OBJECT-TYPE
			SYNTAX ShePotsLineTestTriggerType
			MAX-ACCESS read-only
			STATUS current
			DESCRIPTION
				"Test Trigger Source."
			::= { shePotsLineTestTransmissionSelfTestEntry 7 }

		
--         1.3.6.1.4.1.231.7.1.2.2.1.38.10.7.4.2
		shePotsLineTestTransmissionSelfTestControl OBJECT IDENTIFIER ::= { shePotsLineTestTransmissionSelfTestGroup 2 }

		
--         1.3.6.1.4.1.231.7.1.2.2.1.38.10.7.4.2.1
		shePotsLineTestTransmissionSelfTestControlRequest OBJECT-TYPE
			SYNTAX ShePotsLineTestControlRequestType
			MAX-ACCESS read-write
			STATUS current
			DESCRIPTION
				"User Command
				setTransmitionSelfTest:
				shePotsLineTestTransmissionSelfTestControlIndex
				
				
				Long-running Command"
			::= { shePotsLineTestTransmissionSelfTestControl 1 }

		
--         1.3.6.1.4.1.231.7.1.2.2.1.38.10.7.4.2.2
		shePotsLineTestTransmissionSelfTestControlIndex OBJECT-TYPE
			SYNTAX InterfaceIndex
			MAX-ACCESS read-write
			STATUS current
			DESCRIPTION
				"The IfIndex of the line which test shall be executed"
			::= { shePotsLineTestTransmissionSelfTestControl 2 }

		
--         1.3.6.1.4.1.231.7.1.2.2.1.38.10.7.4.2.3
		shePotsLineTestTransmissionSelfTestControlStatus OBJECT-TYPE
			SYNTAX SheControlStatusType
			MAX-ACCESS read-only
			STATUS current
			DESCRIPTION
				"The status of a user command"
			::= { shePotsLineTestTransmissionSelfTestControl 3 }

		
--         1.3.6.1.4.1.231.7.1.2.2.1.38.10.7.4.2.4
		shePotsLineTestTransmissionSelfTestControlTimer OBJECT-TYPE
			SYNTAX Gauge32
			MAX-ACCESS read-only
			STATUS current
			DESCRIPTION
				"The maximum wait time for the manager for a long running user command."
			::= { shePotsLineTestTransmissionSelfTestControl 4 }

		
--         1.3.6.1.4.1.231.7.1.2.2.1.38.10.7.4.2.5
		shePotsLineTestTransmissionSelfTestControlTimeStamp OBJECT-TYPE
			SYNTAX Unsigned32
			MAX-ACCESS read-only
			STATUS current
			DESCRIPTION
				"The time stamp of the last command (end of command)."
			::= { shePotsLineTestTransmissionSelfTestControl 5 }

		
--         1.3.6.1.4.1.231.7.1.2.2.1.38.10.7.4.2.6
		shePotsLineTestTransmissionSelfTestControlReqResult OBJECT-TYPE
			SYNTAX ShePotsLineTestControlRequestResultType
			MAX-ACCESS read-only
			STATUS current
			DESCRIPTION
				"The result of the last user command."
			::= { shePotsLineTestTransmissionSelfTestControl 6 }

		
--         1.3.6.1.4.1.231.7.1.2.2.1.38.10.7.5
		shePotsLineTestTransHybridLossTestGroup OBJECT IDENTIFIER ::= { shePotsLineTestIltfTestGroup 5 }

		
--         1.3.6.1.4.1.231.7.1.2.2.1.38.10.7.5.1
		shePotsLineTestTransHybridLossTestTable OBJECT-TYPE
			SYNTAX SEQUENCE OF ShePotsLineTestTransHybridLossTestEntry
			MAX-ACCESS not-accessible
			STATUS current
			DESCRIPTION
				"This test measures trans-hybrid loss by generating a tone and measuring the reflected signal."
			::= { shePotsLineTestTransHybridLossTestGroup 1 }

		
--         1.3.6.1.4.1.231.7.1.2.2.1.38.10.7.5.1.1
		shePotsLineTestTransHybridLossTestEntry OBJECT-TYPE
			SYNTAX ShePotsLineTestTransHybridLossTestEntry
			MAX-ACCESS not-accessible
			STATUS current
			DESCRIPTION
				"Entry of shePotsLineTestTransHybridLossTestTable,
				Each entry is used to represent a line which execute the test."
			INDEX { ifIndex }
			::= { shePotsLineTestTransHybridLossTestTable 1 }

		
		ShePotsLineTestTransHybridLossTestEntry ::=
			SEQUENCE { 
				shePotsLineTestTransHybridLossTestEcho
					INTEGER,
				shePotsLineTestTransHybridLossTestLoss
					INTEGER,
				shePotsLineTestTransHybridLossTestTriggerSource
					ShePotsLineTestTriggerType
			 }

--         1.3.6.1.4.1.231.7.1.2.2.1.38.10.7.5.1.1.1
		shePotsLineTestTransHybridLossTestEcho OBJECT-TYPE
			SYNTAX INTEGER
			UNITS "dBm0"
			MAX-ACCESS read-only
			STATUS current
			DESCRIPTION
				" Measured echo in dBm0 x100
				should display as echo/100 dBm0"
			::= { shePotsLineTestTransHybridLossTestEntry 1 }

		
--         1.3.6.1.4.1.231.7.1.2.2.1.38.10.7.5.1.1.2
		shePotsLineTestTransHybridLossTestLoss OBJECT-TYPE
			SYNTAX INTEGER
			UNITS "dB"
			MAX-ACCESS read-only
			STATUS current
			DESCRIPTION
				"Measured loss in dB x100
				should display as loss/100 dB"
			::= { shePotsLineTestTransHybridLossTestEntry 2 }

		
--         1.3.6.1.4.1.231.7.1.2.2.1.38.10.7.5.1.1.4
		shePotsLineTestTransHybridLossTestTriggerSource OBJECT-TYPE
			SYNTAX ShePotsLineTestTriggerType
			MAX-ACCESS read-only
			STATUS current
			DESCRIPTION
				"Test Trigger Source."
			::= { shePotsLineTestTransHybridLossTestEntry 3 }

		
--         1.3.6.1.4.1.231.7.1.2.2.1.38.10.7.5.2
		shePotsLineTestTransHybridLossTestControl OBJECT IDENTIFIER ::= { shePotsLineTestTransHybridLossTestGroup 2 }

		
--         1.3.6.1.4.1.231.7.1.2.2.1.38.10.7.5.2.1
		shePotsLineTestTransHybridLossTestControlRequest OBJECT-TYPE
			SYNTAX ShePotsLineTestControlRequestType
			MAX-ACCESS read-write
			STATUS current
			DESCRIPTION
				"setTransHybridLossTest:
				shePotsLineTestTransHybridLossTestControlIndex
				shePotsLineTestTransHybridLossTestControlTestFreq
				shePotsLineTestTransHybridLossTestControlTestLevel
				shePotsLineTestTransHybridLossTestControlpAcProfileForTest
				shePotsLineTestTransHybridLossTestControlpAcProfileAfterTest
				
				
				Long-running Command"
			::= { shePotsLineTestTransHybridLossTestControl 1 }

		
--         1.3.6.1.4.1.231.7.1.2.2.1.38.10.7.5.2.2
		shePotsLineTestTransHybridLossTestControlIndex OBJECT-TYPE
			SYNTAX InterfaceIndex
			MAX-ACCESS read-write
			STATUS current
			DESCRIPTION
				"The IfIndex of the line which test shall be executed"
			::= { shePotsLineTestTransHybridLossTestControl 2 }

		
--         1.3.6.1.4.1.231.7.1.2.2.1.38.10.7.5.2.3
		shePotsLineTestTransHybridLossTestControlStatus OBJECT-TYPE
			SYNTAX SheControlStatusType
			MAX-ACCESS read-only
			STATUS current
			DESCRIPTION
				"The status of a user command."
			::= { shePotsLineTestTransHybridLossTestControl 3 }

		
--         1.3.6.1.4.1.231.7.1.2.2.1.38.10.7.5.2.4
		shePotsLineTestTransHybridLossTestControlTimer OBJECT-TYPE
			SYNTAX Gauge32
			MAX-ACCESS read-only
			STATUS current
			DESCRIPTION
				"The maximum wait time for the manager for a long running user command."
			::= { shePotsLineTestTransHybridLossTestControl 4 }

		
--         1.3.6.1.4.1.231.7.1.2.2.1.38.10.7.5.2.5
		shePotsLineTestTransHybridLossTestControlTimeStamp OBJECT-TYPE
			SYNTAX Unsigned32
			MAX-ACCESS read-only
			STATUS current
			DESCRIPTION
				"The time stamp of the last command (end of command)."
			::= { shePotsLineTestTransHybridLossTestControl 5 }

		
--         1.3.6.1.4.1.231.7.1.2.2.1.38.10.7.5.2.6
		shePotsLineTestTransHybridLossTestControlReqResult OBJECT-TYPE
			SYNTAX ShePotsLineTestControlRequestResultType
			MAX-ACCESS read-only
			STATUS current
			DESCRIPTION
				"The result of the last user command."
			::= { shePotsLineTestTransHybridLossTestControl 6 }

		
--         1.3.6.1.4.1.231.7.1.2.2.1.38.10.7.5.2.7
		shePotsLineTestTransHybridLossTestControlTestFreq OBJECT-TYPE
			SYNTAX INTEGER (0..3800)
			UNITS "Hz"
			MAX-ACCESS read-write
			STATUS current
			DESCRIPTION
				"Test tone frequency in Hertz."
			DEFVAL { 1010 }
			::= { shePotsLineTestTransHybridLossTestControl 7 }

		
--         1.3.6.1.4.1.231.7.1.2.2.1.38.10.7.5.2.8
		shePotsLineTestTransHybridLossTestControlTestLevel OBJECT-TYPE
			SYNTAX INTEGER (-40..0)
			UNITS "dBm0"
			MAX-ACCESS read-write
			STATUS current
			DESCRIPTION
				"Test tone power level in dBm0."
			DEFVAL { -10 }
			::= { shePotsLineTestTransHybridLossTestControl 8 }

		
--         1.3.6.1.4.1.231.7.1.2.2.1.38.10.7.6
		shePotsLineTestNoiseMeasurementTestGroup OBJECT IDENTIFIER ::= { shePotsLineTestIltfTestGroup 6 }

		
--         1.3.6.1.4.1.231.7.1.2.2.1.38.10.7.6.1
		shePotsLineTestNoiseMeasurementTestTable OBJECT-TYPE
			SYNTAX SEQUENCE OF ShePotsLineTestNoiseMeasurementTestEntry
			MAX-ACCESS not-accessible
			STATUS current
			DESCRIPTION
				"This procedure performs an active or passive noise test. Various filters may be applied to the
				received signal during this test. The application can apply special AC transmission
				coefficients during this test if desired."
			::= { shePotsLineTestNoiseMeasurementTestGroup 1 }

		
--         1.3.6.1.4.1.231.7.1.2.2.1.38.10.7.6.1.1
		shePotsLineTestNoiseMeasurementTestEntry OBJECT-TYPE
			SYNTAX ShePotsLineTestNoiseMeasurementTestEntry
			MAX-ACCESS not-accessible
			STATUS current
			DESCRIPTION
				"Entry of shePotsLineTestNoiseMeasurementTestTable,
				Each entry is used to represent a line which execute the test."
			INDEX { ifIndex }
			::= { shePotsLineTestNoiseMeasurementTestTable 1 }

		
		ShePotsLineTestNoiseMeasurementTestEntry ::=
			SEQUENCE { 
				shePotsLineTestNoiseMeasurementTestNoise
					INTEGER,
				shePotsLineTestNoiseMeasurementTestTriggerSource
					ShePotsLineTestTriggerType
			 }

--         1.3.6.1.4.1.231.7.1.2.2.1.38.10.7.6.1.1.1
		shePotsLineTestNoiseMeasurementTestNoise OBJECT-TYPE
			SYNTAX INTEGER
			UNITS "dBm0"
			MAX-ACCESS read-only
			STATUS current
			DESCRIPTION
				"Measured noise in dBm0 x100
				should display as noise/100"
			::= { shePotsLineTestNoiseMeasurementTestEntry 1 }

		
--         1.3.6.1.4.1.231.7.1.2.2.1.38.10.7.6.1.1.3
		shePotsLineTestNoiseMeasurementTestTriggerSource OBJECT-TYPE
			SYNTAX ShePotsLineTestTriggerType
			MAX-ACCESS read-only
			STATUS current
			DESCRIPTION
				"Test Trigger Source."
			::= { shePotsLineTestNoiseMeasurementTestEntry 2 }

		
--         1.3.6.1.4.1.231.7.1.2.2.1.38.10.7.6.2
		shePotsLineTestNoiseMeasurementTestControl OBJECT IDENTIFIER ::= { shePotsLineTestNoiseMeasurementTestGroup 2 }

		
--         1.3.6.1.4.1.231.7.1.2.2.1.38.10.7.6.2.1
		shePotsLineTestNoiseMeasurementTestControlRequest OBJECT-TYPE
			SYNTAX ShePotsLineTestControlRequestType
			MAX-ACCESS read-write
			STATUS current
			DESCRIPTION
				"User Command.
				setNoiseMeasurementTest:
				shePotsLineTestNoiseMeasurementTestControlIndex
				shePotsLineTestNoiseMeasurementTestControlOutputSignalPower
				shePotsLineTestNoiseMeasurementTestControlVpTestFilter
				
				
				Long-running Command"
			::= { shePotsLineTestNoiseMeasurementTestControl 1 }

		
--         1.3.6.1.4.1.231.7.1.2.2.1.38.10.7.6.2.2
		shePotsLineTestNoiseMeasurementTestControlIndex OBJECT-TYPE
			SYNTAX InterfaceIndex
			MAX-ACCESS read-write
			STATUS current
			DESCRIPTION
				"The IfIndex of the line which test shall be executed."
			::= { shePotsLineTestNoiseMeasurementTestControl 2 }

		
--         1.3.6.1.4.1.231.7.1.2.2.1.38.10.7.6.2.3
		shePotsLineTestNoiseMeasurementTestControlStatus OBJECT-TYPE
			SYNTAX SheControlStatusType
			MAX-ACCESS read-only
			STATUS current
			DESCRIPTION
				"The status of a user command"
			::= { shePotsLineTestNoiseMeasurementTestControl 3 }

		
--         1.3.6.1.4.1.231.7.1.2.2.1.38.10.7.6.2.4
		shePotsLineTestNoiseMeasurementTestControlTimer OBJECT-TYPE
			SYNTAX Gauge32
			MAX-ACCESS read-only
			STATUS current
			DESCRIPTION
				"The maximum wait time for the manager for a long running user command."
			::= { shePotsLineTestNoiseMeasurementTestControl 4 }

		
--         1.3.6.1.4.1.231.7.1.2.2.1.38.10.7.6.2.5
		shePotsLineTestNoiseMeasurementTestControlTimeStamp OBJECT-TYPE
			SYNTAX Unsigned32
			MAX-ACCESS read-only
			STATUS current
			DESCRIPTION
				"The time stamp of the last command (end of command)."
			::= { shePotsLineTestNoiseMeasurementTestControl 5 }

		
--         1.3.6.1.4.1.231.7.1.2.2.1.38.10.7.6.2.6
		shePotsLineTestNoiseMeasurementTestControlReqResult OBJECT-TYPE
			SYNTAX ShePotsLineTestControlRequestResultType
			MAX-ACCESS read-only
			STATUS current
			DESCRIPTION
				"The result of the last user command."
			::= { shePotsLineTestNoiseMeasurementTestControl 6 }

		
--         1.3.6.1.4.1.231.7.1.2.2.1.38.10.7.6.2.8
		shePotsLineTestNoiseMeasurementTestControlVpTestFilter OBJECT-TYPE
			SYNTAX ShePotsLineTestNoiseMeasurementTestControlVpTestFilterType
			MAX-ACCESS read-write
			STATUS current
			DESCRIPTION
				"vPFilterNone(0),
				vPFilter3kHz(1),
				vPFilterCMsg(2),
				vPFilter15kHz(3),
				vPFilter3p4kHz(4),
				vPFilterD(5)
				Default: vPFilterNone"
			DEFVAL { vPFilterNone }
			::= { shePotsLineTestNoiseMeasurementTestControl 7 }

		
--         1.3.6.1.4.1.231.7.1.2.2.1.38.10.7.7
		shePotsLineTestForeignDCVoltageTestGroup OBJECT IDENTIFIER ::= { shePotsLineTestIltfTestGroup 7 }

		
--         1.3.6.1.4.1.231.7.1.2.2.1.38.10.7.7.1
		shePotsLineTestForeignDCVoltageTestTable OBJECT-TYPE
			SYNTAX SEQUENCE OF ShePotsLineTestForeignDCVoltageTestEntry
			MAX-ACCESS not-accessible
			STATUS current
			DESCRIPTION
				"This procedure measures the foreign voltage present on the loop while the line card is in a
				high impedance state. It would be a safe practice to execute this test before putting the line in 
				service."
			::= { shePotsLineTestForeignDCVoltageTestGroup 1 }

		
--         1.3.6.1.4.1.231.7.1.2.2.1.38.10.7.7.1.1
		shePotsLineTestForeignDCVoltageTestEntry OBJECT-TYPE
			SYNTAX ShePotsLineTestForeignDCVoltageTestEntry
			MAX-ACCESS not-accessible
			STATUS current
			DESCRIPTION
				"Entry of shePotsLineTestForeignDCVoltageTestTable,
				Each entry is used to represent a line which execute the test."
			INDEX { ifIndex }
			::= { shePotsLineTestForeignDCVoltageTestTable 1 }

		
		ShePotsLineTestForeignDCVoltageTestEntry ::=
			SEQUENCE { 
				shePotsLineTestForeignDCVoltageTestvTip
					INTEGER,
				shePotsLineTestForeignDCVoltageTestvRing
					INTEGER,
				shePotsLineTestForeignDCVoltageTestvDiff
					INTEGER,
				shePotsLineTestForeignDCVoltageTestPassed
					TruthValue,
				shePotsLineTestForeignDCVoltageTestTriggerSource
					ShePotsLineTestTriggerType
			 }

--         1.3.6.1.4.1.231.7.1.2.2.1.38.10.7.7.1.1.1
		shePotsLineTestForeignDCVoltageTestvTip OBJECT-TYPE
			SYNTAX INTEGER
			UNITS "V"
			MAX-ACCESS read-only
			STATUS current
			DESCRIPTION
				"Measured tip voltage in Volts x100 .
				should display as Voltage/100"
			::= { shePotsLineTestForeignDCVoltageTestEntry 1 }

		
--         1.3.6.1.4.1.231.7.1.2.2.1.38.10.7.7.1.1.2
		shePotsLineTestForeignDCVoltageTestvRing OBJECT-TYPE
			SYNTAX INTEGER
			UNITS "V"
			MAX-ACCESS read-only
			STATUS current
			DESCRIPTION
				"Measured ring voltage in Volts x100 .
				should display as Voltage/100"
			::= { shePotsLineTestForeignDCVoltageTestEntry 2 }

		
--         1.3.6.1.4.1.231.7.1.2.2.1.38.10.7.7.1.1.3
		shePotsLineTestForeignDCVoltageTestvDiff OBJECT-TYPE
			SYNTAX INTEGER
			UNITS "V"
			MAX-ACCESS read-only
			STATUS current
			DESCRIPTION
				"Measured differential voltage in Volts x100 .
				should display as Voltage/100"
			::= { shePotsLineTestForeignDCVoltageTestEntry 3 }

		
--        1.3.6.1.4.1.231.7.1.2.2.1.38.10.7.7.1.1.4
		shePotsLineTestForeignDCVoltageTestPassed OBJECT-TYPE
			SYNTAX TruthValue
			MAX-ACCESS read-only
			STATUS current
			DESCRIPTION
				"1 test passed
				0 test failed
				"
			::= { shePotsLineTestForeignDCVoltageTestEntry 4 }

		
--         1.3.6.1.4.1.231.7.1.2.2.1.38.10.7.7.1.1.5
		shePotsLineTestForeignDCVoltageTestTriggerSource OBJECT-TYPE
			SYNTAX ShePotsLineTestTriggerType
			MAX-ACCESS read-only
			STATUS current
			DESCRIPTION
				"Test Trigger Source."
			::= { shePotsLineTestForeignDCVoltageTestEntry 5 }

		
--         1.3.6.1.4.1.231.7.1.2.2.1.38.10.7.7.2
		shePotsLineTestForeignDCVoltageTestControl OBJECT IDENTIFIER ::= { shePotsLineTestForeignDCVoltageTestGroup 2 }

		
--         1.3.6.1.4.1.231.7.1.2.2.1.38.10.7.7.2.1
		shePotsLineTestForeignDCVoltageTestControlRequest OBJECT-TYPE
			SYNTAX ShePotsLineTestControlRequestType
			MAX-ACCESS read-write
			STATUS current
			DESCRIPTION
				"User command.
				setForeignDCVoltageTest:
				shePotsLineTestForeignDCVoltageTestControlIndex
				
				Long-running Command"
			::= { shePotsLineTestForeignDCVoltageTestControl 1 }

		
--         1.3.6.1.4.1.231.7.1.2.2.1.38.10.7.7.2.2
		shePotsLineTestForeignDCVoltageTestControlIndex OBJECT-TYPE
			SYNTAX InterfaceIndex
			MAX-ACCESS read-write
			STATUS current
			DESCRIPTION
				"The IfIndex of the line which test shall be executed"
			::= { shePotsLineTestForeignDCVoltageTestControl 2 }

		
--         1.3.6.1.4.1.231.7.1.2.2.1.38.10.7.7.2.3
		shePotsLineTestForeignDCVoltageTestControlStatus OBJECT-TYPE
			SYNTAX SheControlStatusType
			MAX-ACCESS read-only
			STATUS current
			DESCRIPTION
				"The status of a user command."
			::= { shePotsLineTestForeignDCVoltageTestControl 3 }

		
--         1.3.6.1.4.1.231.7.1.2.2.1.38.10.7.7.2.4
		shePotsLineTestForeignDCVoltageTestControlTimer OBJECT-TYPE
			SYNTAX Gauge32
			MAX-ACCESS read-only
			STATUS current
			DESCRIPTION
				"The maximum wait time for the manager for a long running user command."
			::= { shePotsLineTestForeignDCVoltageTestControl 4 }

		
--         1.3.6.1.4.1.231.7.1.2.2.1.38.10.7.7.2.5
		shePotsLineTestForeignDCVoltageTestControlTimeStamp OBJECT-TYPE
			SYNTAX Unsigned32
			MAX-ACCESS read-only
			STATUS current
			DESCRIPTION
				"The time stamp of the last command (end of command)."
			::= { shePotsLineTestForeignDCVoltageTestControl 5 }

		
--         1.3.6.1.4.1.231.7.1.2.2.1.38.10.7.7.2.6
		shePotsLineTestForeignDCVoltageTestControlReqResult OBJECT-TYPE
			SYNTAX ShePotsLineTestControlRequestResultType
			MAX-ACCESS read-only
			STATUS current
			DESCRIPTION
				"The result of the last user command."
			::= { shePotsLineTestForeignDCVoltageTestControl 6 }

		
--         1.3.6.1.4.1.231.7.1.2.2.1.38.10.7.8
		shePotsLineTestForeignACVoltageTestGroup OBJECT IDENTIFIER ::= { shePotsLineTestIltfTestGroup 8 }

		
--         1.3.6.1.4.1.231.7.1.2.2.1.38.10.7.8.1
		shePotsLineTestForeignACVoltageTestTable OBJECT-TYPE
			SYNTAX SEQUENCE OF ShePotsLineTestForeignACVoltageTestEntry
			MAX-ACCESS not-accessible
			STATUS current
			DESCRIPTION
				"When measuring the AC foreign voltage, it is not necessary to wait for the DC condition to
				settle on the loop.The test procedure includes a high-pass filter that will remove any DC
				voltage present during the test. The only requirement is to include enough settling time to
				avoid calculating the AC voltage while the DC is changing rapidly. This might happen if the
				fault is low impedance."
			::= { shePotsLineTestForeignACVoltageTestGroup 1 }

		
--         1.3.6.1.4.1.231.7.1.2.2.1.38.10.7.8.1.1
		shePotsLineTestForeignACVoltageTestEntry OBJECT-TYPE
			SYNTAX ShePotsLineTestForeignACVoltageTestEntry
			MAX-ACCESS not-accessible
			STATUS current
			DESCRIPTION
				"Entry of shePotsLineTestForeignACVoltageTestTable,
				Each entry is used to represent a line which execute the test."
			INDEX { ifIndex }
			::= { shePotsLineTestForeignACVoltageTestTable 1 }

		
		ShePotsLineTestForeignACVoltageTestEntry ::=
			SEQUENCE { 
				shePotsLineTestForeignACVoltageTestvTip
					INTEGER,
				shePotsLineTestForeignACVoltageTestvRing
					INTEGER,
				shePotsLineTestForeignACVoltageTestvDiff
					INTEGER,
				shePotsLineTestForeignACVoltageTestTriggerSource
					ShePotsLineTestTriggerType
			 }

--         1.3.6.1.4.1.231.7.1.2.2.1.38.10.7.8.1.1.1
		shePotsLineTestForeignACVoltageTestvTip OBJECT-TYPE
			SYNTAX INTEGER
			UNITS "V"
			MAX-ACCESS read-only
			STATUS current
			DESCRIPTION
				"Measured tip voltage in  in Vrms x100
				should display as Voltage/100"
			::= { shePotsLineTestForeignACVoltageTestEntry 1 }

		
--         1.3.6.1.4.1.231.7.1.2.2.1.38.10.7.8.1.1.2
		shePotsLineTestForeignACVoltageTestvRing OBJECT-TYPE
			SYNTAX INTEGER
			UNITS "V"
			MAX-ACCESS read-only
			STATUS current
			DESCRIPTION
				"Measured ring voltage in Vrms x100 
				should display as Voltage/100"
			::= { shePotsLineTestForeignACVoltageTestEntry 2 }

		
--         1.3.6.1.4.1.231.7.1.2.2.1.38.10.7.8.1.1.2
		shePotsLineTestForeignACVoltageTestvDiff OBJECT-TYPE
			SYNTAX INTEGER
			UNITS "V"
			MAX-ACCESS read-only
			STATUS current
			DESCRIPTION
				"Measured the differential voltagein in Vrms x100 
				should display as Voltage/100"
			::= { shePotsLineTestForeignACVoltageTestEntry 3 }

		
--         1.3.6.1.4.1.231.7.1.2.2.1.38.10.7.8.1.1.5
		shePotsLineTestForeignACVoltageTestTriggerSource OBJECT-TYPE
			SYNTAX ShePotsLineTestTriggerType
			MAX-ACCESS read-only
			STATUS current
			DESCRIPTION
				"Test Trigger Type."
			::= { shePotsLineTestForeignACVoltageTestEntry 4 }

		
--         1.3.6.1.4.1.231.7.1.2.2.1.38.10.7.8.2
		shePotsLineTestForeignACVoltageTestControl OBJECT IDENTIFIER ::= { shePotsLineTestForeignACVoltageTestGroup 2 }

		
--         1.3.6.1.4.1.231.7.1.2.2.1.38.10.7.8.2.1
		shePotsLineTestForeignACVoltageTestControlRequest OBJECT-TYPE
			SYNTAX ShePotsLineTestControlRequestType
			MAX-ACCESS read-write
			STATUS current
			DESCRIPTION
				"User command.
				setForeignACVoltageTest:
				shePotsLineTestForeignACVoltageTestControlIndex
				
				
				Long-running Command"
			::= { shePotsLineTestForeignACVoltageTestControl 1 }

		
--         1.3.6.1.4.1.231.7.1.2.2.1.38.10.7.8.2.2
		shePotsLineTestForeignACVoltageTestControlIndex OBJECT-TYPE
			SYNTAX InterfaceIndex
			MAX-ACCESS read-write
			STATUS current
			DESCRIPTION
				"The IfIndex of the line which test shall be executed"
			::= { shePotsLineTestForeignACVoltageTestControl 2 }

		
--         1.3.6.1.4.1.231.7.1.2.2.1.38.10.7.8.2.3
		shePotsLineTestForeignACVoltageTestControlStatus OBJECT-TYPE
			SYNTAX SheControlStatusType
			MAX-ACCESS read-only
			STATUS current
			DESCRIPTION
				"The status of a user command"
			::= { shePotsLineTestForeignACVoltageTestControl 3 }

		
--         1.3.6.1.4.1.231.7.1.2.2.1.38.10.7.8.2.4
		shePotsLineTestForeignACVoltageTestControlTimer OBJECT-TYPE
			SYNTAX Gauge32
			MAX-ACCESS read-only
			STATUS current
			DESCRIPTION
				"The maximum wait time for the manager for a long running user command."
			::= { shePotsLineTestForeignACVoltageTestControl 4 }

		
--         1.3.6.1.4.1.231.7.1.2.2.1.38.10.7.8.2.5
		shePotsLineTestForeignACVoltageTestControlTimeStamp OBJECT-TYPE
			SYNTAX Unsigned32
			MAX-ACCESS read-only
			STATUS current
			DESCRIPTION
				"The time stamp of the last command (end of command)."
			::= { shePotsLineTestForeignACVoltageTestControl 5 }

		
--         1.3.6.1.4.1.231.7.1.2.2.1.38.10.7.8.2.6
		shePotsLineTestForeignACVoltageTestControlReqResult OBJECT-TYPE
			SYNTAX ShePotsLineTestControlRequestResultType
			MAX-ACCESS read-only
			STATUS current
			DESCRIPTION
				"The result of the last user command."
			::= { shePotsLineTestForeignACVoltageTestControl 6 }

		
--         1.3.6.1.4.1.231.7.1.2.2.1.38.10.7.9
		shePotsLineTestDcLoopResistanceTestGroup OBJECT IDENTIFIER ::= { shePotsLineTestIltfTestGroup 9 }

		
--         1.3.6.1.4.1.231.7.1.2.2.1.38.10.7.9.1
		shePotsLineTestDcLoopResistanceTestTable OBJECT-TYPE
			SYNTAX SEQUENCE OF ShePotsLineTestDcLoopResistanceTestEntry
			MAX-ACCESS not-accessible
			STATUS current
			DESCRIPTION
				"This test measures DC loop resistance"
			::= { shePotsLineTestDcLoopResistanceTestGroup 1 }

		
--         1.3.6.1.4.1.231.7.1.2.2.1.38.10.7.9.1.1
		shePotsLineTestDcLoopResistanceTestEntry OBJECT-TYPE
			SYNTAX ShePotsLineTestDcLoopResistanceTestEntry
			MAX-ACCESS not-accessible
			STATUS current
			DESCRIPTION
				"Entry of shePotsLineTestDcLoopResistanceTestTable,
				Each entry is used to represent a line which execute the test."
			INDEX { ifIndex }
			::= { shePotsLineTestDcLoopResistanceTestTable 1 }

		
		ShePotsLineTestDcLoopResistanceTestEntry ::=
			SEQUENCE { 
				shePotsLineTestDcLoopResistanceTestrLoop
					INTEGER,
				shePotsLineTestDcLoopResistanceTestiLg
					INTEGER,
				shePotsLineTestDcLoopResistanceTestiLg2
					INTEGER,
				shePotsLineTestDcLoopResistanceTestvoltageSaturation
					TruthValue,
				shePotsLineTestDcLoopResistanceTestdegradedByCmc
					TruthValue,
				shePotsLineTestDcLoopResistanceTestTriggerSource
					ShePotsLineTestTriggerType
			 }

--         1.3.6.1.4.1.231.7.1.2.2.1.38.10.7.9.1.1.1
		shePotsLineTestDcLoopResistanceTestrLoop OBJECT-TYPE
			SYNTAX INTEGER
			UNITS "Ohm"
			MAX-ACCESS read-only
			STATUS current
			DESCRIPTION
				"Measured loop resistance Ohms x100
				should display as rLoop/100"
			::= { shePotsLineTestDcLoopResistanceTestEntry 1 }

		
--         1.3.6.1.4.1.231.7.1.2.2.1.38.10.7.9.1.1.2
		shePotsLineTestDcLoopResistanceTestiLg OBJECT-TYPE
			SYNTAX INTEGER
			UNITS "A"
			MAX-ACCESS read-only
			STATUS current
			DESCRIPTION
				"Common mode current.Amps x100
				However, this output should not be shown to users."
			::= { shePotsLineTestDcLoopResistanceTestEntry 2 }

		
--         1.3.6.1.4.1.231.7.1.2.2.1.38.10.7.9.1.1.3
		shePotsLineTestDcLoopResistanceTestiLg2 OBJECT-TYPE
			SYNTAX INTEGER
			UNITS "A"
			MAX-ACCESS read-only
			STATUS current
			DESCRIPTION
				"Common mode current in Amps x100
				However, this output should not be shown to users."
			::= { shePotsLineTestDcLoopResistanceTestEntry 3 }

		
--         1.3.6.1.4.1.231.7.1.2.2.1.38.10.7.9.1.1.4
		shePotsLineTestDcLoopResistanceTestvoltageSaturation OBJECT-TYPE
			SYNTAX TruthValue
			MAX-ACCESS read-only
			STATUS current
			DESCRIPTION
				"This flag (if set) indicated Voltage* Saturation occured during the test
				However, this output should not be shown to users."
			::= { shePotsLineTestDcLoopResistanceTestEntry 4 }

		
--         1.3.6.1.4.1.231.7.1.2.2.1.38.10.7.9.1.1.5
		shePotsLineTestDcLoopResistanceTestdegradedByCmc OBJECT-TYPE
			SYNTAX TruthValue
			MAX-ACCESS read-only
			STATUS current
			DESCRIPTION
				"Test results degraded by common mode current
				However, this output should not be shown to users."
			::= { shePotsLineTestDcLoopResistanceTestEntry 5 }

		
--         1.3.6.1.4.1.231.7.1.2.2.1.38.10.7.9.1.1.7
		shePotsLineTestDcLoopResistanceTestTriggerSource OBJECT-TYPE
			SYNTAX ShePotsLineTestTriggerType
			MAX-ACCESS read-only
			STATUS current
			DESCRIPTION
				"Test Trigger Source."
			::= { shePotsLineTestDcLoopResistanceTestEntry 6 }

		
--         1.3.6.1.4.1.231.7.1.2.2.1.38.10.7.9.2
		shePotsLineTestDcLoopResistanceTestControl OBJECT IDENTIFIER ::= { shePotsLineTestDcLoopResistanceTestGroup 2 }

		
--         1.3.6.1.4.1.231.7.1.2.2.1.38.10.7.9.2.1
		shePotsLineTestDcLoopResistanceSelfTestControlRequest OBJECT-TYPE
			SYNTAX ShePotsLineTestControlRequestType
			MAX-ACCESS read-write
			STATUS current
			DESCRIPTION
				"User command.
				setDcLoopResistanceTest:
				shePotsLineTestDcLoopResistanceTestControlIndex
				
				
				Long-running Command"
			::= { shePotsLineTestDcLoopResistanceTestControl 1 }

		
--         1.3.6.1.4.1.231.7.1.2.2.1.38.10.7.9.2.2
		shePotsLineTestDcLoopResistanceTestControlIndex OBJECT-TYPE
			SYNTAX InterfaceIndex
			MAX-ACCESS read-write
			STATUS current
			DESCRIPTION
				"The IfIndex of the line which test shall be executed"
			::= { shePotsLineTestDcLoopResistanceTestControl 2 }

		
--         1.3.6.1.4.1.231.7.1.2.2.1.38.10.7.9.2.3
		shePotsLineTestDcLoopResistanceTestControlStatus OBJECT-TYPE
			SYNTAX SheControlStatusType
			MAX-ACCESS read-only
			STATUS current
			DESCRIPTION
				"The status of a user command"
			::= { shePotsLineTestDcLoopResistanceTestControl 3 }

		
--         1.3.6.1.4.1.231.7.1.2.2.1.38.10.7.9.2.4
		shePotsLineTestDcLoopResistanceTestControlTimer OBJECT-TYPE
			SYNTAX Gauge32
			MAX-ACCESS read-only
			STATUS current
			DESCRIPTION
				"The maximum wait time for the manager for a long running user command."
			::= { shePotsLineTestDcLoopResistanceTestControl 4 }

		
--         1.3.6.1.4.1.231.7.1.2.2.1.38.10.7.9.2.5
		shePotsLineTestDcLoopResistanceTestControlTimeStamp OBJECT-TYPE
			SYNTAX Unsigned32
			MAX-ACCESS read-only
			STATUS current
			DESCRIPTION
				"The time stamp of the last command (end of command)."
			::= { shePotsLineTestDcLoopResistanceTestControl 5 }

		
--         1.3.6.1.4.1.231.7.1.2.2.1.38.10.7.9.2.6
		shePotsLineTestDcLoopResistanceTestControlReqResult OBJECT-TYPE
			SYNTAX ShePotsLineTestControlRequestResultType
			MAX-ACCESS read-only
			STATUS current
			DESCRIPTION
				"The result of the last user command."
			::= { shePotsLineTestDcLoopResistanceTestControl 6 }

		
--         1.3.6.1.4.1.231.7.1.2.2.1.38.10.7.10
		shePotsLineTest3ElementInsulationResistanceTestGroup OBJECT IDENTIFIER ::= { shePotsLineTestIltfTestGroup 10 }

		
--         1.3.6.1.4.1.231.7.1.2.2.1.38.10.7.10.1
		shePotsLineTest3ElementInsulationResistanceTestTable OBJECT-TYPE
			SYNTAX SEQUENCE OF ShePotsLineTest3ElementInsulationResistanceTestEntry
			MAX-ACCESS not-accessible
			STATUS current
			DESCRIPTION
				"This test measures tip-to-ground, ring-to-ground, and tip-to-ring resistance. This test can
				also measure the foreign DC voltage and current on the tip and ring leads."
			::= { shePotsLineTest3ElementInsulationResistanceTestGroup 1 }

		
--         1.3.6.1.4.1.231.7.1.2.2.1.38.10.7.10.1.1
		shePotsLineTest3ElementInsulationResistanceTestEntry OBJECT-TYPE
			SYNTAX ShePotsLineTest3ElementInsulationResistanceTestEntry
			MAX-ACCESS not-accessible
			STATUS current
			DESCRIPTION
				"Entry of shePotsLineTest3ElementInsulationResistanceTestTable,
				Each entry is used to represent a line which execute the test."
			INDEX { ifIndex }
			::= { shePotsLineTest3ElementInsulationResistanceTestTable 1 }

		
		ShePotsLineTest3ElementInsulationResistanceTestEntry ::=
			SEQUENCE { 
				shePotsLineTest3ElementInsulationResistanceTestrtg
					INTEGER,
				shePotsLineTest3ElementInsulationResistanceTestrrg
					INTEGER,
				shePotsLineTest3ElementInsulationResistanceTestrtr
					INTEGER,
				shePotsLineTest3ElementInsulationResistanceTestrGnd
					INTEGER,
				shePotsLineTest3ElementInsulationResistanceTestvTip
					INTEGER,
				shePotsLineTest3ElementInsulationResistanceTestvRing
					INTEGER,
				shePotsLineTest3ElementInsulationResistanceTestiTip
					INTEGER,
				shePotsLineTest3ElementInsulationResistanceTestiRing
					INTEGER,
				shePotsLineTest3ElementInsulationResistanceTestTriggerSource
					ShePotsLineTestTriggerType
			 }

--         1.3.6.1.4.1.231.7.1.2.2.1.38.10.7.10.1.1.1
		shePotsLineTest3ElementInsulationResistanceTestrtg OBJECT-TYPE
			SYNTAX INTEGER
			UNITS "Ohm"
			MAX-ACCESS read-only
			STATUS current
			DESCRIPTION
				"Tip-to-Ground resistance in Ohms x100
				0 impedance not measured
				>= 200000000 open
				<= -200000000 short 
				else should display as resistance/100"
			::= { shePotsLineTest3ElementInsulationResistanceTestEntry 1 }

		
--         1.3.6.1.4.1.231.7.1.2.2.1.38.10.7.10.1.1.2
		shePotsLineTest3ElementInsulationResistanceTestrrg OBJECT-TYPE
			SYNTAX INTEGER
			UNITS "Ohm"
			MAX-ACCESS read-only
			STATUS current
			DESCRIPTION
				"Ring-To_Ground resistance in Ohms x100
				0 impedance not measured
				>= 200000000 open
				<= -200000000 short  
				else should display as resistance/100"
			::= { shePotsLineTest3ElementInsulationResistanceTestEntry 2 }

		
--         1.3.6.1.4.1.231.7.1.2.2.1.38.10.7.10.1.1.3
		shePotsLineTest3ElementInsulationResistanceTestrtr OBJECT-TYPE
			SYNTAX INTEGER
			UNITS "Ohm"
			MAX-ACCESS read-only
			STATUS current
			DESCRIPTION
				"Tip-to-Ring resistance in Ohms x100
				0 impedance not measured
				>= 200000000 open
				<= -200000000 short 
				else should display as resistance/100"
			::= { shePotsLineTest3ElementInsulationResistanceTestEntry 3 }

		
--         1.3.6.1.4.1.231.7.1.2.2.1.38.10.7.10.1.1.4
		shePotsLineTest3ElementInsulationResistanceTestrGnd OBJECT-TYPE
			SYNTAX INTEGER
			UNITS "Ohm"
			MAX-ACCESS read-only
			STATUS current
			DESCRIPTION
				"Resistance to ground in Ohms  x100; Applicable if 
				there  exists a fault between tip and ring. 
				However, this output should not be shown to users."
			::= { shePotsLineTest3ElementInsulationResistanceTestEntry 4 }

		
--         1.3.6.1.4.1.231.7.1.2.2.1.38.10.7.10.1.1.5
		shePotsLineTest3ElementInsulationResistanceTestvTip OBJECT-TYPE
			SYNTAX INTEGER
			UNITS "V"
			MAX-ACCESS read-only
			STATUS current
			DESCRIPTION
				"Measured tip lead DC voltage in Volts x100
				However, this output should not be shown to users."
			::= { shePotsLineTest3ElementInsulationResistanceTestEntry 5 }

		
--         1.3.6.1.4.1.231.7.1.2.2.1.38.10.7.10.1.1.6
		shePotsLineTest3ElementInsulationResistanceTestvRing OBJECT-TYPE
			SYNTAX INTEGER
			UNITS "V"
			MAX-ACCESS read-only
			STATUS current
			DESCRIPTION
				"Measured ring lead DC voltage in Volts x100
				However, this output should not be shown to users."
			::= { shePotsLineTest3ElementInsulationResistanceTestEntry 6 }

		
--         1.3.6.1.4.1.231.7.1.2.2.1.38.10.7.10.1.1.7
		shePotsLineTest3ElementInsulationResistanceTestiTip OBJECT-TYPE
			SYNTAX INTEGER
			UNITS "mA"
			MAX-ACCESS read-only
			STATUS current
			DESCRIPTION
				"Measured tip lead DC current in  Amps x100
				However, this output should not be shown to users."
			::= { shePotsLineTest3ElementInsulationResistanceTestEntry 7 }

		
--         1.3.6.1.4.1.231.7.1.2.2.1.38.10.7.10.1.1.8
		shePotsLineTest3ElementInsulationResistanceTestiRing OBJECT-TYPE
			SYNTAX INTEGER
			UNITS "mA"
			MAX-ACCESS read-only
			STATUS current
			DESCRIPTION
				"Measured ring lead DC current in  Amps x100
				However, this output should not be shown to users."
			::= { shePotsLineTest3ElementInsulationResistanceTestEntry 8 }

		
--         1.3.6.1.4.1.231.7.1.2.2.1.38.10.7.10.1.1.10
		shePotsLineTest3ElementInsulationResistanceTestTriggerSource OBJECT-TYPE
			SYNTAX ShePotsLineTestTriggerType
			MAX-ACCESS read-only
			STATUS current
			DESCRIPTION
				"Test Trigger Source."
			::= { shePotsLineTest3ElementInsulationResistanceTestEntry 9 }

		
--         1.3.6.1.4.1.231.7.1.2.2.1.38.10.7.10.2
		shePotsLineTest3ElementInsulationResistanceTestControl OBJECT IDENTIFIER ::= { shePotsLineTest3ElementInsulationResistanceTestGroup 2 }

		
--         1.3.6.1.4.1.231.7.1.2.2.1.38.10.7.10.2.1
		shePotsLineTest3ElementInsulationResTestControlRequest OBJECT-TYPE
			SYNTAX ShePotsLineTestControlRequestType
			MAX-ACCESS read-write
			STATUS current
			DESCRIPTION
				"User command.
				set3ElementInsulationResistanceTest:
				shePotsLineTest3ElementInsulationResistanceTestControlIndex
				shePotsLineTest3ElementInsulationResistanceTestControlHighImpedanceTest
				shePotsLineTest3ElementInsulationResistanceTestControlMeasureForeignVI
				
				
				Long-running Command"
			::= { shePotsLineTest3ElementInsulationResistanceTestControl 1 }

		
--         1.3.6.1.4.1.231.7.1.2.2.1.38.10.7.10.2.2
		shePotsLineTest3ElementInsulationResTestControlIndex OBJECT-TYPE
			SYNTAX InterfaceIndex
			MAX-ACCESS read-write
			STATUS current
			DESCRIPTION
				"The IfIndex of the line which test shall be executed"
			::= { shePotsLineTest3ElementInsulationResistanceTestControl 2 }

		
--         1.3.6.1.4.1.231.7.1.2.2.1.38.10.7.10.2.3
		shePotsLineTest3ElementInsulationResTestControlStatus OBJECT-TYPE
			SYNTAX SheControlStatusType
			MAX-ACCESS read-only
			STATUS current
			DESCRIPTION
				"The status of a user command"
			::= { shePotsLineTest3ElementInsulationResistanceTestControl 3 }

		
--         1.3.6.1.4.1.231.7.1.2.2.1.38.10.7.10.2.4
		shePotsLineTest3ElementInsulationResTestControlTimer OBJECT-TYPE
			SYNTAX Gauge32
			MAX-ACCESS read-only
			STATUS current
			DESCRIPTION
				"The maximum wait time for the manager for a long running user command."
			::= { shePotsLineTest3ElementInsulationResistanceTestControl 4 }

		
--         1.3.6.1.4.1.231.7.1.2.2.1.38.10.7.10.2.5
		shePotsLineTest3ElementInsulationResTestControlTimeStamp OBJECT-TYPE
			SYNTAX Unsigned32
			MAX-ACCESS read-only
			STATUS current
			DESCRIPTION
				"The time stamp of the last command (end of command)."
			::= { shePotsLineTest3ElementInsulationResistanceTestControl 5 }

		
--         1.3.6.1.4.1.231.7.1.2.2.1.38.10.7.10.2.6
		shePotsLineTest3ElementInsulationResTestControlReqResult OBJECT-TYPE
			SYNTAX ShePotsLineTestControlRequestResultType
			MAX-ACCESS read-only
			STATUS current
			DESCRIPTION
				"The result of the last user command."
			::= { shePotsLineTest3ElementInsulationResistanceTestControl 6 }

		
--         1.3.6.1.4.1.231.7.1.2.2.1.38.10.7.10.2.7
		shePotsLineTest3ElementInsulationResTestControlHighImpedanceTest OBJECT-TYPE
			SYNTAX TruthValue
			MAX-ACCESS read-write
			STATUS current
			DESCRIPTION
				"test is in high-impedance mode (TRUE) or low impedance mode (FALSE)
				Default:FALSE, 
				Range: TRUE, FALSE
				
				HighImpedanceTest and measureForeignVI could not be true at the same time.	"
			DEFVAL { false }
			::= { shePotsLineTest3ElementInsulationResistanceTestControl 7 }

		
--         1.3.6.1.4.1.231.7.1.2.2.1.38.10.7.10.2.8
		shePotsLineTest3ElementInsulationResTestControlMeasureForeignVI OBJECT-TYPE
			SYNTAX TruthValue
			MAX-ACCESS read-write
			STATUS current
			DESCRIPTION
				"If set to TRUE this test also performs foreign DC voltage and foreign DC current
				measurement. If set to FALSE it does not perform these measurements.
				HighImpedanceTest and measureForeignVI could not be true at the same time"
			DEFVAL { true }
			::= { shePotsLineTest3ElementInsulationResistanceTestControl 8 }

		
--         1.3.6.1.4.1.231.7.1.2.2.1.38.10.7.11
		shePotsLineTest3ElementInsulationCapacitanceTestGroup OBJECT IDENTIFIER ::= { shePotsLineTestIltfTestGroup 11 }

		
--         1.3.6.1.4.1.231.7.1.2.2.1.38.10.7.11.1
		shePotsLineTest3ElementInsulationCapacitanceTestTable OBJECT-TYPE
			SYNTAX SEQUENCE OF ShePotsLineTest3ElementInsulationCapacitanceTestEntry
			MAX-ACCESS not-accessible
			STATUS current
			DESCRIPTION
				"This test measures tip-to-ground, ring-to-ground, and tip-to-ring Capacitance and impedance.
				This test also returns the foreign AC voltage present on tip and ring."
			::= { shePotsLineTest3ElementInsulationCapacitanceTestGroup 1 }

		
--         1.3.6.1.4.1.231.7.1.2.2.1.38.10.7.11.1.1
		shePotsLineTest3ElementInsulationCapacitanceTestEntry OBJECT-TYPE
			SYNTAX ShePotsLineTest3ElementInsulationCapacitanceTestEntry
			MAX-ACCESS not-accessible
			STATUS current
			DESCRIPTION
				"Entry of shePotsLineTest3ElementInsulationCapacitanceTestTable,
				Each entry is used to represent a line which execute the test."
			INDEX { ifIndex }
			::= { shePotsLineTest3ElementInsulationCapacitanceTestTable 1 }

		
		ShePotsLineTest3ElementInsulationCapacitanceTestEntry ::=
			SEQUENCE { 
				shePotsLineTest3ElementInsulationCapacitanceTestctg
					INTEGER,
				shePotsLineTest3ElemenInsulationtCapacitanceTestcrg
					INTEGER,
				shePotsLineTest3ElementInsulationCapacitanceTestctr
					INTEGER,
				shePotsLineTest3ElementInsulationCapacitanceTestztg
					INTEGER,
				shePotsLineTest3ElementInsulationCapacitanceTestzrg
					INTEGER,
				shePotsLineTest3ElementInsulationCapacitanceTestztr
					INTEGER,
				shePotsLineTest3ElementInsulationCapacitanceTestDegradedAccuracy
					TruthValue,
				shePotsLineTest3ElementInsulationCapacitanceTestvtgAc
					INTEGER,
				shePotsLineTest3ElementInsulationCapacitanceTestvrgAc
					INTEGER,
				shePotsLineTest3ElementInsulationCapacitanceTestTriggerSource
					ShePotsLineTestTriggerType
			 }

--         1.3.6.1.4.1.231.7.1.2.2.1.38.10.7.11.1.1.1
		shePotsLineTest3ElementInsulationCapacitanceTestctg OBJECT-TYPE
			SYNTAX INTEGER
			UNITS "nF"
			MAX-ACCESS read-only
			STATUS current
			DESCRIPTION
				"Tip-to-Ground Capacitance in nFarads x100
				if  ctg>=700000 shoud display as the ctg capacitance could not be measured.
				should display as ctg/100 nF
				"
			::= { shePotsLineTest3ElementInsulationCapacitanceTestEntry 1 }

		
--         1.3.6.1.4.1.231.7.1.2.2.1.38.10.7.11.1.1.2
		shePotsLineTest3ElemenInsulationtCapacitanceTestcrg OBJECT-TYPE
			SYNTAX INTEGER
			UNITS "nF"
			MAX-ACCESS read-only
			STATUS current
			DESCRIPTION
				"Ring-to-Ground Capacitance in nFarads x100
				if  crg>=700000 shoud display as the ctg capacitance could not be measured
				should display as crg/100 nF"
			::= { shePotsLineTest3ElementInsulationCapacitanceTestEntry 2 }

		
--         1.3.6.1.4.1.231.7.1.2.2.1.38.10.7.11.1.1.3
		shePotsLineTest3ElementInsulationCapacitanceTestctr OBJECT-TYPE
			SYNTAX INTEGER
			UNITS "nF"
			MAX-ACCESS read-only
			STATUS current
			DESCRIPTION
				"Tip-to-Ring Capacitance in nFarads x100
				if  ctr>=700000 shoud display as the ctg capacitance could not be measured
				should display as ctr/100 nF"
			::= { shePotsLineTest3ElementInsulationCapacitanceTestEntry 3 }

		
--         1.3.6.1.4.1.231.7.1.2.2.1.38.10.7.11.1.1.4
		shePotsLineTest3ElementInsulationCapacitanceTestztg OBJECT-TYPE
			SYNTAX INTEGER
			UNITS "Ohm"
			MAX-ACCESS read-only
			STATUS current
			DESCRIPTION
				"Tip-to-Ground impedance (Ohms).
				However, this output should not be shown to users."
			::= { shePotsLineTest3ElementInsulationCapacitanceTestEntry 4 }

		
--         1.3.6.1.4.1.231.7.1.2.2.1.38.10.7.11.1.1.5
		shePotsLineTest3ElementInsulationCapacitanceTestzrg OBJECT-TYPE
			SYNTAX INTEGER
			UNITS "Ohm"
			MAX-ACCESS read-only
			STATUS current
			DESCRIPTION
				"Ring-to-Ground impedance (Ohms).
				However, this output should not be shown to users."
			::= { shePotsLineTest3ElementInsulationCapacitanceTestEntry 5 }

		
--         1.3.6.1.4.1.231.7.1.2.2.1.38.10.7.11.1.1.6
		shePotsLineTest3ElementInsulationCapacitanceTestztr OBJECT-TYPE
			SYNTAX INTEGER
			MAX-ACCESS read-only
			STATUS current
			DESCRIPTION
				"Tip-to-Ring impedance (Ohms).
				However, this output should not be shown to users."
			::= { shePotsLineTest3ElementInsulationCapacitanceTestEntry 6 }

		
--         1.3.6.1.4.1.231.7.1.2.2.1.38.10.7.11.1.1.7
		shePotsLineTest3ElementInsulationCapacitanceTestDegradedAccuracy OBJECT-TYPE
			SYNTAX TruthValue
			MAX-ACCESS read-only
			STATUS current
			DESCRIPTION
				"If set to TRUE this flag indicates that the accuracy
				of the measured capacitance is degraded because of the low 
				leakage resistance.
				However, this output should not be shown to users."
			::= { shePotsLineTest3ElementInsulationCapacitanceTestEntry 7 }

		
--         1.3.6.1.4.1.231.7.1.2.2.1.38.10.7.11.1.1.8
		shePotsLineTest3ElementInsulationCapacitanceTestvtgAc OBJECT-TYPE
			SYNTAX INTEGER
			UNITS "V"
			MAX-ACCESS read-only
			STATUS current
			DESCRIPTION
				"Foreign AC Tip to ground voltage in Vrms x100
				However, this output should not be shown to users."
			::= { shePotsLineTest3ElementInsulationCapacitanceTestEntry 8 }

		
--         1.3.6.1.4.1.231.7.1.2.2.1.38.10.7.11.1.1.9
		shePotsLineTest3ElementInsulationCapacitanceTestvrgAc OBJECT-TYPE
			SYNTAX INTEGER
			UNITS "V"
			MAX-ACCESS read-only
			STATUS current
			DESCRIPTION
				"Foreign AC Ring to ground voltage in Vrms x100
				However, this output should not be shown to users."
			::= { shePotsLineTest3ElementInsulationCapacitanceTestEntry 9 }

		
--         1.3.6.1.4.1.231.7.1.2.2.1.38.10.7.11.1.1.11
		shePotsLineTest3ElementInsulationCapacitanceTestTriggerSource OBJECT-TYPE
			SYNTAX ShePotsLineTestTriggerType
			MAX-ACCESS read-only
			STATUS current
			DESCRIPTION
				"Test Trigger Source."
			::= { shePotsLineTest3ElementInsulationCapacitanceTestEntry 10 }

		
--         1.3.6.1.4.1.231.7.1.2.2.1.38.10.7.11.2
		shePotsLineTest3ElementInsulationCapacitanceTestControl OBJECT IDENTIFIER ::= { shePotsLineTest3ElementInsulationCapacitanceTestGroup 2 }

		
--         1.3.6.1.4.1.231.7.1.2.2.1.38.10.7.11.2.1
		shePotsLineTest3ElementInsulationCapacitanceTestControlRequest OBJECT-TYPE
			SYNTAX ShePotsLineTestControlRequestType
			MAX-ACCESS read-write
			STATUS current
			DESCRIPTION
				"User command.
				set3ElementInsulationCapacitanceTest:
				shePotsLineTest3ElementInsulationCapacitanceTestControlIndex
				shePotsLineTest3ElementInsulationCapacitanceTestControlvDiffMax
				
				
				Long-running Command"
			::= { shePotsLineTest3ElementInsulationCapacitanceTestControl 1 }

		
--         1.3.6.1.4.1.231.7.1.2.2.1.38.10.7.11.2.2
		shePotsLineTest3ElementInsulationCapacitanceTestControlIndex OBJECT-TYPE
			SYNTAX InterfaceIndex
			MAX-ACCESS read-write
			STATUS current
			DESCRIPTION
				"The IfIndex of the line which test shall be executed"
			::= { shePotsLineTest3ElementInsulationCapacitanceTestControl 2 }

		
--         1.3.6.1.4.1.231.7.1.2.2.1.38.10.7.11.2.3
		shePotsLineTest3ElementInsulationCapacitanceTestControlStatus OBJECT-TYPE
			SYNTAX SheControlStatusType
			MAX-ACCESS read-only
			STATUS current
			DESCRIPTION
				"The status of a user command"
			::= { shePotsLineTest3ElementInsulationCapacitanceTestControl 3 }

		
--         1.3.6.1.4.1.231.7.1.2.2.1.38.10.7.11.2.4
		shePotsLineTest3ElementInsulationCapacitanceTesControlTimer OBJECT-TYPE
			SYNTAX Gauge32
			MAX-ACCESS read-only
			STATUS current
			DESCRIPTION
				"The maximum wait time for the manager for a long running user command."
			::= { shePotsLineTest3ElementInsulationCapacitanceTestControl 4 }

		
--         1.3.6.1.4.1.231.7.1.2.2.1.38.10.7.11.2.5
		shePotsLineTest3ElementInsulationCapacitanceTestControlTimeStamp OBJECT-TYPE
			SYNTAX Unsigned32
			MAX-ACCESS read-only
			STATUS current
			DESCRIPTION
				"The time stamp of the last command (end of command)."
			::= { shePotsLineTest3ElementInsulationCapacitanceTestControl 5 }

		
--         1.3.6.1.4.1.231.7.1.2.2.1.38.10.7.11.2.6
		shePotsLineTest3ElementInsulationCapacitanceTestControlReqResult OBJECT-TYPE
			SYNTAX ShePotsLineTestControlRequestResultType
			MAX-ACCESS read-only
			STATUS current
			DESCRIPTION
				"The result of the last user command."
			::= { shePotsLineTest3ElementInsulationCapacitanceTestControl 6 }

		
--         1.3.6.1.4.1.231.7.1.2.2.1.38.10.7.11.2.7
		shePotsLineTest3ElementInsulationCapacitanceTestControlvDiffMax OBJECT-TYPE
			SYNTAX INTEGER (5..40)
			UNITS "V"
			MAX-ACCESS read-write
			STATUS current
			DESCRIPTION
				"Maximum peak differential voltage applied  during this test (in mV)."
			DEFVAL { 20 }
			::= { shePotsLineTest3ElementInsulationCapacitanceTestControl 7 }

		
--         1.3.6.1.4.1.231.7.1.2.2.1.38.10.7.12
		shePotsLineTestReceiverOffHookTestGroup OBJECT IDENTIFIER ::= { shePotsLineTestIltfTestGroup 12 }

		
--         1.3.6.1.4.1.231.7.1.2.2.1.38.10.7.12.1
		shePotsLineTestReceiverOffHookTestTable OBJECT-TYPE
			SYNTAX SEQUENCE OF ShePotsLineTestReceiverOffHookTestEntry
			MAX-ACCESS not-accessible
			STATUS current
			DESCRIPTION
				"This test determines whether the receiver is off-hook by running the DC Loop Resistance
				Test twice with different test currents and analyzing the results."
			::= { shePotsLineTestReceiverOffHookTestGroup 1 }

		
--         1.3.6.1.4.1.231.7.1.2.2.1.38.10.7.12.1.1
		shePotsLineTestReceiverOffHookTestEntry OBJECT-TYPE
			SYNTAX ShePotsLineTestReceiverOffHookTestEntry
			MAX-ACCESS not-accessible
			STATUS current
			DESCRIPTION
				"Entry of shePotsLineTestReceiverOffHookTestTable,
				Each entry is used to represent a card which execute the test."
			INDEX { ifIndex }
			::= { shePotsLineTestReceiverOffHookTestTable 1 }

		
		ShePotsLineTestReceiverOffHookTestEntry ::=
			SEQUENCE { 
				shePotsLineTestReceiverOffHookTestReceiverOffHook
					TruthValue,
				shePotsLineTestReceiverOffHookTestrLoopOutOfRange
					TruthValue,
				shePotsLineTestReceiverOffHookTestTriggerSource
					ShePotsLineTestTriggerType
			 }

--         1.3.6.1.4.1.231.7.1.2.2.1.38.10.7.12.1.1.1
		shePotsLineTestReceiverOffHookTestReceiverOffHook OBJECT-TYPE
			SYNTAX TruthValue
			MAX-ACCESS read-only
			STATUS current
			DESCRIPTION
				"If set to TRUE indicates receiver off-hook has been detected. 
				If set to FALSE it indicates a short circuit of the line. 
				Receiverofhook   Rloopoutofrange
				     0              0:           the line has real loop resistance but not in hook off situation;
				     1              0:           the real hook off situation;
				     0              1:           hook on situation;
				     1              1:           test failed to return any result. 
				"
			::= { shePotsLineTestReceiverOffHookTestEntry 1 }

		
--         1.3.6.1.4.1.231.7.1.2.2.1.38.10.7.12.1.1.2
		shePotsLineTestReceiverOffHookTestrLoopOutOfRange OBJECT-TYPE
			SYNTAX TruthValue
			MAX-ACCESS read-only
			STATUS current
			DESCRIPTION
				"whether loop resistance is out of range   
				Receiverofhook   Rloopoutofrange
				     0              0:           the line has real loop resistance but not in hook off situation;
				     1              0:           the real hook off situation;
				     0              1:           hook on situation;
				     1              1:           test failed to return any result. 
				"
			::= { shePotsLineTestReceiverOffHookTestEntry 2 }

		
--         1.3.6.1.4.1.231.7.1.2.2.1.38.10.7.12.1.1.3
		shePotsLineTestReceiverOffHookTestTriggerSource OBJECT-TYPE
			SYNTAX ShePotsLineTestTriggerType
			MAX-ACCESS read-only
			STATUS current
			DESCRIPTION
				"Test Trigger Source."
			::= { shePotsLineTestReceiverOffHookTestEntry 3 }

		
--         1.3.6.1.4.1.231.7.1.2.2.1.38.10.7.12.2
		shePotsLineTestReceiverOffHookTestControl OBJECT IDENTIFIER ::= { shePotsLineTestReceiverOffHookTestGroup 2 }

		
--         1.3.6.1.4.1.231.7.1.2.2.1.38.10.7.12.2.1
		shePotsLineTestReceiverOffHookTestControlRequest OBJECT-TYPE
			SYNTAX ShePotsLineTestControlRequestType
			MAX-ACCESS read-write
			STATUS current
			DESCRIPTION
				"User command.
				setReceiverOffHookTest:
				shePotsLineTestReceiverOffHookTestControlIndex
				
				
				Long-running Command"
			::= { shePotsLineTestReceiverOffHookTestControl 1 }

		
--         1.3.6.1.4.1.231.7.1.2.2.1.38.10.7.12.2.2
		shePotsLineTestReceiverOffHookTestControlIndex OBJECT-TYPE
			SYNTAX InterfaceIndex
			MAX-ACCESS read-write
			STATUS current
			DESCRIPTION
				"The IfIndex of the line which test shall be executed"
			::= { shePotsLineTestReceiverOffHookTestControl 2 }

		
--         1.3.6.1.4.1.231.7.1.2.2.1.38.10.7.12.2.3
		shePotsLineTestReceiverOffHookTestControlStatus OBJECT-TYPE
			SYNTAX SheControlStatusType
			MAX-ACCESS read-only
			STATUS current
			DESCRIPTION
				"The status of a user command"
			::= { shePotsLineTestReceiverOffHookTestControl 3 }

		
--         1.3.6.1.4.1.231.7.1.2.2.1.38.10.7.12.2.4
		shePotsLineTestReceiverOffHookTestControlTimer OBJECT-TYPE
			SYNTAX Gauge32
			MAX-ACCESS read-only
			STATUS current
			DESCRIPTION
				"The maximum wait time for the manager for a long running user command."
			::= { shePotsLineTestReceiverOffHookTestControl 4 }

		
--         1.3.6.1.4.1.231.7.1.2.2.1.38.10.7.12.2.5
		shePotsLineTestReceiverOffHookTestControlTimeStamp OBJECT-TYPE
			SYNTAX Unsigned32
			MAX-ACCESS read-only
			STATUS current
			DESCRIPTION
				"The time stamp of the last command (end of command)."
			::= { shePotsLineTestReceiverOffHookTestControl 5 }

		
--         1.3.6.1.4.1.231.7.1.2.2.1.38.10.7.12.2.6
		shePotsLineTestReceiverOffHookTestControlReqResult OBJECT-TYPE
			SYNTAX ShePotsLineTestControlRequestResultType
			MAX-ACCESS read-only
			STATUS current
			DESCRIPTION
				"The result of the last user command."
			::= { shePotsLineTestReceiverOffHookTestControl 6 }

		
--         1.3.6.1.4.1.231.7.1.2.2.1.38.10.7.13
		shePotsLineTestDistanceToOpenTestGroup OBJECT IDENTIFIER ::= { shePotsLineTestIltfTestGroup 13 }

		
--         1.3.6.1.4.1.231.7.1.2.2.1.38.10.7.13.1
		shePotsLineTestDistanceToOpenTestTable OBJECT-TYPE
			SYNTAX SEQUENCE OF ShePotsLineTestDistanceToOpenTestEntry
			MAX-ACCESS not-accessible
			STATUS current
			DESCRIPTION
				"This test estimates the distance to an open-circuit by analyzing the results of a Three-
				Element Insulation Resistance Test and a Three-Element Capacitance Test."
			::= { shePotsLineTestDistanceToOpenTestGroup 1 }

		
--         1.3.6.1.4.1.231.7.1.2.2.1.38.10.7.13.1.1
		shePotsLineTestDistanceToOpenTestEntry OBJECT-TYPE
			SYNTAX ShePotsLineTestDistanceToOpenTestEntry
			MAX-ACCESS not-accessible
			STATUS current
			DESCRIPTION
				"Entry of shePotsLineTestDistanceToOpenTestTable,
				Each entry is used to represent a line which execute the test."
			INDEX { ifIndex }
			::= { shePotsLineTestDistanceToOpenTestTable 1 }

		
		ShePotsLineTestDistanceToOpenTestEntry ::=
			SEQUENCE { 
				shePotsLineTestDistanceToOpenTestDistanceToOpen
					INTEGER,
				shePotsLineTestDistanceToOpenTestExcessiveLeakage
					TruthValue,
				shePotsLineTestDistanceToOpenTestCapacitanceTestFailed
					TruthValue,
				shePotsLineTestDistanceToOpenTestTriggerSource
					ShePotsLineTestTriggerType
			 }

--         1.3.6.1.4.1.231.7.1.2.2.1.38.10.7.13.1.1.1
		shePotsLineTestDistanceToOpenTestDistanceToOpen OBJECT-TYPE
			SYNTAX INTEGER
			UNITS "meter"
			MAX-ACCESS read-only
			STATUS current
			DESCRIPTION
				"To estimate the distance o the open circuit in meters x100
				should display as DistanceToOpen/100"
			::= { shePotsLineTestDistanceToOpenTestEntry 1 }

		
--         1.3.6.1.4.1.231.7.1.2.2.1.38.10.7.13.1.1.2
		shePotsLineTestDistanceToOpenTestExcessiveLeakage OBJECT-TYPE
			SYNTAX TruthValue
			MAX-ACCESS read-only
			STATUS current
			DESCRIPTION
				"set to TRUE if the test failed to complete.
				However, this output should not be shown to users."
			::= { shePotsLineTestDistanceToOpenTestEntry 2 }

		
--         1.3.6.1.4.1.231.7.1.2.2.1.38.10.7.13.1.1.3
		shePotsLineTestDistanceToOpenTestCapacitanceTestFailed OBJECT-TYPE
			SYNTAX TruthValue
			MAX-ACCESS read-only
			STATUS current
			DESCRIPTION
				"set to TRUE if the test failed to complete.
				However, this output should not be shown to users."
			::= { shePotsLineTestDistanceToOpenTestEntry 3 }

		
--         1.3.6.1.4.1.231.7.1.2.2.1.38.10.7.13.1.1.5
		shePotsLineTestDistanceToOpenTestTriggerSource OBJECT-TYPE
			SYNTAX ShePotsLineTestTriggerType
			MAX-ACCESS read-only
			STATUS current
			DESCRIPTION
				"Test Trigger Source."
			::= { shePotsLineTestDistanceToOpenTestEntry 4 }

		
--         1.3.6.1.4.1.231.7.1.2.2.1.38.10.7.13.2
		shePotsLineTestDistanceToOpenTestControl OBJECT IDENTIFIER ::= { shePotsLineTestDistanceToOpenTestGroup 2 }

		
--         1.3.6.1.4.1.231.7.1.2.2.1.38.10.7.13.2.1
		shePotsLineTestDistanceToOpenTestControlRequest OBJECT-TYPE
			SYNTAX ShePotsLineTestControlRequestType
			MAX-ACCESS read-write
			STATUS current
			DESCRIPTION
				"User command
				setDistanceToOpenTest:
				shePotsLineTestDistanceToOpenTestControlIndex
				
				
				Long-running Command
				"
			::= { shePotsLineTestDistanceToOpenTestControl 1 }

		
--         1.3.6.1.4.1.231.7.1.2.2.1.38.10.7.13.2.2
		shePotsLineTestDistanceToOpenTestControlIndex OBJECT-TYPE
			SYNTAX InterfaceIndex
			MAX-ACCESS read-write
			STATUS current
			DESCRIPTION
				"The IfIndex of the line which test shall be executed"
			::= { shePotsLineTestDistanceToOpenTestControl 2 }

		
--         1.3.6.1.4.1.231.7.1.2.2.1.38.10.7.13.2.3
		shePotsLineTestDistanceToOpenTestControlStatus OBJECT-TYPE
			SYNTAX SheControlStatusType
			MAX-ACCESS read-only
			STATUS current
			DESCRIPTION
				"The maximum wait time for the manager for a long running user command."
			::= { shePotsLineTestDistanceToOpenTestControl 3 }

		
--         1.3.6.1.4.1.231.7.1.2.2.1.38.10.7.13.2.4
		shePotsLineTestDistanceToOpenTestControlTimer OBJECT-TYPE
			SYNTAX Gauge32
			MAX-ACCESS read-only
			STATUS current
			DESCRIPTION
				"The maximum wait time for the manager for a long running user command."
			::= { shePotsLineTestDistanceToOpenTestControl 4 }

		
--         1.3.6.1.4.1.231.7.1.2.2.1.38.10.7.13.2.5
		shePotsLineTestDistanceToOpenTestControlTimeStamp OBJECT-TYPE
			SYNTAX Unsigned32
			MAX-ACCESS read-only
			STATUS current
			DESCRIPTION
				"The time stamp of the last command (end of command)."
			::= { shePotsLineTestDistanceToOpenTestControl 5 }

		
--         1.3.6.1.4.1.231.7.1.2.2.1.38.10.7.13.2.6
		shePotsLineTestDistanceToOpenTestControlReqResult OBJECT-TYPE
			SYNTAX ShePotsLineTestControlRequestResultType
			MAX-ACCESS read-only
			STATUS current
			DESCRIPTION
				"The result of the last user command."
			::= { shePotsLineTestDistanceToOpenTestControl 6 }

		
--         1.3.6.1.4.1.231.7.1.2.2.1.38.10.7.14
		shePotsLineTestRingerEquivalencyNumberTestGroup OBJECT IDENTIFIER ::= { shePotsLineTestIltfTestGroup 14 }

		
--         1.3.6.1.4.1.231.7.1.2.2.1.38.10.7.14.1
		shePotsLineTestRingerEquivalencyNumberTestTable OBJECT-TYPE
			SYNTAX SEQUENCE OF ShePotsLineTestRingerEquivalencyNumberTestEntry
			MAX-ACCESS not-accessible
			STATUS current
			DESCRIPTION
				"This test calculates the Ringer Equivalency Number (REN) for the telephone attached to the
				line. The test supports both the regular and electronic phone REN measurement techniques."
			::= { shePotsLineTestRingerEquivalencyNumberTestGroup 1 }

		
--         1.3.6.1.4.1.231.7.1.2.2.1.38.10.7.14.1.1
		shePotsLineTestRingerEquivalencyNumberTestEntry OBJECT-TYPE
			SYNTAX ShePotsLineTestRingerEquivalencyNumberTestEntry
			MAX-ACCESS not-accessible
			STATUS current
			DESCRIPTION
				"Entry of shePotsLineTestRingerEquivalencyNumberTestTable,
				Each entry is used to represent a line which execute the test."
			INDEX { ifIndex }
			::= { shePotsLineTestRingerEquivalencyNumberTestTable 1 }

		
		ShePotsLineTestRingerEquivalencyNumberTestEntry ::=
			SEQUENCE { 
				shePotsLineTestRingerEquivalencyNumberTestRen
					INTEGER,
				shePotsLineTestRingerEquivalencyNumberTestTriggerSource
					ShePotsLineTestTriggerType
			 }

--         1.3.6.1.4.1.231.7.1.2.2.1.38.10.7.14.1.1.1
		shePotsLineTestRingerEquivalencyNumberTestRen OBJECT-TYPE
			SYNTAX INTEGER
			MAX-ACCESS read-only
			STATUS current
			DESCRIPTION
				" reports the measured Ringer Equivalency Number(ren x100)
				should display as ren/100"
			::= { shePotsLineTestRingerEquivalencyNumberTestEntry 1 }

		
--         1.3.6.1.4.1.231.7.1.2.2.1.38.10.7.14.1.1.5
		shePotsLineTestRingerEquivalencyNumberTestTriggerSource OBJECT-TYPE
			SYNTAX ShePotsLineTestTriggerType
			MAX-ACCESS read-only
			STATUS current
			DESCRIPTION
				"Test Trigger Source."
			::= { shePotsLineTestRingerEquivalencyNumberTestEntry 2 }

		
--         1.3.6.1.4.1.231.7.1.2.2.1.38.10.7.14.2
		shePotsLineTestRingerEquivalencyNumberTestControl OBJECT IDENTIFIER ::= { shePotsLineTestRingerEquivalencyNumberTestGroup 2 }

		
--         1.3.6.1.4.1.231.7.1.2.2.1.38.10.7.14.2.1
		shePotsLineTestRingerEquivalencyNumberTestControlRequest OBJECT-TYPE
			SYNTAX ShePotsLineTestControlRequestType
			MAX-ACCESS read-write
			STATUS current
			DESCRIPTION
				"User command.
				setRingerEquivalencyNumberTest:
				shePotsLineTestRingerEquivalencyNumberTestControlIndex
				shePotsLineTestRingerEquivalencyNumberTestControlRentestType
				
				
				Long-running Command
				
				"
			::= { shePotsLineTestRingerEquivalencyNumberTestControl 1 }

		
--         1.3.6.1.4.1.231.7.1.2.2.1.38.10.7.14.2.2
		shePotsLineTestRingerEquivalencyNumberTestControlIndex OBJECT-TYPE
			SYNTAX InterfaceIndex
			MAX-ACCESS read-write
			STATUS current
			DESCRIPTION
				"The IfIndex of the line which test shall be executed"
			::= { shePotsLineTestRingerEquivalencyNumberTestControl 2 }

		
--         1.3.6.1.4.1.231.7.1.2.2.1.38.10.7.14.2.3
		shePotsLineTestRingerEquivalencyNumberTestControlStatus OBJECT-TYPE
			SYNTAX SheControlStatusType
			MAX-ACCESS read-only
			STATUS current
			DESCRIPTION
				"The status of a user command"
			::= { shePotsLineTestRingerEquivalencyNumberTestControl 3 }

		
--         1.3.6.1.4.1.231.7.1.2.2.1.38.10.7.14.2.4
		shePotsLineTestRingerEquivalencyNumberTestControlTimer OBJECT-TYPE
			SYNTAX Gauge32
			MAX-ACCESS read-only
			STATUS current
			DESCRIPTION
				"The maximum wait time for the manager for a long running user command."
			::= { shePotsLineTestRingerEquivalencyNumberTestControl 4 }

		
--         1.3.6.1.4.1.231.7.1.2.2.1.38.10.7.14.2.5
		shePotsLineTestRingerEquivalencyNumberTestControlTimeStamp OBJECT-TYPE
			SYNTAX Unsigned32
			MAX-ACCESS read-only
			STATUS current
			DESCRIPTION
				"The time stamp of the last command (end of command)."
			::= { shePotsLineTestRingerEquivalencyNumberTestControl 5 }

		
--         1.3.6.1.4.1.231.7.1.2.2.1.38.10.7.14.2.6
		shePotsLineTestRingerEquivalencyNumberTestControlReqResult OBJECT-TYPE
			SYNTAX ShePotsLineTestControlRequestResultType
			MAX-ACCESS read-only
			STATUS current
			DESCRIPTION
				"The result of the last user command."
			::= { shePotsLineTestRingerEquivalencyNumberTestControl 6 }

		
--         1.3.6.1.4.1.231.7.1.2.2.1.38.10.7.14.2.7
		shePotsLineTestRingerEquivalencyNumberTestControlRentestType OBJECT-TYPE
			SYNTAX ShePotsLineTestRingerEquivalencyNumberTestControlRentestType
			MAX-ACCESS read-write
			STATUS current
			DESCRIPTION
				"vPTLRenRegularPhoneTest(0),
				vPTLRenElectronicPhoneTest(1)
				Default: 1 vPTLRenElectronicPhoneTest
				"
			DEFVAL { vPTLRenElectronicPhoneTest }
			::= { shePotsLineTestRingerEquivalencyNumberTestControl 7 }

		
--         1.3.6.1.4.1.231.7.1.2.2.1.38.10.7.15
		shePotsLineTestDTMFandPulseDigitMeasurTestGroup OBJECT IDENTIFIER ::= { shePotsLineTestIltfTestGroup 15 }

		
--         1.3.6.1.4.1.231.7.1.2.2.1.38.10.7.15.1
		shePotsLineTestDTMFandPulseDigitMeasureTestTable OBJECT-TYPE
			SYNTAX SEQUENCE OF ShePotsLineTestDTMFandPulseDigitMeasureTestEntry
			MAX-ACCESS not-accessible
			STATUS current
			DESCRIPTION
				"This test detects and measures a DTMF digit, pulse digit, or hook-switch flash. Only one
				digit or flash is reported for each invocation of this test. By default, a single tone is output on
				the line during this test."
			::= { shePotsLineTestDTMFandPulseDigitMeasurTestGroup 1 }

		
--         1.3.6.1.4.1.231.7.1.2.2.1.38.10.7.15.1.1
		shePotsLineTestDTMFandPulseDigitMeasureTestEntry OBJECT-TYPE
			SYNTAX ShePotsLineTestDTMFandPulseDigitMeasureTestEntry
			MAX-ACCESS not-accessible
			STATUS current
			DESCRIPTION
				"Entry of shePotsLineTestDTMFandPulseDigitMeasureTestTable,
				Each entry is used to represent a line which execute the test."
			INDEX { ifIndex }
			::= { shePotsLineTestDTMFandPulseDigitMeasureTestTable 1 }

		
		ShePotsLineTestDTMFandPulseDigitMeasureTestEntry ::=
			SEQUENCE { 
				shePotsLineTestDTMFandPulseDigitMeasureTestTimeout
					TruthValue,
				shePotsLineTestDTMFandPulseDigitMeasureTestDisconnectDetected
					TruthValue,
				shePotsLineTestDTMFandPulseDigitMeasureTestkTestResult
					ShePotsLineTestDTMFandPulseDigitMeasureTestkTestResultType,
				shePotsLineTestDTMFandPulseDigitMeasureTestDigit
					ShePotsLineTestVpDigitType,
				shePotsLineTestDTMFandPulseDigitMeasureTestHookFlashOk
					TruthValue,
				shePotsLineTestDTMFandPulseDigitMeasureTestFlash
					INTEGER,
				shePotsLineTestDTMFandPulseDigitMeasureTestFreq0
					INTEGER,
				shePotsLineTestDTMFandPulseDigitMeasureTestLevel0
					INTEGER,
				shePotsLineTestDTMFandPulseDigitMeasureTestFreq1
					INTEGER,
				shePotsLineTestDTMFandPulseDigitMeasureTestLevel1
					INTEGER,
				shePotsLineTestDTMFandPulseDigitMeasureTestFftSize
					INTEGER,
				shePotsLineTestDTMFandPulseDigitMeasureTestMinBreak
					INTEGER,
				shePotsLineTestDTMFandPulseDigitMeasureTestMaxBreak
					INTEGER,
				shePotsLineTestDTMFandPulseDigitMeasureTestAvgBreak
					INTEGER,
				shePotsLineTestDTMFandPulseDigitMeasureTestPps
					INTEGER,
				shePotsLineTestDTMFandPulseDigitMeasureTestTriggerSource
					ShePotsLineTestTriggerType
			 }

--         1.3.6.1.4.1.231.7.1.2.2.1.38.10.7.15.1.1.1
		shePotsLineTestDTMFandPulseDigitMeasureTestTimeout OBJECT-TYPE
			SYNTAX TruthValue
			MAX-ACCESS read-only
			STATUS current
			DESCRIPTION
				"If set to TRUE the test timed out without detecting anything"
			::= { shePotsLineTestDTMFandPulseDigitMeasureTestEntry 1 }

		
--         1.3.6.1.4.1.231.7.1.2.2.1.38.10.7.15.1.1.2
		shePotsLineTestDTMFandPulseDigitMeasureTestDisconnectDetected OBJECT-TYPE
			SYNTAX TruthValue
			MAX-ACCESS read-only
			STATUS current
			DESCRIPTION
				"If set to TRUE the on-hook detected while performing the test. 
				The following results are valid only if the above two flags are set to FALSE"
			::= { shePotsLineTestDTMFandPulseDigitMeasureTestEntry 2 }

		
--         1.3.6.1.4.1.231.7.1.2.2.1.38.10.7.15.1.1.3
		shePotsLineTestDTMFandPulseDigitMeasureTestkTestResult OBJECT-TYPE
			SYNTAX ShePotsLineTestDTMFandPulseDigitMeasureTestkTestResultType
			MAX-ACCESS read-only
			STATUS current
			DESCRIPTION
				"vPKtDtmfDet(0),
				vPKtDtmfMes(1),
				vPKtPulse(2),
				vPKtThreshDet(3)"
			::= { shePotsLineTestDTMFandPulseDigitMeasureTestEntry 3 }

		
--         1.3.6.1.4.1.231.7.1.2.2.1.38.10.7.15.1.1.4
		shePotsLineTestDTMFandPulseDigitMeasureTestDigit OBJECT-TYPE
			SYNTAX ShePotsLineTestVpDigitType
			MAX-ACCESS read-only
			STATUS current
			DESCRIPTION
				"the detected digit
				        null(0),
					vpDIG1(1),
					vpDIG2(2),
					vpDIG3(3),
					vpDIG4(4),
					vpDIG5(5),
					vpDIG6(6),
					vpDIG7(7),
					vpDIG8(8),
					vpDIG9(9),
					vDIGZero(10),
					vpDIGAster(11),
					vpDIGPound(12),
					vDIGA(13),
					vDIGB(14),
					vDIGC(15),
					vDIGD(16),
					vDIGNone(17)"
			::= { shePotsLineTestDTMFandPulseDigitMeasureTestEntry 4 }

		
--         1.3.6.1.4.1.231.7.1.2.2.1.38.10.7.15.1.1.5
		shePotsLineTestDTMFandPulseDigitMeasureTestHookFlashOk OBJECT-TYPE
			SYNTAX TruthValue
			MAX-ACCESS read-only
			STATUS current
			DESCRIPTION
				"If set to TRUE, Hook flash detected"
			::= { shePotsLineTestDTMFandPulseDigitMeasureTestEntry 5 }

		
--         1.3.6.1.4.1.231.7.1.2.2.1.38.10.7.15.1.1.6
		shePotsLineTestDTMFandPulseDigitMeasureTestFlash OBJECT-TYPE
			SYNTAX INTEGER
			UNITS "sec"
			MAX-ACCESS read-only
			STATUS current
			DESCRIPTION
				"the duration of a hook flash in Seconds x 100
				should display as Flash/100 sec"
			::= { shePotsLineTestDTMFandPulseDigitMeasureTestEntry 6 }

		
--         1.3.6.1.4.1.231.7.1.2.2.1.38.10.7.15.1.1.7
		shePotsLineTestDTMFandPulseDigitMeasureTestFreq0 OBJECT-TYPE
			SYNTAX INTEGER
			UNITS "Hz"
			MAX-ACCESS read-only
			STATUS current
			DESCRIPTION
				"Frequency in Hertz ."
			::= { shePotsLineTestDTMFandPulseDigitMeasureTestEntry 7 }

		
--         1.3.6.1.4.1.231.7.1.2.2.1.38.10.7.15.1.1.8
		shePotsLineTestDTMFandPulseDigitMeasureTestLevel0 OBJECT-TYPE
			SYNTAX INTEGER
			UNITS "dBm0"
			MAX-ACCESS read-only
			STATUS current
			DESCRIPTION
				"Power referenced to the 0 TLP, in dBm0 ."
			::= { shePotsLineTestDTMFandPulseDigitMeasureTestEntry 8 }

		
--         1.3.6.1.4.1.231.7.1.2.2.1.38.10.7.15.1.1.9
		shePotsLineTestDTMFandPulseDigitMeasureTestFreq1 OBJECT-TYPE
			SYNTAX INTEGER
			UNITS "Hz"
			MAX-ACCESS read-only
			STATUS current
			DESCRIPTION
				"Frequency in Hertz ."
			::= { shePotsLineTestDTMFandPulseDigitMeasureTestEntry 9 }

		
--         1.3.6.1.4.1.231.7.1.2.2.1.38.10.7.15.1.1.10
		shePotsLineTestDTMFandPulseDigitMeasureTestLevel1 OBJECT-TYPE
			SYNTAX INTEGER
			UNITS "dBm0"
			MAX-ACCESS read-only
			STATUS current
			DESCRIPTION
				"Power referenced to the 0 TLP, in dBm0 ."
			::= { shePotsLineTestDTMFandPulseDigitMeasureTestEntry 10 }

		
--         1.3.6.1.4.1.231.7.1.2.2.1.38.10.7.15.1.1.11
		shePotsLineTestDTMFandPulseDigitMeasureTestFftSize OBJECT-TYPE
			SYNTAX INTEGER (0..65535)
			MAX-ACCESS read-only
			STATUS current
			DESCRIPTION
				"Indicates the FFT size"
			::= { shePotsLineTestDTMFandPulseDigitMeasureTestEntry 11 }

		
--         1.3.6.1.4.1.231.7.1.2.2.1.38.10.7.15.1.1.12
		shePotsLineTestDTMFandPulseDigitMeasureTestMinBreak OBJECT-TYPE
			SYNTAX INTEGER (0..65535)
			UNITS "0.1 sec"
			MAX-ACCESS read-only
			STATUS current
			DESCRIPTION
				"Minimum break time ."
			::= { shePotsLineTestDTMFandPulseDigitMeasureTestEntry 12 }

		
--         1.3.6.1.4.1.231.7.1.2.2.1.38.10.7.15.1.1.13
		shePotsLineTestDTMFandPulseDigitMeasureTestMaxBreak OBJECT-TYPE
			SYNTAX INTEGER (0..65535)
			UNITS "0.1 sec"
			MAX-ACCESS read-only
			STATUS current
			DESCRIPTION
				"Maximum break time."
			::= { shePotsLineTestDTMFandPulseDigitMeasureTestEntry 13 }

		
--         1.3.6.1.4.1.231.7.1.2.2.1.38.10.7.15.1.1.14
		shePotsLineTestDTMFandPulseDigitMeasureTestAvgBreak OBJECT-TYPE
			SYNTAX INTEGER (0..65535)
			UNITS "0.1 sec"
			MAX-ACCESS read-only
			STATUS current
			DESCRIPTION
				"Average break time."
			::= { shePotsLineTestDTMFandPulseDigitMeasureTestEntry 14 }

		
--         1.3.6.1.4.1.231.7.1.2.2.1.38.10.7.15.1.1.15
		shePotsLineTestDTMFandPulseDigitMeasureTestPps OBJECT-TYPE
			SYNTAX INTEGER
			MAX-ACCESS read-only
			STATUS current
			DESCRIPTION
				"Pulse per second"
			::= { shePotsLineTestDTMFandPulseDigitMeasureTestEntry 15 }

		
--         1.3.6.1.4.1.231.7.1.2.2.1.38.10.7.15.1.1.16
		shePotsLineTestDTMFandPulseDigitMeasureTestTriggerSource OBJECT-TYPE
			SYNTAX ShePotsLineTestTriggerType
			MAX-ACCESS read-only
			STATUS current
			DESCRIPTION
				"Test Trigger Source."
			::= { shePotsLineTestDTMFandPulseDigitMeasureTestEntry 16 }

		
--         1.3.6.1.4.1.231.7.1.2.2.1.38.10.7.15.2
		shePotsLineTestDTMFandPulseDigitMeasureTestControl OBJECT IDENTIFIER ::= { shePotsLineTestDTMFandPulseDigitMeasurTestGroup 2 }

		
--         1.3.6.1.4.1.231.7.1.2.2.1.38.10.7.15.2.1
		shePotsLineTestDTMFandPulseDigitMeasureTestControlRequest OBJECT-TYPE
			SYNTAX ShePotsLineTestControlRequestType
			MAX-ACCESS read-write
			STATUS current
			DESCRIPTION
				"User command.
				setDTMFandPulseDigitMeasureTest:
				shePotsLineTestDTMFandPulseDigitMeasureTestControlIndex
				shePotsLineTestDTMFandPulseDigitMeasureTestControlTestType
				
				
				Long-running Command"
			::= { shePotsLineTestDTMFandPulseDigitMeasureTestControl 1 }

		
--         1.3.6.1.4.1.231.7.1.2.2.1.38.10.7.15.2.2
		shePotsLineTestDTMFandPulseDigitMeasureTestControlIndex OBJECT-TYPE
			SYNTAX InterfaceIndex
			MAX-ACCESS read-write
			STATUS current
			DESCRIPTION
				"The IfIndex of the line which test shall be executed"
			::= { shePotsLineTestDTMFandPulseDigitMeasureTestControl 2 }

		
--         1.3.6.1.4.1.231.7.1.2.2.1.38.10.7.15.2.3
		shePotsLineTestDTMFandPulseDigitMeasureTestControlStatus OBJECT-TYPE
			SYNTAX SheControlStatusType
			MAX-ACCESS read-only
			STATUS current
			DESCRIPTION
				"The status of a user command"
			::= { shePotsLineTestDTMFandPulseDigitMeasureTestControl 3 }

		
--         1.3.6.1.4.1.231.7.1.2.2.1.38.10.7.15.2.4
		shePotsLineTestDTMFandPulseDigitMeasureTestControlTimer OBJECT-TYPE
			SYNTAX Gauge32
			MAX-ACCESS read-only
			STATUS current
			DESCRIPTION
				"The maximum wait time for the manager for a long running user command."
			::= { shePotsLineTestDTMFandPulseDigitMeasureTestControl 4 }

		
--         1.3.6.1.4.1.231.7.1.2.2.1.38.10.7.15.2.5
		shePotsLineTestDTMFandPulseDigitMeasureTestControlTimeStamp OBJECT-TYPE
			SYNTAX Unsigned32
			MAX-ACCESS read-only
			STATUS current
			DESCRIPTION
				"The time stamp of the last command (end of command)."
			::= { shePotsLineTestDTMFandPulseDigitMeasureTestControl 5 }

		
--         1.3.6.1.4.1.231.7.1.2.2.1.38.10.7.15.2.6
		shePotsLineTestDTMFandPulseDigitMeasureTestControlReqResult OBJECT-TYPE
			SYNTAX ShePotsLineTestControlRequestResultType
			MAX-ACCESS read-only
			STATUS current
			DESCRIPTION
				"The result of the last user command."
			::= { shePotsLineTestDTMFandPulseDigitMeasureTestControl 6 }

		
--         1.3.6.1.4.1.231.7.1.2.2.1.38.10.7.15.2.7
		shePotsLineTestDTMFandPulseDigitMeasureTestControlTestType OBJECT-TYPE
			SYNTAX ShePotsLineTestDTMFandPulseDigitMeasureTestControlTestType
			MAX-ACCESS read-write
			STATUS current
			DESCRIPTION
				"vPTLKeyDtmfTest(0),
				vPTLKeyPulseTest(1),
				vPTLKeyBoth(2)
				"
			::= { shePotsLineTestDTMFandPulseDigitMeasureTestControl 7 }

		
--         1.3.6.1.4.1.231.7.1.2.2.1.38.10.7.16
		shePotsLineTestToneGenerationTestGroup OBJECT IDENTIFIER ::= { shePotsLineTestIltfTestGroup 16 }

		
--         1.3.6.1.4.1.231.7.1.2.2.1.38.10.7.16.1
		shePotsLineTestToneGenerationTestTable OBJECT-TYPE
			SYNTAX SEQUENCE OF ShePotsLineTestToneGenerationTestEntry
			MAX-ACCESS not-accessible
			STATUS current
			DESCRIPTION
				"This test generates up to four sinusoidal tones simultaneously."
			::= { shePotsLineTestToneGenerationTestGroup 1 }

		
--         1.3.6.1.4.1.231.7.1.2.2.1.38.10.7.16.1.1
		shePotsLineTestToneGenerationTestEntry OBJECT-TYPE
			SYNTAX ShePotsLineTestToneGenerationTestEntry
			MAX-ACCESS not-accessible
			STATUS current
			DESCRIPTION
				"Entry of shePotsLineTestToneGenerationTestTable,
				Each entry is used to represent a line which execute the test."
			INDEX { ifIndex }
			::= { shePotsLineTestToneGenerationTestTable 1 }

		
		ShePotsLineTestToneGenerationTestEntry ::=
			SEQUENCE { 
				shePotsLineTestToneGenerationTestTriggerSource
					ShePotsLineTestTriggerType
			 }

--         1.3.6.1.4.1.231.7.1.2.2.1.38.10.7.16.1.1.2
		shePotsLineTestToneGenerationTestTriggerSource OBJECT-TYPE
			SYNTAX ShePotsLineTestTriggerType
			MAX-ACCESS read-only
			STATUS current
			DESCRIPTION
				"Test Trigger Source."
			::= { shePotsLineTestToneGenerationTestEntry 1 }

		
--         1.3.6.1.4.1.231.7.1.2.2.1.38.10.7.16.2
		shePotsLineTestToneGenerationTestControl OBJECT IDENTIFIER ::= { shePotsLineTestToneGenerationTestGroup 2 }

		
--         1.3.6.1.4.1.231.7.1.2.2.1.38.10.7.16.2.1
		shePotsLineTestToneGenerationTestControlRequest OBJECT-TYPE
			SYNTAX ShePotsLineTestControlRequestType
			MAX-ACCESS read-write
			STATUS current
			DESCRIPTION
				"User command.
				setToneGenerationTest:
				shePotsLineTestToneGenerationTestControlIndex
				shePotsLineTestToneGenerationTestControlTestFreq0
				shePotsLineTestToneGenerationTestControlTestLevel0
				shePotsLineTestToneGenerationTestControlTestFreq1
				shePotsLineTestToneGenerationTestControlTestLevel1
				shePotsLineTestToneGenerationTestControlTestFreq2
				shePotsLineTestToneGenerationTestControlTestLevel2
				shePotsLineTestToneGenerationTestControlTestFreq3
				shePotsLineTestToneGenerationTestControlTestLevel3
				shePotsLineTestToneGenerationTestControlDuration
				
				
				Long-running Command"
			::= { shePotsLineTestToneGenerationTestControl 1 }

		
--         1.3.6.1.4.1.231.7.1.2.2.1.38.10.7.16.2.2
		shePotsLineTestToneGenerationTestControlIndex OBJECT-TYPE
			SYNTAX InterfaceIndex
			MAX-ACCESS read-write
			STATUS current
			DESCRIPTION
				"The IfIndex of the line which test shall be executed"
			::= { shePotsLineTestToneGenerationTestControl 2 }

		
--         1.3.6.1.4.1.231.7.1.2.2.1.38.10.7.16.2.3
		shePotsLineTestToneGenerationTestControlStatus OBJECT-TYPE
			SYNTAX SheControlStatusType
			MAX-ACCESS read-only
			STATUS current
			DESCRIPTION
				"The status of a user command"
			::= { shePotsLineTestToneGenerationTestControl 3 }

		
--         1.3.6.1.4.1.231.7.1.2.2.1.38.10.7.16.2.4
		shePotsLineTestToneGenerationTestControlTimer OBJECT-TYPE
			SYNTAX Gauge32
			MAX-ACCESS read-only
			STATUS current
			DESCRIPTION
				"The maximum wait time for the manager for a long running user command."
			::= { shePotsLineTestToneGenerationTestControl 4 }

		
--         1.3.6.1.4.1.231.7.1.2.2.1.38.10.7.16.2.5
		shePotsLineTestToneGenerationTestControlTimeStamp OBJECT-TYPE
			SYNTAX Unsigned32
			MAX-ACCESS read-only
			STATUS current
			DESCRIPTION
				"The time stamp of the last command (end of command)."
			::= { shePotsLineTestToneGenerationTestControl 5 }

		
--         1.3.6.1.4.1.231.7.1.2.2.1.38.10.7.16.2.6
		shePotsLineTestToneGenerationTestControlReqResult OBJECT-TYPE
			SYNTAX ShePotsLineTestControlRequestResultType
			MAX-ACCESS read-only
			STATUS current
			DESCRIPTION
				"The result of the last user command."
			::= { shePotsLineTestToneGenerationTestControl 6 }

		
--         1.3.6.1.4.1.231.7.1.2.2.1.38.10.7.16.2.7
		shePotsLineTestToneGenerationTestControlTestFreq0 OBJECT-TYPE
			SYNTAX INTEGER (0 | 100..3400)
			UNITS "Hz"
			MAX-ACCESS read-write
			STATUS current
			DESCRIPTION
				"Frequency in Hertz. 0 means tone is disabled"
			DEFVAL { 425 }
			::= { shePotsLineTestToneGenerationTestControl 7 }

		
--         1.3.6.1.4.1.231.7.1.2.2.1.38.10.7.16.2.8
		shePotsLineTestToneGenerationTestControlTestLevel0 OBJECT-TYPE
			SYNTAX INTEGER (-40..0)
			UNITS "dBm0"
			MAX-ACCESS read-write
			STATUS current
			DESCRIPTION
				"Power referenced to the 0 TLP, in dBm0. 0 means tone is disabled."
			DEFVAL { -10 }
			::= { shePotsLineTestToneGenerationTestControl 8 }

		
--         1.3.6.1.4.1.231.7.1.2.2.1.38.10.7.16.2.9
		shePotsLineTestToneGenerationTestControlTestFreq1 OBJECT-TYPE
			SYNTAX INTEGER (0 | 100..3400)
			UNITS "Hz"
			MAX-ACCESS read-write
			STATUS current
			DESCRIPTION
				"Frequency in Hertz .0 means tone is disabled"
			DEFVAL { 0 }
			::= { shePotsLineTestToneGenerationTestControl 9 }

		
--         1.3.6.1.4.1.231.7.1.2.2.1.38.10.7.16.2.10
		shePotsLineTestToneGenerationTestControlTestLevel1 OBJECT-TYPE
			SYNTAX INTEGER (-40..0)
			UNITS "dBm0"
			MAX-ACCESS read-write
			STATUS current
			DESCRIPTION
				"Power referenced to the 0 TLP, in dBm0. 0 means tone is disabled."
			DEFVAL { -10 }
			::= { shePotsLineTestToneGenerationTestControl 10 }

		
--         1.3.6.1.4.1.231.7.1.2.2.1.38.10.7.16.2.11
		shePotsLineTestToneGenerationTestControlTestFreq2 OBJECT-TYPE
			SYNTAX INTEGER (0 | 100..3400)
			UNITS "Hz"
			MAX-ACCESS read-write
			STATUS current
			DESCRIPTION
				"Frequency in Hertz. 0 means tone is disabled"
			DEFVAL { 0 }
			::= { shePotsLineTestToneGenerationTestControl 11 }

		
--         1.3.6.1.4.1.231.7.1.2.2.1.38.10.7.16.2.12
		shePotsLineTestToneGenerationTestControlTestLevel2 OBJECT-TYPE
			SYNTAX INTEGER (-40..0)
			UNITS "dBm0"
			MAX-ACCESS read-write
			STATUS current
			DESCRIPTION
				"Power referenced to the 0 TLP, in dBm0. 0 means tone is disabled."
			DEFVAL { -10 }
			::= { shePotsLineTestToneGenerationTestControl 12 }

		
--         1.3.6.1.4.1.231.7.1.2.2.1.38.10.7.16.2.13
		shePotsLineTestToneGenerationTestControlTestFreq3 OBJECT-TYPE
			SYNTAX INTEGER (0 | 100..3400)
			UNITS "Hz"
			MAX-ACCESS read-write
			STATUS current
			DESCRIPTION
				"Frequency in Hertz. 0 means tone is disabled"
			DEFVAL { 0 }
			::= { shePotsLineTestToneGenerationTestControl 13 }

		
--         1.3.6.1.4.1.231.7.1.2.2.1.38.10.7.16.2.14
		shePotsLineTestToneGenerationTestControlTestLevel3 OBJECT-TYPE
			SYNTAX INTEGER (-40..0)
			UNITS "dBm0"
			MAX-ACCESS read-write
			STATUS current
			DESCRIPTION
				"Power referenced to the 0 TLP, in dBm0. 0 means tone is disabled."
			DEFVAL { -10 }
			::= { shePotsLineTestToneGenerationTestControl 14 }

		
--         1.3.6.1.4.1.231.7.1.2.2.1.38.10.7.16.2.15
		shePotsLineTestToneGenerationTestControlDuration OBJECT-TYPE
			SYNTAX INTEGER (0..8192)
			UNITS "msec"
			MAX-ACCESS read-write
			STATUS current
			DESCRIPTION
				"Duration of tone generation (in msec)   maximum duration that can be specified is VPTL_MAX_DURATION"
			DEFVAL { 5000 }
			::= { shePotsLineTestToneGenerationTestControl 15 }

		
--         1.3.6.1.4.1.231.7.1.2.2.1.38.10.7.17
		shePotsLineTestReadLoopandBatteryConditionsTestGroup OBJECT IDENTIFIER ::= { shePotsLineTestIltfTestGroup 17 }

		
--         1.3.6.1.4.1.231.7.1.2.2.1.38.10.7.17.1
		shePotsLineTestReadLoopandBatteryConditionsTestTable OBJECT-TYPE
			SYNTAX SEQUENCE OF ShePotsLineTestReadLoopandBatteryConditionsTestEntry
			MAX-ACCESS not-accessible
			STATUS current
			DESCRIPTION
				"This procedure measures the instantaneous loop resistance, loop currents, and loop and
				battery voltages.No filtering is done during the measurement, so the results may fluctuate
				from one reading to the next in the presence of AC induction on the line."
			::= { shePotsLineTestReadLoopandBatteryConditionsTestGroup 1 }

		
--         1.3.6.1.4.1.231.7.1.2.2.1.38.10.7.17.1.1
		shePotsLineTestReadLoopandBatteryConditionsTestEntry OBJECT-TYPE
			SYNTAX ShePotsLineTestReadLoopandBatteryConditionsTestEntry
			MAX-ACCESS not-accessible
			STATUS current
			DESCRIPTION
				"Entry of shePotsLineTestReadLoopandBatteryConditionsTestTable,
				Each entry is used to represent a line which execute the test."
			INDEX { ifIndex }
			::= { shePotsLineTestReadLoopandBatteryConditionsTestTable 1 }

		
		ShePotsLineTestReadLoopandBatteryConditionsTestEntry ::=
			SEQUENCE { 
				shePotsLineTestReadLoopandBatteryConditionsTestrLoop
					INTEGER,
				shePotsLineTestReadLoopandBatteryConditionsTestiLg
					INTEGER,
				shePotsLineTestReadLoopandBatteryConditionsTestiMt
					INTEGER,
				shePotsLineTestReadLoopandBatteryConditionsTestvSab
					INTEGER,
				shePotsLineTestReadLoopandBatteryConditionsTestvHb
					INTEGER,
				shePotsLineTestReadLoopandBatteryConditionsTestvLb
					INTEGER,
				shePotsLineTestReadLoopandBatteryConditionsTestvPb
					INTEGER,
				shePotsLineTestReadLoopandBatteryConditionsTestMspl
					INTEGER,
				shePotsLineTestReadLoopandBatteryConditionsTestTriggerSource
					ShePotsLineTestTriggerType
			 }

--         1.3.6.1.4.1.231.7.1.2.2.1.38.10.7.17.1.1.1
		shePotsLineTestReadLoopandBatteryConditionsTestrLoop OBJECT-TYPE
			SYNTAX INTEGER
			UNITS "Ohm"
			MAX-ACCESS read-only
			STATUS current
			DESCRIPTION
				" Loop resistance in ohms x100
				should display as rLoop/100 Ohms"
			::= { shePotsLineTestReadLoopandBatteryConditionsTestEntry 1 }

		
--         1.3.6.1.4.1.231.7.1.2.2.1.38.10.7.17.1.1.2
		shePotsLineTestReadLoopandBatteryConditionsTestiLg OBJECT-TYPE
			SYNTAX INTEGER
			UNITS "A"
			MAX-ACCESS read-only
			STATUS current
			DESCRIPTION
				"Logitudinal current in in amps x100
				should display as iLg/100 A"
			::= { shePotsLineTestReadLoopandBatteryConditionsTestEntry 2 }

		
--         1.3.6.1.4.1.231.7.1.2.2.1.38.10.7.17.1.1.3
		shePotsLineTestReadLoopandBatteryConditionsTestiMt OBJECT-TYPE
			SYNTAX INTEGER
			UNITS "A"
			MAX-ACCESS read-only
			STATUS current
			DESCRIPTION
				"Metallic current in amps x100
				should display as iMt/100 A"
			::= { shePotsLineTestReadLoopandBatteryConditionsTestEntry 3 }

		
--         1.3.6.1.4.1.231.7.1.2.2.1.38.10.7.17.1.1.4
		shePotsLineTestReadLoopandBatteryConditionsTestvSab OBJECT-TYPE
			SYNTAX INTEGER
			UNITS "V"
			MAX-ACCESS read-only
			STATUS current
			DESCRIPTION
				"Sensed AB voltage in Volts x100
				should display as vSab/100 V"
			::= { shePotsLineTestReadLoopandBatteryConditionsTestEntry 4 }

		
--         1.3.6.1.4.1.231.7.1.2.2.1.38.10.7.17.1.1.5
		shePotsLineTestReadLoopandBatteryConditionsTestvHb OBJECT-TYPE
			SYNTAX INTEGER
			UNITS "V"
			MAX-ACCESS read-only
			STATUS current
			DESCRIPTION
				"High battery voltage in Volts x100
				should display as vHb/100 V
				"
			::= { shePotsLineTestReadLoopandBatteryConditionsTestEntry 5 }

		
--         1.3.6.1.4.1.231.7.1.2.2.1.38.10.7.17.1.1.6
		shePotsLineTestReadLoopandBatteryConditionsTestvLb OBJECT-TYPE
			SYNTAX INTEGER
			UNITS "V"
			MAX-ACCESS read-only
			STATUS current
			DESCRIPTION
				"Low battery voltage in Volts x100
				should display as vLb/100 V"
			::= { shePotsLineTestReadLoopandBatteryConditionsTestEntry 6 }

		
--         1.3.6.1.4.1.231.7.1.2.2.1.38.10.7.17.1.1.7
		shePotsLineTestReadLoopandBatteryConditionsTestvPb OBJECT-TYPE
			SYNTAX INTEGER
			UNITS "V"
			MAX-ACCESS read-only
			STATUS current
			DESCRIPTION
				"Positive battery voltage in Volts x100
				should display as vPb/100 V"
			::= { shePotsLineTestReadLoopandBatteryConditionsTestEntry 7 }

		
--         1.3.6.1.4.1.231.7.1.2.2.1.38.10.7.17.1.1.8
		shePotsLineTestReadLoopandBatteryConditionsTestMspl OBJECT-TYPE
			SYNTAX INTEGER
			UNITS "V"
			MAX-ACCESS read-only
			STATUS current
			DESCRIPTION
				"Measured Metering signal peak voltage in Volts x100
				should display as Mspl/100 V"
			::= { shePotsLineTestReadLoopandBatteryConditionsTestEntry 8 }

		
--         1.3.6.1.4.1.231.7.1.2.2.1.38.10.7.17.1.1.10
		shePotsLineTestReadLoopandBatteryConditionsTestTriggerSource OBJECT-TYPE
			SYNTAX ShePotsLineTestTriggerType
			MAX-ACCESS read-only
			STATUS current
			DESCRIPTION
				"Test Trigger Source."
			::= { shePotsLineTestReadLoopandBatteryConditionsTestEntry 9 }

		
--         1.3.6.1.4.1.231.7.1.2.2.1.38.10.7.17.2
		shePotsLineTestReadLoopandBatteryConditionsTestControl OBJECT IDENTIFIER ::= { shePotsLineTestReadLoopandBatteryConditionsTestGroup 2 }

		
--         1.3.6.1.4.1.231.7.1.2.2.1.38.10.7.17.2.1
		shePotsLineTestReadLoopandBatteryConditionsTestControlRequest OBJECT-TYPE
			SYNTAX ShePotsLineTestControlRequestType
			MAX-ACCESS read-write
			STATUS current
			DESCRIPTION
				"User command
				setReadLoopandBatteryConditionsTest:
				shePotsLineTestReadLoopandBatteryConditionsTestControlIndex
				
				
				Long-running Command
				"
			::= { shePotsLineTestReadLoopandBatteryConditionsTestControl 1 }

		
--         1.3.6.1.4.1.231.7.1.2.2.1.38.10.7.17.2.2
		shePotsLineTestReadLoopandBatteryConditionsTestControlIndex OBJECT-TYPE
			SYNTAX InterfaceIndex
			MAX-ACCESS read-write
			STATUS current
			DESCRIPTION
				"The IfIndex of the card which test shall be executed"
			::= { shePotsLineTestReadLoopandBatteryConditionsTestControl 2 }

		
--         1.3.6.1.4.1.231.7.1.2.2.1.38.10.7.17.2.3
		shePotsLineTestReadLoopandBatteryConditionsTestControlStatus OBJECT-TYPE
			SYNTAX SheControlStatusType
			MAX-ACCESS read-only
			STATUS current
			DESCRIPTION
				"The status of a user command"
			::= { shePotsLineTestReadLoopandBatteryConditionsTestControl 3 }

		
--         1.3.6.1.4.1.231.7.1.2.2.1.38.10.7.17.2.4
		shePotsLineTestReadLoopandBatteryConditionsTestControlTimer OBJECT-TYPE
			SYNTAX Gauge32
			MAX-ACCESS read-only
			STATUS current
			DESCRIPTION
				"The maximum wait time for the manager for a long running user command."
			::= { shePotsLineTestReadLoopandBatteryConditionsTestControl 4 }

		
--         1.3.6.1.4.1.231.7.1.2.2.1.38.10.7.17.2.5
		shePotsLineTestReadLoopandBatteryConditionsTestControlTimeStamp OBJECT-TYPE
			SYNTAX Unsigned32
			MAX-ACCESS read-only
			STATUS current
			DESCRIPTION
				"The time stamp of the last command (end of command)."
			::= { shePotsLineTestReadLoopandBatteryConditionsTestControl 5 }

		
--         1.3.6.1.4.1.231.7.1.2.2.1.38.10.7.17.2.6
		shePotsLineTestReadLoopandBatteryConditionsTestControlReqResult OBJECT-TYPE
			SYNTAX ShePotsLineTestControlRequestResultType
			MAX-ACCESS read-only
			STATUS current
			DESCRIPTION
				"The result of the last user command."
			::= { shePotsLineTestReadLoopandBatteryConditionsTestControl 6 }

		
--         1.3.6.1.4.1.231.7.1.2.2.1.38.10.7.18
		shePotsLineTestMeteringSelfTestGroup OBJECT IDENTIFIER ::= { shePotsLineTestIltfTestGroup 18 }

		
--         1.3.6.1.4.1.231.7.1.2.2.1.38.10.7.18.1
		shePotsLineTestMeteringSelfTestTable OBJECT-TYPE
			SYNTAX SEQUENCE OF ShePotsLineTestMeteringSelfTestEntry
			MAX-ACCESS not-accessible
			STATUS current
			DESCRIPTION
				"This procedure verifies that the line card can generate a metering pulse. It drives a metering
				signal into both a resistive load and an open-circuit using the current Metering Profile applied
				to the line."
			::= { shePotsLineTestMeteringSelfTestGroup 1 }

		
--         1.3.6.1.4.1.231.7.1.2.2.1.38.10.7.18.1.1
		shePotsLineTestMeteringSelfTestEntry OBJECT-TYPE
			SYNTAX ShePotsLineTestMeteringSelfTestEntry
			MAX-ACCESS not-accessible
			STATUS current
			DESCRIPTION
				"Entry of shePotsLineTestMeteringSelfTestTable ,
				Each entry is used to represent a line which execute the test."
			INDEX { ifIndex }
			::= { shePotsLineTestMeteringSelfTestTable 1 }

		
		ShePotsLineTestMeteringSelfTestEntry ::=
			SEQUENCE { 
				shePotsLineTestMeteringSelfMeterTerm
					INTEGER,
				shePotsLineTestMeteringSelfMeterTermCkt
					INTEGER,
				shePotsLineTestMeteringSelfTestTestPassed
					TruthValue,
				shePotsLineTestMeteringSelfTestTriggerSource
					ShePotsLineTestTriggerType
			 }

--         1.3.6.1.4.1.231.7.1.2.2.1.38.10.7.18.1.1.1
		shePotsLineTestMeteringSelfMeterTerm OBJECT-TYPE
			SYNTAX INTEGER
			UNITS "V"
			MAX-ACCESS read-only
			STATUS current
			DESCRIPTION
				"Metering signal level in Volts x100 under load condition .
				However, this output should not be shown to users.
				should display as Term/100 V"
			::= { shePotsLineTestMeteringSelfTestEntry 1 }

		
--         1.3.6.1.4.1.231.7.1.2.2.1.38.10.7.18.1.1.2
		shePotsLineTestMeteringSelfMeterTermCkt OBJECT-TYPE
			SYNTAX INTEGER
			UNITS "V"
			MAX-ACCESS read-only
			STATUS current
			DESCRIPTION
				"Metering signal level in Volts x100 under open circuit condition .
				However, this output should not be shown to users.
				should display as TermCkt/100 V"
			::= { shePotsLineTestMeteringSelfTestEntry 2 }

		
--         1.3.6.1.4.1.231.7.1.2.2.1.38.10.7.18.1.1.3
		shePotsLineTestMeteringSelfTestTestPassed OBJECT-TYPE
			SYNTAX TruthValue
			MAX-ACCESS read-only
			STATUS current
			DESCRIPTION
				"Test passed flag.
				1: the test passed;
				0: the test failed.    "
			::= { shePotsLineTestMeteringSelfTestEntry 3 }

		
--         1.3.6.1.4.1.231.7.1.2.2.1.38.10.7.18.1.1.4
		shePotsLineTestMeteringSelfTestTriggerSource OBJECT-TYPE
			SYNTAX ShePotsLineTestTriggerType
			MAX-ACCESS read-only
			STATUS current
			DESCRIPTION
				"Test Trigger Source."
			::= { shePotsLineTestMeteringSelfTestEntry 4 }

		
--         1.3.6.1.4.1.231.7.1.2.2.1.38.10.7.18.2
		shePotsLineTestMeteringSelfTestControl OBJECT IDENTIFIER ::= { shePotsLineTestMeteringSelfTestGroup 2 }

		
--         1.3.6.1.4.1.231.7.1.2.2.1.38.10.7.18.2.1
		shePotsLineTestMeteringSelfTestControlRequest OBJECT-TYPE
			SYNTAX ShePotsLineTestControlRequestType
			MAX-ACCESS read-write
			STATUS current
			DESCRIPTION
				"user command.
				setMeteringSelfTest:
				shePotsLineTestMeteringSelfTestControlIndex
				
				
				Long-running Command
				"
			::= { shePotsLineTestMeteringSelfTestControl 1 }

		
--         1.3.6.1.4.1.231.7.1.2.2.1.38.10.7.18.2.2
		shePotsLineTestMeteringSelfTestControlIndex OBJECT-TYPE
			SYNTAX InterfaceIndex
			MAX-ACCESS read-write
			STATUS current
			DESCRIPTION
				"The IfIndex of the line which test shall be executed"
			::= { shePotsLineTestMeteringSelfTestControl 2 }

		
--         1.3.6.1.4.1.231.7.1.2.2.1.38.10.7.18.2.3
		shePotsLineTestMeteringSelfTestControlStatus OBJECT-TYPE
			SYNTAX SheControlStatusType
			MAX-ACCESS read-only
			STATUS current
			DESCRIPTION
				"The status of a user command"
			::= { shePotsLineTestMeteringSelfTestControl 3 }

		
--         1.3.6.1.4.1.231.7.1.2.2.1.38.10.7.18.2.4
		shePotsLineTestMeteringSelfTestControlTimer OBJECT-TYPE
			SYNTAX Gauge32
			MAX-ACCESS read-only
			STATUS current
			DESCRIPTION
				"The maximum wait time for the manager for a long running user command."
			::= { shePotsLineTestMeteringSelfTestControl 4 }

		
--         1.3.6.1.4.1.231.7.1.2.2.1.38.10.7.18.2.5
		shePotsLineTestMeteringSelfTestControlTimeStamp OBJECT-TYPE
			SYNTAX Unsigned32
			MAX-ACCESS read-only
			STATUS current
			DESCRIPTION
				"The time stamp of the last command (end of command)."
			::= { shePotsLineTestMeteringSelfTestControl 5 }

		
--         1.3.6.1.4.1.231.7.1.2.2.1.38.10.7.18.2.6
		shePotsLineTestMeteringSelfTestControlReqResult OBJECT-TYPE
			SYNTAX ShePotsLineTestControlRequestResultType
			MAX-ACCESS read-only
			STATUS current
			DESCRIPTION
				"The result of the last user command."
			::= { shePotsLineTestMeteringSelfTestControl 6 }

		
--         1.3.6.1.4.1.231.7.1.2.2.1.38.10.7.19
		shePotsLineTestForeignACcurrentsTestGroup OBJECT IDENTIFIER ::= { shePotsLineTestIltfTestGroup 19 }

		
--         1.3.6.1.4.1.231.7.1.2.2.1.38.10.7.19.1
		shePotsLineTestForeignACcurrentsTestTable OBJECT-TYPE
			SYNTAX SEQUENCE OF ShePotsLineTestForeignACcurrentsTestEntry
			MAX-ACCESS not-accessible
			STATUS current
			DESCRIPTION
				"This test measures foreign AC currents."
			::= { shePotsLineTestForeignACcurrentsTestGroup 1 }

		
--         1.3.6.1.4.1.231.7.1.2.2.1.38.10.7.19.1.1
		shePotsLineTestForeignACcurrentsTestEntry OBJECT-TYPE
			SYNTAX ShePotsLineTestForeignACcurrentsTestEntry
			MAX-ACCESS not-accessible
			STATUS current
			DESCRIPTION
				"Entry of shePotsLineTestForeignACcurrentsTestTable ,
				Each entry is used to represent a line which execute the test."
			INDEX { ifIndex }
			::= { shePotsLineTestForeignACcurrentsTestTable 1 }

		
		ShePotsLineTestForeignACcurrentsTestEntry ::=
			SEQUENCE { 
				shePotsLineTestForeignACcurrentsTestiTip
					INTEGER,
				shePotsLineTestForeignACcurrentsTestiRing
					INTEGER,
				shePotsLineTestForeignACcurrentsTestTriggerSource
					ShePotsLineTestTriggerType
			 }

--         1.3.6.1.4.1.231.7.1.2.2.1.38.10.7.19.1.1.1
		shePotsLineTestForeignACcurrentsTestiTip OBJECT-TYPE
			SYNTAX INTEGER
			UNITS "A"
			MAX-ACCESS read-only
			STATUS current
			DESCRIPTION
				"Measured tip lead current in Amps x100
				should display as iTip/100 A"
			::= { shePotsLineTestForeignACcurrentsTestEntry 1 }

		
--         1.3.6.1.4.1.231.7.1.2.2.1.38.10.7.19.1.1.2
		shePotsLineTestForeignACcurrentsTestiRing OBJECT-TYPE
			SYNTAX INTEGER
			UNITS "A"
			MAX-ACCESS read-only
			STATUS current
			DESCRIPTION
				"Measured ring lead current in Amps x100
				should display as iRing/100 A"
			::= { shePotsLineTestForeignACcurrentsTestEntry 2 }

		
--         1.3.6.1.4.1.231.7.1.2.2.1.38.10.7.19.1.1.4
		shePotsLineTestForeignACcurrentsTestTriggerSource OBJECT-TYPE
			SYNTAX ShePotsLineTestTriggerType
			MAX-ACCESS read-only
			STATUS current
			DESCRIPTION
				"Test Trigger Source."
			::= { shePotsLineTestForeignACcurrentsTestEntry 3 }

		
--         1.3.6.1.4.1.231.7.1.2.2.1.38.10.7.19.2
		shePotsLineTestForeignAcCurrentsTestControl OBJECT IDENTIFIER ::= { shePotsLineTestForeignACcurrentsTestGroup 2 }

		
--         1.3.6.1.4.1.231.7.1.2.2.1.38.10.7.19.2.1
		shePotsLineTestForeignACcurrentsTestControlRequest OBJECT-TYPE
			SYNTAX ShePotsLineTestControlRequestType
			MAX-ACCESS read-write
			STATUS current
			DESCRIPTION
				"User command.
				setForeignACcurrentsTest:
				shePotsLineTestForeignACcurrentsTestControlIndex
				
				
				Long-running Command"
			::= { shePotsLineTestForeignAcCurrentsTestControl 1 }

		
--         1.3.6.1.4.1.231.7.1.2.2.1.38.10.7.19.2.2
		shePotsLineTestForeignACcurrentsTestControlIndex OBJECT-TYPE
			SYNTAX InterfaceIndex
			MAX-ACCESS read-write
			STATUS current
			DESCRIPTION
				"The IfIndex of the line which test shall be executed"
			::= { shePotsLineTestForeignAcCurrentsTestControl 2 }

		
--         1.3.6.1.4.1.231.7.1.2.2.1.38.10.7.19.2.3
		shePotsLineTestForeignACcurrentsTestControlStatus OBJECT-TYPE
			SYNTAX SheControlStatusType
			MAX-ACCESS read-only
			STATUS current
			DESCRIPTION
				"The status of a user command"
			::= { shePotsLineTestForeignAcCurrentsTestControl 3 }

		
--         1.3.6.1.4.1.231.7.1.2.2.1.38.10.7.19.2.4
		shePotsLineTestForeignACcurrentsTestControlTimer OBJECT-TYPE
			SYNTAX Gauge32
			MAX-ACCESS read-only
			STATUS current
			DESCRIPTION
				"The maximum wait time for the manager for a long running user command."
			::= { shePotsLineTestForeignAcCurrentsTestControl 4 }

		
--         1.3.6.1.4.1.231.7.1.2.2.1.38.10.7.19.2.5
		shePotsLineTestForeignACcurrentsTestControlTimeStamp OBJECT-TYPE
			SYNTAX Unsigned32
			MAX-ACCESS read-only
			STATUS current
			DESCRIPTION
				"The time stamp of the last command (end of command)."
			::= { shePotsLineTestForeignAcCurrentsTestControl 5 }

		
--         1.3.6.1.4.1.231.7.1.2.2.1.38.10.7.19.2.6
		shePotsLineTestForeignACcurrentsTestControlReqResult OBJECT-TYPE
			SYNTAX ShePotsLineTestControlRequestResultType
			MAX-ACCESS read-only
			STATUS current
			DESCRIPTION
				"The result of the last user command."
			::= { shePotsLineTestForeignAcCurrentsTestControl 6 }

		
--         1.3.6.1.4.1.231.7.1.2.2.1.38.10.7.20
		shePotsLineTestHowlerTestGroup OBJECT IDENTIFIER ::= { shePotsLineTestIltfTestGroup 20 }

		
--         1.3.6.1.4.1.231.7.1.2.2.1.38.10.7.20.1
		shePotsLineTestHowlerTestTable OBJECT-TYPE
			SYNTAX SEQUENCE OF ShePotsLineTestHowlerTestEntry
			MAX-ACCESS not-accessible
			STATUS current
			DESCRIPTION
				"This procedure generates a Howler (Receiver Off Hook) tone until the phone goes on hook."
			::= { shePotsLineTestHowlerTestGroup 1 }

		
--         1.3.6.1.4.1.231.7.1.2.2.1.38.10.7.20.1.1
		shePotsLineTestHowlerTestEntry OBJECT-TYPE
			SYNTAX ShePotsLineTestHowlerTestEntry
			MAX-ACCESS not-accessible
			STATUS current
			DESCRIPTION
				"Entry of shePotsLineTestHowlerTestTable ,
				Each entry is used to represent a line which execute the test.
				"
			INDEX { ifIndex }
			::= { shePotsLineTestHowlerTestTable 1 }

		
		ShePotsLineTestHowlerTestEntry ::=
			SEQUENCE { 
				shePotsLineTestHowlerTestTriggerSource
					ShePotsLineTestTriggerType,
				shePotsLineTestHowlerTestTimeLimitExpired
					TruthValue
			 }

--         1.3.6.1.4.1.231.7.1.2.2.1.38.10.7.20.1.1.2
		shePotsLineTestHowlerTestTriggerSource OBJECT-TYPE
			SYNTAX ShePotsLineTestTriggerType
			MAX-ACCESS read-only
			STATUS current
			DESCRIPTION
				"Test Trigger Source."
			::= { shePotsLineTestHowlerTestEntry 1 }

		
--         1.3.6.1.4.1.231.7.1.2.2.1.38.10.7.20.1.1.2
		shePotsLineTestHowlerTestTimeLimitExpired OBJECT-TYPE
			SYNTAX TruthValue
			MAX-ACCESS read-only
			STATUS current
			DESCRIPTION
				"0	test case is stopped by hook on event
				1	test case is stopped due to howler timer time out "
			::= { shePotsLineTestHowlerTestEntry 2 }

		
--         1.3.6.1.4.1.231.7.1.2.2.1.38.10.7.20.2
		shePotsLineTestHowlerTestControl OBJECT IDENTIFIER ::= { shePotsLineTestHowlerTestGroup 2 }

		
--         1.3.6.1.4.1.231.7.1.2.2.1.38.10.7.20.2.1
		shePotsLineTestHowlerTestControlRequest OBJECT-TYPE
			SYNTAX ShePotsLineTestControlRequestType
			MAX-ACCESS read-write
			STATUS current
			DESCRIPTION
				"User command.
				setHowlerTest:
				shePotsLineTestHowlerTestControlIndex
				shePotsLineTestHowlerTestControlToneType
				
				
				Long-running Command"
			::= { shePotsLineTestHowlerTestControl 1 }

		
--         1.3.6.1.4.1.231.7.1.2.2.1.38.10.7.20.2.2
		shePotsLineTestHowlerTestControlIndex OBJECT-TYPE
			SYNTAX InterfaceIndex
			MAX-ACCESS read-write
			STATUS current
			DESCRIPTION
				"The IfIndex of the line which test shall be executed"
			::= { shePotsLineTestHowlerTestControl 2 }

		
--         1.3.6.1.4.1.231.7.1.2.2.1.38.10.7.20.2.3
		shePotsLineTestHowlerTestControlStatus OBJECT-TYPE
			SYNTAX SheControlStatusType
			MAX-ACCESS read-only
			STATUS current
			DESCRIPTION
				"
				The status of a user command"
			::= { shePotsLineTestHowlerTestControl 3 }

		
--         1.3.6.1.4.1.231.7.1.2.2.1.38.10.7.20.2.4
		shePotsLineTestHowlerTestControlTimer OBJECT-TYPE
			SYNTAX Gauge32
			MAX-ACCESS read-only
			STATUS current
			DESCRIPTION
				"The maximum wait time for the manager for a long running user command."
			::= { shePotsLineTestHowlerTestControl 4 }

		
--         1.3.6.1.4.1.231.7.1.2.2.1.38.10.7.20.2.5
		shePotsLineTestHowlerTestControlTimeStamp OBJECT-TYPE
			SYNTAX Unsigned32
			MAX-ACCESS read-only
			STATUS current
			DESCRIPTION
				"The time stamp of the last command (end of command)."
			::= { shePotsLineTestHowlerTestControl 5 }

		
--         1.3.6.1.4.1.231.7.1.2.2.1.38.10.7.20.2.5
		shePotsLineTestHowlerTestControlReqResult OBJECT-TYPE
			SYNTAX ShePotsLineTestControlRequestResultType
			MAX-ACCESS read-only
			STATUS current
			DESCRIPTION
				"The result of the last user command."
			::= { shePotsLineTestHowlerTestControl 6 }

		
--         1.3.6.1.4.1.231.7.1.2.2.1.38.10.7.20.2.7
		shePotsLineTestHowlerTestControlToneType OBJECT-TYPE
			SYNTAX ShePotsLineTestHowlerTestControlToneType
			MAX-ACCESS read-write
			STATUS current
			DESCRIPTION
				"vPTLNorthAmericanHowlerTone(0),
				
				Following 2 types are not supported now.
				vPTLBritishHowlerTone(1),
				vPTLAustralianHowlerTone(2)
				"
			::= { shePotsLineTestHowlerTestControl 7 }

		
--         1.3.6.1.4.1.231.7.1.2.2.1.38.10.7.21
		shePotsLineTestReversalTestGroup OBJECT IDENTIFIER ::= { shePotsLineTestIltfTestGroup 21 }

		
--         1.3.6.1.4.1.231.7.1.2.2.1.38.10.7.21.1
		shePotsLineTestReversalTestTable OBJECT-TYPE
			SYNTAX SEQUENCE OF ShePotsLineTestReversalTestEntry
			MAX-ACCESS not-accessible
			STATUS current
			DESCRIPTION
				"Talble of Reversal Test"
			::= { shePotsLineTestReversalTestGroup 1 }

		
--         1.3.6.1.4.1.231.7.1.2.2.1.38.10.7.21.1.1
		shePotsLineTestReversalTestEntry OBJECT-TYPE
			SYNTAX ShePotsLineTestReversalTestEntry
			MAX-ACCESS not-accessible
			STATUS current
			DESCRIPTION
				"Entry of shePotsLineTestReversalTestTable ,
				Each entry is used to represent a line which execute the test.
				"
			INDEX { ifIndex }
			::= { shePotsLineTestReversalTestTable 1 }

		
		ShePotsLineTestReversalTestEntry ::=
			SEQUENCE { 
				shePotsLineTestReversalTestTriggerSource
					ShePotsLineTestTriggerType,
				shePotsLineTestReversalTestpassed
					TruthValue
			 }

--         1.3.6.1.4.1.231.7.1.2.2.1.38.10.7.21.1.1.3
		shePotsLineTestReversalTestTriggerSource OBJECT-TYPE
			SYNTAX ShePotsLineTestTriggerType
			MAX-ACCESS read-only
			STATUS current
			DESCRIPTION
				"Test Trigger Source."
			::= { shePotsLineTestReversalTestEntry 1 }

		
--         1.3.6.1.4.1.231.7.1.2.2.1.38.10.7.21.1.1.3
		shePotsLineTestReversalTestpassed OBJECT-TYPE
			SYNTAX TruthValue
			MAX-ACCESS read-only
			STATUS current
			DESCRIPTION
				"0	test case failed
				1	test case passed "
			::= { shePotsLineTestReversalTestEntry 2 }

		
--         1.3.6.1.4.1.231.7.1.2.2.1.38.10.7.21.2
		shePotsLineTestReversalTestGroupControl OBJECT IDENTIFIER ::= { shePotsLineTestReversalTestGroup 2 }

		
--         1.3.6.1.4.1.231.7.1.2.2.1.38.10.7.21.2.1
		shePotsLineTestReversalTestControlRequest OBJECT-TYPE
			SYNTAX ShePotsLineTestControlRequestType
			MAX-ACCESS read-write
			STATUS current
			DESCRIPTION
				"User command.
				setReversalTest:
				shePotsLineTestReversalTestControlIndex
				
				
				Long-running Command
				"
			::= { shePotsLineTestReversalTestGroupControl 1 }

		
--         1.3.6.1.4.1.231.7.1.2.2.1.38.10.7.21.2.2
		shePotsLineTestReversalTestControlIndex OBJECT-TYPE
			SYNTAX InterfaceIndex
			MAX-ACCESS read-write
			STATUS current
			DESCRIPTION
				"The IfIndex of the line which test shall be executed"
			::= { shePotsLineTestReversalTestGroupControl 2 }

		
--         1.3.6.1.4.1.231.7.1.2.2.1.38.10.7.21.2.3
		shePotsLineTestReversalTestControlStatus OBJECT-TYPE
			SYNTAX SheControlStatusType
			MAX-ACCESS read-only
			STATUS current
			DESCRIPTION
				"The status of a user command"
			::= { shePotsLineTestReversalTestGroupControl 3 }

		
--         1.3.6.1.4.1.231.7.1.2.2.1.38.10.7.21.2.4
		shePotsLineTestReversalTestControlTimer OBJECT-TYPE
			SYNTAX Gauge32
			MAX-ACCESS read-only
			STATUS current
			DESCRIPTION
				"The maximum wait time for the manager for a long running user command."
			::= { shePotsLineTestReversalTestGroupControl 4 }

		
--         1.3.6.1.4.1.231.7.1.2.2.1.38.10.7.21.2.5
		shePotsLineTestReversalTestControlTimeStamp OBJECT-TYPE
			SYNTAX Unsigned32
			MAX-ACCESS read-only
			STATUS current
			DESCRIPTION
				"The time stamp of the last command (end of command)."
			::= { shePotsLineTestReversalTestGroupControl 5 }

		
--         1.3.6.1.4.1.231.7.1.2.2.1.38.10.7.21.2.6
		shePotsLineTestReversalTestControlReqResult OBJECT-TYPE
			SYNTAX ShePotsLineTestControlRequestResultType
			MAX-ACCESS read-only
			STATUS current
			DESCRIPTION
				"The result of the last user command."
			::= { shePotsLineTestReversalTestGroupControl 6 }

		
--         1.3.6.1.4.1.231.7.1.2.2.1.38.10.8
		shePotsLineTestNotificationGroup OBJECT IDENTIFIER ::= { shePotsLineTest 8 }

		
--         1.3.6.1.4.1.231.7.1.2.2.1.38.10.8.1
		shePotsLineTestAlarms OBJECT IDENTIFIER ::= { shePotsLineTestNotificationGroup 1 }

		
		shePotsLineTestpat3EleResFltAlm NOTIFICATION-TYPE
			OBJECTS { sheAlarmTimeAndDate, sheAlarmReportingSource, sheAlarmReportingSourceType, sheAlarmSeverity }
			STATUS current
			DESCRIPTION 
				"Alarm of Three Element Resistance Test"
			::= { shePotsLineTestAlarms 1 }

		
		shePotsLineTestpat3EleCapFltAlm NOTIFICATION-TYPE
			OBJECTS { sheAlarmTimeAndDate, sheAlarmReportingSource, sheAlarmReportingSourceType, sheAlarmSeverity }
			STATUS current
			DESCRIPTION 
				"Alarm of Three Element Capacitance Test"
			::= { shePotsLineTestAlarms 2 }

		
		shePotsLineTestpatNoiseFltAlm NOTIFICATION-TYPE
			OBJECTS { sheAlarmTimeAndDate, sheAlarmReportingSource, sheAlarmReportingSourceType, sheAlarmSeverity }
			STATUS current
			DESCRIPTION 
				"Alarm of Noise Measurement Test"
			::= { shePotsLineTestAlarms 3 }

		
		shePotsLineTestpatDcFeedFltAlm NOTIFICATION-TYPE
			OBJECTS { sheAlarmTimeAndDate, sheAlarmReportingSource, sheAlarmReportingSourceType, sheAlarmSeverity }
			STATUS current
			DESCRIPTION 
				"Alarm of DC Feed Self Test"
			::= { shePotsLineTestAlarms 4 }

		
		shePotsLineTestAcAlarms NOTIFICATION-TYPE
			OBJECTS { sheAlarmTimeAndDate, sheAlarmReportingSource, sheAlarmReportingSourceType, sheAlarmSeverity }
			STATUS current
			DESCRIPTION 
				"AC fault alarm "
			::= { shePotsLineTestAlarms 5 }

		
		shePotsLineTestDcAlarms NOTIFICATION-TYPE
			OBJECTS { sheAlarmTimeAndDate, sheAlarmReportingSource, sheAlarmReportingSourceType, sheAlarmSeverity }
			STATUS current
			DESCRIPTION 
				"DC fault alarm "
			::= { shePotsLineTestAlarms 6 }

		
		shePotsLineTestGkAlarms NOTIFICATION-TYPE
			OBJECTS { sheAlarmTimeAndDate, sheAlarmReportingSource, sheAlarmReportingSourceType, sheAlarmSeverity }
			STATUS current
			DESCRIPTION 
				"GK fault alarm"
			::= { shePotsLineTestAlarms 7 }

		
		shePotsLineTestThermAlalarms NOTIFICATION-TYPE
			OBJECTS { sheAlarmTimeAndDate, sheAlarmReportingSource, sheAlarmReportingSourceType, sheAlarmSeverity }
			STATUS current
			DESCRIPTION 
				"Thermal fault alarm"
			::= { shePotsLineTestAlarms 8 }

		
--         1.3.6.1.4.1.231.7.1.2.2.1.38.10.8.2
		shePotsLineTestIltfTraps OBJECT IDENTIFIER ::= { shePotsLineTestNotificationGroup 2 }

		
		shePotsLineTestVptlTidOnOffHookSelfTestTrap NOTIFICATION-TYPE
			OBJECTS { ifIndex, shePotsLineTestVptlOnOffHookSelfTestStatus, shePotsLineTestVptlOnOffHookSelfTestTriggerSource, shePotsLineTestAlarm, sheAlarmTimeAndDate, 
				shePotsLineTestVptlTidOnOffHookSelfTestControlTimeStamp }
			STATUS current
			DESCRIPTION 
				"Trap of On/Off Hook Self Test.
				SheAlarmTimeAndDate is filled with the same value as the set alarms(AC, DC, GK)
				triggering automeasure test, otherwise it should be filled with 0."
			::= { shePotsLineTestIltfTraps 1 }

		
		shePotsLineTestDCFeedSelfTestTrap NOTIFICATION-TYPE
			OBJECTS { ifIndex, shePotsLineTestDcFeedSelfTestImtHighBatNormalFeed, shePotsLineTestDcFeedSelfTestImtHighBatReverseFeed, shePotsLineTestDcFeedSelfTestImtLowBatNormalFeed, shePotsLineTestDcFeedSelfTestImtBoostBatNormalFeed, 
				shePotsLineTestDcFeedSelfTestRloadMsrd, shePotsLineTestDcFeedSelfTestvBat, shePotsLineTestDcFeedSelfTestvTr, shePotsLineTestDcFeedSelfTestPassed, shePotsLineTestDcFeedSelfTestTriggerSource, 
				shePotsLineTestAlarm, sheAlarmTimeAndDate, shePotsLineTestLineTestDcFeedSelfTestControlTimeStamp }
			STATUS current
			DESCRIPTION 
				"Trap of DC Feed Self Test
				However only Vtr and TestPassed should be shown to users.
				sheAlarmTimeAndDate is filled with the same value as the set alarms(AC, DC, GK)
				triggering automeasure test, otherwise it should be filled with 0."
			::= { shePotsLineTestIltfTraps 2 }

		
		shePotsLineTestRingingSelfTestTrap NOTIFICATION-TYPE
			OBJECTS { ifIndex, shePotsLineTestRingingSelfTestOnOffHookChangeDetected, shePotsLineTestRingingSelfTestTestPassed, shePotsLineTestRingingSelfTestTriggerSource, shePotsLineTestAlarm, 
				sheAlarmTimeAndDate, shePotsLineTestRingingSelfTestControlTimeStamp }
			STATUS current
			DESCRIPTION 
				"Trap of Ringing Self Test.
				sheAlarmTimeAndDate is filled with the same value as the set alarms(AC, DC, GK)
				triggering automeasure test, otherwise it should be filled with 0."
			::= { shePotsLineTestIltfTraps 3 }

		
		shePotsLineTestTransmitionSelfTestTrap NOTIFICATION-TYPE
			OBJECTS { ifIndex, shePotsLineTestTransmissionSelfTestThlOpen, shePotsLineTestTransmissionSelfTestThlExpectedLL, shePotsLineTestTransmissionSelfTestThlExpectedUL, shePotsLineTestTransmissionSelfTestThlRload, 
				shePotsLineTestTransmissionSelfTestAbortedDueToOffHook, shePotsLineTestTransmissionSelfTestPassed, shePotsLineTestTransmissionSelfTestTriggerSource, shePotsLineTestAlarm, sheAlarmTimeAndDate, 
				shePotsLineTestTransmissionSelfTestControlTimeStamp }
			STATUS current
			DESCRIPTION 
				"Trap of Transmition Self Test
				However only  TestPassed should be shown to users.
				sheAlarmTimeAndDate is filled with the same value as the set alarms(AC, DC, GK)
				triggering automeasure test, otherwise it should be filled with 0."
			::= { shePotsLineTestIltfTraps 4 }

		
		shePotsLineTestTransHybridLossTestTrap NOTIFICATION-TYPE
			OBJECTS { ifIndex, shePotsLineTestTransHybridLossTestEcho, shePotsLineTestTransHybridLossTestLoss, shePotsLineTestTransHybridLossTestTriggerSource, shePotsLineTestAlarm, 
				sheAlarmTimeAndDate, shePotsLineTestTransHybridLossTestControlTimeStamp }
			STATUS current
			DESCRIPTION 
				"Trap of Trans-Hybrid Loss Test.
				sheAlarmTimeAndDate is filled with the same value as the set alarms(AC, DC, GK)
				triggering automeasure test, otherwise it should be filled with 0."
			::= { shePotsLineTestIltfTraps 5 }

		
		shePotsLineTestNoiseMeasurementTestTrap NOTIFICATION-TYPE
			OBJECTS { ifIndex, shePotsLineTestNoiseMeasurementTestNoise, shePotsLineTestNoiseMeasurementTestTriggerSource, shePotsLineTestAlarm, sheAlarmTimeAndDate, 
				shePotsLineTestNoiseMeasurementTestControlTimeStamp }
			STATUS current
			DESCRIPTION 
				"Trap of Noise Measurement Test.
				sheAlarmTimeAndDate is filled with the same value as the set alarms(AC, DC, GK)
				triggering automeasure test, otherwise it should be filled with 0."
			::= { shePotsLineTestIltfTraps 6 }

		
		shePotsLineTestForeignDCVoltageTestTrap NOTIFICATION-TYPE
			OBJECTS { ifIndex, shePotsLineTestForeignDCVoltageTestvTip, shePotsLineTestForeignDCVoltageTestvRing, shePotsLineTestForeignDCVoltageTestvDiff, shePotsLineTestForeignDCVoltageTestPassed, 
				shePotsLineTestForeignDCVoltageTestTriggerSource, shePotsLineTestAlarm, sheAlarmTimeAndDate, shePotsLineTestForeignDCVoltageTestControlTimeStamp }
			STATUS current
			DESCRIPTION 
				"Trap of Foreign DC Voltage Test.
				sheAlarmTimeAndDate is filled with the same value as the set alarms(AC, DC, GK)
				triggering automeasure test, otherwise it should be filled with 0."
			::= { shePotsLineTestIltfTraps 7 }

		
		shePotsLineTestForeignACVoltageTestTrap NOTIFICATION-TYPE
			OBJECTS { ifIndex, shePotsLineTestForeignACVoltageTestvTip, shePotsLineTestForeignACVoltageTestvRing, shePotsLineTestForeignACVoltageTestvDiff, shePotsLineTestForeignACVoltageTestTriggerSource, 
				shePotsLineTestAlarm, sheAlarmTimeAndDate, shePotsLineTestForeignACVoltageTestControlTimeStamp }
			STATUS current
			DESCRIPTION 
				"Trap of Foreign AC Voltage Test.
				sheAlarmTimeAndDate is filled with the same value as the set alarms(AC, DC, GK)
				triggering automeasure test, otherwise it should be filled with 0."
			::= { shePotsLineTestIltfTraps 8 }

		
		shePotsLineTestDcLoopResistanceTestTrap NOTIFICATION-TYPE
			OBJECTS { ifIndex, shePotsLineTestDcLoopResistanceTestrLoop, shePotsLineTestDcLoopResistanceTestiLg, shePotsLineTestDcLoopResistanceTestiLg2, shePotsLineTestDcLoopResistanceTestvoltageSaturation, 
				shePotsLineTestDcLoopResistanceTestdegradedByCmc, shePotsLineTestDcLoopResistanceTestTriggerSource, shePotsLineTestAlarm, sheAlarmTimeAndDate, shePotsLineTestDcLoopResistanceTestControlTimeStamp
				 }
			STATUS current
			DESCRIPTION 
				"Trap of DC Loop Resistence
				However only rLoop should be shown to users.
				sheAlarmTimeAndDate is filled with the same value as the set alarms(AC, DC, GK)
				triggering automeasure test, otherwise it should be filled with 0."
			::= { shePotsLineTestIltfTraps 9 }

		
		shePotsLineTest3ElementInsulationResistanceTestTrap NOTIFICATION-TYPE
			OBJECTS { ifIndex, shePotsLineTest3ElementInsulationResistanceTestrtg, shePotsLineTest3ElementInsulationResistanceTestrrg, shePotsLineTest3ElementInsulationResistanceTestrtr, shePotsLineTest3ElementInsulationResistanceTestrGnd, 
				shePotsLineTest3ElementInsulationResistanceTestvTip, shePotsLineTest3ElementInsulationResistanceTestvRing, shePotsLineTest3ElementInsulationResistanceTestiTip, shePotsLineTest3ElementInsulationResistanceTestiRing, shePotsLineTest3ElementInsulationResistanceTestTriggerSource, 
				shePotsLineTestAlarm, sheAlarmTimeAndDate, shePotsLineTest3ElementInsulationResTestControlTimeStamp }
			STATUS current
			DESCRIPTION 
				"Trap of Three-Element Insulation Resistance Test
				However only Rtg, Rrg and Rtr should be shown to users.
				sheAlarmTimeAndDate is filled with the same value as the set alarms(AC, DC, GK)
				triggering automeasure test, otherwise it should be filled with 0."
			::= { shePotsLineTestIltfTraps 10 }

		
--                       
		shePotsLineTest3ElementInsulationCapacitanceTestTrap NOTIFICATION-TYPE
			OBJECTS { ifIndex, shePotsLineTest3ElementInsulationCapacitanceTestctg, shePotsLineTest3ElemenInsulationtCapacitanceTestcrg, shePotsLineTest3ElementInsulationCapacitanceTestctr, shePotsLineTest3ElementInsulationCapacitanceTestztg, 
				shePotsLineTest3ElementInsulationCapacitanceTestzrg, shePotsLineTest3ElementInsulationCapacitanceTestztr, shePotsLineTest3ElementInsulationCapacitanceTestDegradedAccuracy, shePotsLineTest3ElementInsulationCapacitanceTestvtgAc, shePotsLineTest3ElementInsulationCapacitanceTestvrgAc, 
				shePotsLineTest3ElementInsulationCapacitanceTestTriggerSource, shePotsLineTestAlarm, sheAlarmTimeAndDate, shePotsLineTest3ElementInsulationCapacitanceTestControlTimeStamp }
			STATUS current
			DESCRIPTION 
				"Trap of Three-Element Capacitance Test
				However only ctg, crg and ctr should be shown to users.
				sheAlarmTimeAndDate is filled with the same value as the set alarms(AC, DC, GK)
				triggering automeasure test, otherwise it should be filled with 0.
				"
			::= { shePotsLineTestIltfTraps 11 }

		
		shePotsLineTestReceiverOffHookTestTrap NOTIFICATION-TYPE
			OBJECTS { ifIndex, shePotsLineTestReceiverOffHookTestrLoopOutOfRange, shePotsLineTestReceiverOffHookTestReceiverOffHook, shePotsLineTestReceiverOffHookTestTriggerSource, shePotsLineTestAlarm, 
				sheAlarmTimeAndDate, shePotsLineTestReceiverOffHookTestControlTimeStamp }
			STATUS current
			DESCRIPTION 
				"Trap of Receiver Off-Hook Test.
				sheAlarmTimeAndDate is filled with the same value as the set alarms(AC, DC, GK)
				triggering automeasure test, otherwise it should be filled with 0."
			::= { shePotsLineTestIltfTraps 12 }

		
		shePotsLineTestDistanceToOpenTestTrap NOTIFICATION-TYPE
			OBJECTS { ifIndex, shePotsLineTestDistanceToOpenTestDistanceToOpen, shePotsLineTestDistanceToOpenTestExcessiveLeakage, shePotsLineTestDistanceToOpenTestCapacitanceTestFailed, shePotsLineTestDistanceToOpenTestTriggerSource, 
				shePotsLineTestAlarm, sheAlarmTimeAndDate, shePotsLineTestDistanceToOpenTestControlTimeStamp }
			STATUS current
			DESCRIPTION 
				"Trap of Distance To Open Test
				However only distancetoopen should be shown to users.
				sheAlarmTimeAndDate is filled with the same value as the set alarms(AC, DC, GK)
				triggering automeasure test, otherwise it should be filled with 0."
			::= { shePotsLineTestIltfTraps 13 }

		
		shePotsLineTestRingerEquivalencyNumberTestTrap NOTIFICATION-TYPE
			OBJECTS { ifIndex, shePotsLineTestRingerEquivalencyNumberTestRen, shePotsLineTestRingerEquivalencyNumberTestTriggerSource, shePotsLineTestAlarm, sheAlarmTimeAndDate, 
				shePotsLineTestRingerEquivalencyNumberTestControlTimeStamp }
			STATUS current
			DESCRIPTION 
				"Trap of Ringer Equivalency Number Test.
				sheAlarmTimeAndDate is filled with the same value as the set alarms(AC, DC, GK)
				triggering automeasure test, otherwise it should be filled with 0."
			::= { shePotsLineTestIltfTraps 14 }

		
		shePotsLineTestDTMFandPulseDigitMeasurementTestTrap NOTIFICATION-TYPE
			OBJECTS { ifIndex, shePotsLineTestDTMFandPulseDigitMeasureTestkTestResult, shePotsLineTestDTMFandPulseDigitMeasureTestTimeout, shePotsLineTestDTMFandPulseDigitMeasureTestDisconnectDetected, shePotsLineTestDTMFandPulseDigitMeasureTestDigit, 
				shePotsLineTestDTMFandPulseDigitMeasureTestHookFlashOk, shePotsLineTestDTMFandPulseDigitMeasureTestFlash, shePotsLineTestDTMFandPulseDigitMeasureTestFreq0, shePotsLineTestDTMFandPulseDigitMeasureTestLevel0, shePotsLineTestDTMFandPulseDigitMeasureTestFreq1, 
				shePotsLineTestDTMFandPulseDigitMeasureTestLevel1, shePotsLineTestDTMFandPulseDigitMeasureTestFftSize, shePotsLineTestDTMFandPulseDigitMeasureTestMinBreak, shePotsLineTestDTMFandPulseDigitMeasureTestMaxBreak, shePotsLineTestDTMFandPulseDigitMeasureTestAvgBreak, 
				shePotsLineTestDTMFandPulseDigitMeasureTestPps, shePotsLineTestDTMFandPulseDigitMeasureTestTriggerSource, shePotsLineTestAlarm, sheAlarmTimeAndDate, shePotsLineTestDTMFandPulseDigitMeasureTestControlTimeStamp
				 }
			STATUS current
			DESCRIPTION 
				"Trap of DTMF and Pulse Digit Measurement Test.
				sheAlarmTimeAndDate is filled with the same value as the set alarms(AC, DC, GK)
				triggering automeasure test, otherwise it should be filled with 0."
			::= { shePotsLineTestIltfTraps 15 }

		
		shePotsLineTestToneGenerationTestTrap NOTIFICATION-TYPE
			OBJECTS { ifIndex, shePotsLineTestToneGenerationTestTriggerSource, shePotsLineTestAlarm, sheAlarmTimeAndDate, shePotsLineTestToneGenerationTestControlTimeStamp
				 }
			STATUS current
			DESCRIPTION 
				"Trap of Tone Generation Test.
				sheAlarmTimeAndDate is filled with the same value as the set alarms(AC, DC, GK)
				triggering automeasure test, otherwise it should be filled with 0."
			::= { shePotsLineTestIltfTraps 16 }

		
		shePotsLineTestReadLoopandBatteryConditionsTestTrap NOTIFICATION-TYPE
			OBJECTS { ifIndex, shePotsLineTestReadLoopandBatteryConditionsTestrLoop, shePotsLineTestReadLoopandBatteryConditionsTestiLg, shePotsLineTestReadLoopandBatteryConditionsTestiMt, shePotsLineTestReadLoopandBatteryConditionsTestvSab, 
				shePotsLineTestReadLoopandBatteryConditionsTestvHb, shePotsLineTestReadLoopandBatteryConditionsTestvLb, shePotsLineTestReadLoopandBatteryConditionsTestvPb, shePotsLineTestReadLoopandBatteryConditionsTestMspl, shePotsLineTestReadLoopandBatteryConditionsTestTriggerSource, 
				shePotsLineTestAlarm, sheAlarmTimeAndDate, shePotsLineTestReadLoopandBatteryConditionsTestControlTimeStamp }
			STATUS current
			DESCRIPTION 
				"Trap of Read Loop and Battery Conditions.
				sheAlarmTimeAndDate is filled with the same value as the set alarms(AC, DC, GK)
				triggering automeasure test, otherwise it should be filled with 0. "
			::= { shePotsLineTestIltfTraps 17 }

		
		shePotsLineTestMeteringSelfTestTrap NOTIFICATION-TYPE
			OBJECTS { ifIndex, shePotsLineTestMeteringSelfMeterTerm, shePotsLineTestMeteringSelfMeterTermCkt, shePotsLineTestMeteringSelfTestTestPassed, shePotsLineTestMeteringSelfTestTriggerSource, 
				shePotsLineTestAlarm, sheAlarmTimeAndDate, shePotsLineTestMeteringSelfTestControlTimeStamp }
			STATUS current
			DESCRIPTION 
				"Trap of Metering self-test
				However only TestPassed should be shown to users.
				sheAlarmTimeAndDate is filled with the same value as the set alarms(AC, DC, GK)
				triggering automeasure test, otherwise it should be filled with 0."
			::= { shePotsLineTestIltfTraps 18 }

		
		shePotsLineTestForeignACcurrentsTestTrap NOTIFICATION-TYPE
			OBJECTS { ifIndex, shePotsLineTestForeignACcurrentsTestiTip, shePotsLineTestForeignACcurrentsTestiRing, shePotsLineTestForeignACcurrentsTestTriggerSource, shePotsLineTestAlarm, 
				sheAlarmTimeAndDate, shePotsLineTestForeignACcurrentsTestControlTimeStamp }
			STATUS current
			DESCRIPTION 
				"Trap of Foreign AC currents Test.
				sheAlarmTimeAndDate is filled with the same value as the set alarms(AC, DC, GK)
				triggering automeasure test, otherwise it should be filled with 0."
			::= { shePotsLineTestIltfTraps 19 }

		
		shePotsLineTestHowlerTestTrap NOTIFICATION-TYPE
			OBJECTS { ifIndex, shePotsLineTestHowlerTestTriggerSource, shePotsLineTestHowlerTestTimeLimitExpired, shePotsLineTestAlarm, sheAlarmTimeAndDate, 
				shePotsLineTestHowlerTestControlTimeStamp }
			STATUS current
			DESCRIPTION 
				"Trap of Howler Test.
				sheAlarmTimeAndDate is filled with the same value as the set alarms(AC, DC, GK)
				triggering automeasure test, otherwise it should be filled with 0."
			::= { shePotsLineTestIltfTraps 20 }

		
		shePotsLineTestReversalTestTrap NOTIFICATION-TYPE
			OBJECTS { ifIndex, shePotsLineTestReversalTestTriggerSource, shePotsLineTestReversalTestpassed, shePotsLineTestAlarm, sheAlarmTimeAndDate, 
				shePotsLineTestReversalTestControlTimeStamp }
			STATUS current
			DESCRIPTION 
				"The Trap of Reversal test.
				sheAlarmTimeAndDate is filled with the same value as the set alarms(AC, DC, GK)
				triggering automeasure test, otherwise it should be filled with 0."
			::= { shePotsLineTestIltfTraps 21 }

		
		shePotsLineTestConfigurationTraps OBJECT IDENTIFIER ::= { shePotsLineTestNotificationGroup 3 }

		
		shePotsLineTestMibSwitchModified NOTIFICATION-TYPE
			OBJECTS { shePotsLineTestMibSwitchControlTimeStamp, shePotsLineTestMibSwitchControlSwitch }
			STATUS current
			DESCRIPTION 
				"Motify Mib Switch is set."
			::= { shePotsLineTestConfigurationTraps 1 }

		
		sheAutoMeasureTestListModified NOTIFICATION-TYPE
			OBJECTS { shePotsLineTestAutoMeasureTestListControlTimeStamp, shePotsLineTestAutoMeasureTestListControlAcTestList, shePotsLineTestAutoMeasureTestListControlDcTestList, shePotsLineTestAutoMeasureTestListControlGkTestList, shePotsLineTestAutoMeasureControlAlarmTimeRange
				 }
			STATUS current
			DESCRIPTION 
				"Notify AutoMeasure test lists have been set."
			::= { shePotsLineTestConfigurationTraps 2 }

		
		sheAutoMeasureSwitchModified NOTIFICATION-TYPE
			OBJECTS { shePotsLineTestAutoMeasureControlIndex, shePotsLineTestAutoMeasureControlTimeStamp, shePotsLineTestAutoMeasureControlSwitch }
			STATUS current
			DESCRIPTION 
				"Notify Aotumeasure test switch is set."
			::= { shePotsLineTestConfigurationTraps 3 }

		
		shePatThresholdsModified NOTIFICATION-TYPE
			OBJECTS { shePotsLineTestPatThControlTimeStamp, shePotsLineTestPatThControlNoiseThreshold, shePotsLineTestPatThControl3EleResistancertgThreshold, shePotsLineTestPatThControl3EleResistancettgThreshold, shePotsLineTestPatThControl3EleResistancertrThreshold, 
				shePotsLineTestPatThControl3EleCapacitancectgThreshold, shePotsLineTestPatThControl3EleCapacitancecrgThreshold, shePotsLineTestPatThControl3EleCapacitancectrThreshold, shePotsLineTestPatThControlDcFeedimtHighBatNormalFeedThreshold, shePotsLineTestPatThControlDcFeedimtHighBatReverseFeedThreshold, 
				shePotsLineTestPatThControlDcFeedimtLowBatNormalFeedThreshold, shePotsLineTestPatControlStartTime }
			STATUS current
			DESCRIPTION 
				"Notify PAT thresholds are set."
			::= { shePotsLineTestConfigurationTraps 4 }

		
		shePatSwitchModified NOTIFICATION-TYPE
			OBJECTS { shePotsLineTestPatControlIndex, shePotsLineTestPatControlTimeStamp, shePotsLineTestPatControlSwitch, shePotsLineTestPatControlPollingTime }
			STATUS current
			DESCRIPTION 
				"Notify PAT switch is set."
			::= { shePotsLineTestConfigurationTraps 5 }

		
		sheDeployTestListModified NOTIFICATION-TYPE
			OBJECTS { shePotsLineTestDeployTestListControlTimeStamp, shePotsLineTestDeployTestListControlDeployTestList }
			STATUS current
			DESCRIPTION 
				"Notify Deploy test list is set."
			::= { shePotsLineTestConfigurationTraps 6 }

		
		sheDeploySwitchModified NOTIFICATION-TYPE
			OBJECTS { shePotsLineTestDeployTestControlIndex, shePotsLineTestDeployTestControlTimeStamp, shePotsLineTestCalibrationTestControlSwitch }
			STATUS current
			DESCRIPTION 
				"Notify Deploy test switch is set."
			::= { shePotsLineTestConfigurationTraps 7 }

		
		shePotsLineTestCompliance MODULE-COMPLIANCE
			STATUS current
			DESCRIPTION 
				"Description."
			MODULE -- this module
				MANDATORY-GROUPS { shePotsLineTestConformanceGroup, shePotsLineTestControlConformanceGroup, shePotsLineTestNotificationConformanceGroup }
			::= { shePotsCompliances 10 }

		
		shePotsLineTestConformanceGroup OBJECT-GROUP
			OBJECTS { shePotsLineTestMibSwitch, shePotsLineTestAlarmID, shePotsLineTestAlarm, shePotsLineTestAutoMeasureTestListAcTestList, shePotsLineTestAutoMeasureTestListDcTestList, 
				shePotsLineTestAutoMeasureTestListGkTestList, shePotsLineTestAutoMeasureTestListControlRequest, shePotsLineTestAutoMeasureTestListControlStatus, shePotsLineTestAutoMeasureTestListControlTimer, shePotsLineTestAutoMeasureTestListControlTimeStamp, 
				shePotsLineTestAutoMeasureTestListControlReqResult, shePotsLineTestAutoMeasureTestListControlAcTestList, shePotsLineTestAutoMeasureTestListControlDcTestList, shePotsLineTestAutoMeasureTestListControlGkTestList, shePotsLineTestAutoMeasureSwitch, 
				shePotsLineTestPatThresholdNoiseThreshold, shePotsLineTestPatThreshold3EleResistancertgThreshold, shePotsLineTestPatThreshold3EleResistancettgThreshold, shePotsLineTestPatThreshold3EleResistancertrThreshold, shePotsLineTestPatThreshold3EleCapacitancectgThreshold, 
				shePotsLineTestPatThreshold3EleCapacitancecrgThreshold, shePotsLineTestPatThreshold3EleCapacitancectrThreshold, shePotsLineTestPatThresholdDcFeedimtHighBatNormalFeedThreshold, shePotsLineTestPatThresholdDcFeedimtHighBatReverseFeedThreshold, shePotsLineTestPatThresholdDcFeedimtLowBatNormalFeedThreshold, 
				shePotsLineTestPatSwitch, shePotsLineTestPatPollingTime, shePotsLineTestPatStartTime, shePotsLineTestDeployTestList, shePotsLineTestDeployTestListControlRequest, 
				shePotsLineTestDeployTestListControlStatus, shePotsLineTestDeployTestListControlTimer, shePotsLineTestDeployTestListControlTimeStamp, shePotsLineTestDeployTestListControlReqResult, shePotsLineTestDeployTestListControlDeployTestList, 
				shePotsLineTestCalibrationTestSwitch, shePotsLineTestVptlOnOffHookSelfTestStatus, shePotsLineTestVptlOnOffHookSelfTestTriggerSource, shePotsLineTestDcFeedSelfTestImtHighBatNormalFeed, shePotsLineTestDcFeedSelfTestImtHighBatReverseFeed, 
				shePotsLineTestDcFeedSelfTestImtLowBatNormalFeed, shePotsLineTestDcFeedSelfTestImtBoostBatNormalFeed, shePotsLineTestDcFeedSelfTestRloadMsrd, shePotsLineTestDcFeedSelfTestvBat, shePotsLineTestDcFeedSelfTestvTr, 
				shePotsLineTestDcFeedSelfTestPassed, shePotsLineTestDcFeedSelfTestTriggerSource, shePotsLineTestRingingSelfTestOnOffHookChangeDetected, shePotsLineTestRingingSelfTestTestPassed, shePotsLineTestRingingSelfTestTriggerSource, 
				shePotsLineTestTransmissionSelfTestThlOpen, shePotsLineTestTransmissionSelfTestThlExpectedLL, shePotsLineTestTransmissionSelfTestThlExpectedUL, shePotsLineTestTransmissionSelfTestPassed, shePotsLineTestTransmissionSelfTestAbortedDueToOffHook, 
				shePotsLineTestTransmissionSelfTestTriggerSource, shePotsLineTestTransHybridLossTestEcho, shePotsLineTestTransHybridLossTestLoss, shePotsLineTestTransHybridLossTestTriggerSource, shePotsLineTestNoiseMeasurementTestNoise, 
				shePotsLineTestNoiseMeasurementTestTriggerSource, shePotsLineTestForeignDCVoltageTestPassed, shePotsLineTestForeignDCVoltageTestvTip, shePotsLineTestForeignDCVoltageTestvRing, shePotsLineTestForeignDCVoltageTestvDiff, 
				shePotsLineTestForeignDCVoltageTestTriggerSource, shePotsLineTestForeignACVoltageTestvTip, shePotsLineTestForeignACVoltageTestvRing, shePotsLineTestForeignACVoltageTestvDiff, shePotsLineTestForeignACVoltageTestTriggerSource, 
				shePotsLineTestDcLoopResistanceTestrLoop, shePotsLineTestDcLoopResistanceTestiLg, shePotsLineTestDcLoopResistanceTestiLg2, shePotsLineTestDcLoopResistanceTestvoltageSaturation, shePotsLineTestDcLoopResistanceTestdegradedByCmc, 
				shePotsLineTestDcLoopResistanceTestTriggerSource, shePotsLineTest3ElementInsulationResistanceTestrtg, shePotsLineTest3ElementInsulationResistanceTestrrg, shePotsLineTest3ElementInsulationResistanceTestrtr, shePotsLineTest3ElementInsulationResistanceTestrGnd, 
				shePotsLineTest3ElementInsulationResistanceTestvTip, shePotsLineTest3ElementInsulationResistanceTestvRing, shePotsLineTest3ElementInsulationResistanceTestiTip, shePotsLineTest3ElementInsulationResistanceTestiRing, shePotsLineTest3ElementInsulationResistanceTestTriggerSource, 
				shePotsLineTest3ElementInsulationCapacitanceTestctg, shePotsLineTest3ElemenInsulationtCapacitanceTestcrg, shePotsLineTest3ElementInsulationCapacitanceTestctr, shePotsLineTest3ElementInsulationCapacitanceTestztg, shePotsLineTest3ElementInsulationCapacitanceTestzrg, 
				shePotsLineTest3ElementInsulationCapacitanceTestztr, shePotsLineTest3ElementInsulationCapacitanceTestDegradedAccuracy, shePotsLineTest3ElementInsulationCapacitanceTestvtgAc, shePotsLineTest3ElementInsulationCapacitanceTestvrgAc, shePotsLineTest3ElementInsulationCapacitanceTestTriggerSource, 
				shePotsLineTestReceiverOffHookTestReceiverOffHook, shePotsLineTestReceiverOffHookTestrLoopOutOfRange, shePotsLineTestReceiverOffHookTestTriggerSource, shePotsLineTestDistanceToOpenTestDistanceToOpen, shePotsLineTestDistanceToOpenTestExcessiveLeakage, 
				shePotsLineTestDistanceToOpenTestCapacitanceTestFailed, shePotsLineTestDistanceToOpenTestTriggerSource, shePotsLineTestRingerEquivalencyNumberTestRen, shePotsLineTestRingerEquivalencyNumberTestTriggerSource, shePotsLineTestDTMFandPulseDigitMeasureTestTimeout, 
				shePotsLineTestDTMFandPulseDigitMeasureTestDisconnectDetected, shePotsLineTestDTMFandPulseDigitMeasureTestkTestResult, shePotsLineTestDTMFandPulseDigitMeasureTestDigit, shePotsLineTestDTMFandPulseDigitMeasureTestHookFlashOk, shePotsLineTestDTMFandPulseDigitMeasureTestFlash, 
				shePotsLineTestDTMFandPulseDigitMeasureTestFreq0, shePotsLineTestDTMFandPulseDigitMeasureTestLevel0, shePotsLineTestDTMFandPulseDigitMeasureTestFreq1, shePotsLineTestDTMFandPulseDigitMeasureTestLevel1, shePotsLineTestDTMFandPulseDigitMeasureTestFftSize, 
				shePotsLineTestDTMFandPulseDigitMeasureTestMinBreak, shePotsLineTestDTMFandPulseDigitMeasureTestMaxBreak, shePotsLineTestDTMFandPulseDigitMeasureTestAvgBreak, shePotsLineTestDTMFandPulseDigitMeasureTestPps, shePotsLineTestDTMFandPulseDigitMeasureTestTriggerSource, 
				shePotsLineTestToneGenerationTestTriggerSource, shePotsLineTestReadLoopandBatteryConditionsTestrLoop, shePotsLineTestReadLoopandBatteryConditionsTestiLg, shePotsLineTestReadLoopandBatteryConditionsTestiMt, shePotsLineTestReadLoopandBatteryConditionsTestvSab, 
				shePotsLineTestReadLoopandBatteryConditionsTestvHb, shePotsLineTestReadLoopandBatteryConditionsTestvLb, shePotsLineTestReadLoopandBatteryConditionsTestvPb, shePotsLineTestReadLoopandBatteryConditionsTestMspl, shePotsLineTestReadLoopandBatteryConditionsTestTriggerSource, 
				shePotsLineTestMeteringSelfMeterTerm, shePotsLineTestMeteringSelfMeterTermCkt, shePotsLineTestMeteringSelfTestTriggerSource, shePotsLineTestForeignACcurrentsTestTriggerSource, shePotsLineTestHowlerTestTriggerSource, 
				shePotsLineTestReversalTestTriggerSource, shePotsLineTestForeignACcurrentsTestiTip, shePotsLineTestForeignACcurrentsTestiRing, shePotsLineTestHowlerTestTimeLimitExpired, shePotsLineTestAutoMeasureAlarmTimeRange, 
				shePotsLineTestReversalTestpassed, shePotsLineTestMeteringSelfTestTestPassed, shePotsLineTestTransmissionSelfTestThlRload }
			STATUS current
			DESCRIPTION 
				"Description."
			::= { shePotsGroups 10 }

		
		shePotsLineTestControlConformanceGroup OBJECT-GROUP
			OBJECTS { shePotsLineTestMibSwitchControlRequest, shePotsLineTestMibSwitchControlStatus, shePotsLineTestMibSwitchControlTimer, shePotsLineTestMibSwitchControlTimeStamp, shePotsLineTestMibSwitchControlControlReqResult, 
				shePotsLineTestMibSwitchControlSwitch, shePotsLineTestAutoMeasureTestListControlRequest, shePotsLineTestAutoMeasureTestListControlStatus, shePotsLineTestAutoMeasureTestListControlTimer, shePotsLineTestAutoMeasureTestListControlTimeStamp, 
				shePotsLineTestAutoMeasureTestListControlReqResult, shePotsLineTestAutoMeasureTestListControlAcTestList, shePotsLineTestAutoMeasureTestListControlDcTestList, shePotsLineTestAutoMeasureTestListControlGkTestList, shePotsLineTestAutoMeasureControlRequest, 
				shePotsLineTestAutoMeasureControlIndex, shePotsLineTestAutoMeasureControlStatus, shePotsLineTestAutoMeasureControlTimer, shePotsLineTestAutoMeasureControlTimeStamp, shePotsLineTestAutoMeasureControlReqResult, 
				shePotsLineTestAutoMeasureControlSwitch, shePotsLineTestPatThControlRequest, shePotsLineTestPatThControlStatus, shePotsLineTestPatThControlTimer, shePotsLineTestPatThControlTimeStamp, 
				shePotsLineTestPatThControlReqResult, shePotsLineTestPatThControlNoiseThreshold, shePotsLineTestPatThControl3EleResistancertgThreshold, shePotsLineTestPatThControl3EleResistancettgThreshold, shePotsLineTestPatThControl3EleResistancertrThreshold, 
				shePotsLineTestPatThControl3EleCapacitancectgThreshold, shePotsLineTestPatThControl3EleCapacitancecrgThreshold, shePotsLineTestPatThControl3EleCapacitancectrThreshold, shePotsLineTestPatThControlDcFeedimtHighBatNormalFeedThreshold, shePotsLineTestPatThControlDcFeedimtHighBatReverseFeedThreshold, 
				shePotsLineTestPatThControlDcFeedimtLowBatNormalFeedThreshold, shePotsLineTestPatControlRequest, shePotsLineTestPatControlIndex, shePotsLineTestPatControlStatus, shePotsLineTestPatControlTimer, 
				shePotsLineTestPatControlTimeStamp, shePotsLineTestPatControlReqResult, shePotsLineTestPatControlSwitch, shePotsLineTestPatControlPollingTime, shePotsLineTestPatControlStartTime, 
				shePotsLineTestDeployTestListControlRequest, shePotsLineTestDeployTestListControlStatus, shePotsLineTestDeployTestListControlTimer, shePotsLineTestDeployTestListControlTimeStamp, shePotsLineTestDeployTestListControlReqResult, 
				shePotsLineTestDeployTestListControlDeployTestList, shePotsLineTestDeployTestControlRequest, shePotsLineTestDeployTestControlIndex, shePotsLineTestDeployTestControlStatus, shePotsLineTestDeployTestControlTimer, 
				shePotsLineTestDeployTestControlTimeStamp, shePotsLineTestDeployTestControlReqResult, shePotsLineTestCalibrationTestControlSwitch, shePotsLineTestVptlTidOnOffHookSelfTestControlRequest, shePotsLineTestVptlTidOnOffHookSelfTestControlIndex, 
				shePotsLineTestVptlTidOnOffHookSelfTestControlStatus, shePotsLineTestVptlTidOnOffHookSelfTestControlTimer, shePotsLineTestVptlTidOnOffHookSelfTestControlTimeStamp, shePotsLineTestVptlTidOnOffHookSelfTestControlReqResult, shePotsLineTestLineTestDcFeedSelfTestControlRequest, 
				shePotsLineTestLineTestDcFeedSelfTestControlIndex, shePotsLineTestLineTestDcFeedSelfTestControlStatus, shePotsLineTestLineTestDcFeedSelfTestControlTimer, shePotsLineTestLineTestDcFeedSelfTestControlTimeStamp, shePotsLineTestLineTestDcFeedSelfTestControlReqResult, 
				shePotsLineTestRingingSelfTestControlRequest, shePotsLineTestRingingSelfTestControlIndex, shePotsLineTestRingingSelfTestControlStatus, shePotsLineTestRingingSelfTestControlTimer, shePotsLineTestRingingSelfTestControlTimeStamp, 
				shePotsLineTestRingingSelfTestControlReqResult, shePotsLineTestTransmissionSelfTestControlRequest, shePotsLineTestTransmissionSelfTestControlIndex, shePotsLineTestTransmissionSelfTestControlStatus, shePotsLineTestTransmissionSelfTestControlTimer, 
				shePotsLineTestTransmissionSelfTestControlTimeStamp, shePotsLineTestTransmissionSelfTestControlReqResult, shePotsLineTestTransHybridLossTestControlRequest, shePotsLineTestTransHybridLossTestControlIndex, shePotsLineTestTransHybridLossTestControlStatus, 
				shePotsLineTestTransHybridLossTestControlTimer, shePotsLineTestTransHybridLossTestControlTimeStamp, shePotsLineTestTransHybridLossTestControlReqResult, shePotsLineTestTransHybridLossTestControlTestFreq, shePotsLineTestTransHybridLossTestControlTestLevel, 
				shePotsLineTestNoiseMeasurementTestControlRequest, shePotsLineTestNoiseMeasurementTestControlIndex, shePotsLineTestNoiseMeasurementTestControlStatus, shePotsLineTestNoiseMeasurementTestControlTimer, shePotsLineTestNoiseMeasurementTestControlTimeStamp, 
				shePotsLineTestNoiseMeasurementTestControlReqResult, shePotsLineTestNoiseMeasurementTestControlVpTestFilter, shePotsLineTestForeignDCVoltageTestControlRequest, shePotsLineTestForeignDCVoltageTestControlIndex, shePotsLineTestForeignDCVoltageTestControlStatus, 
				shePotsLineTestForeignDCVoltageTestControlTimer, shePotsLineTestForeignDCVoltageTestControlTimeStamp, shePotsLineTestForeignDCVoltageTestControlReqResult, shePotsLineTestForeignACVoltageTestControlRequest, shePotsLineTestForeignACVoltageTestControlIndex, 
				shePotsLineTestForeignACVoltageTestControlStatus, shePotsLineTestForeignACVoltageTestControlTimer, shePotsLineTestForeignACVoltageTestControlReqResult, shePotsLineTestDcLoopResistanceSelfTestControlRequest, shePotsLineTestDcLoopResistanceTestControlIndex, 
				shePotsLineTestDcLoopResistanceTestControlStatus, shePotsLineTestDcLoopResistanceTestControlTimer, shePotsLineTestDcLoopResistanceTestControlTimeStamp, shePotsLineTestDcLoopResistanceTestControlReqResult, shePotsLineTest3ElementInsulationResTestControlRequest, 
				shePotsLineTest3ElementInsulationResTestControlIndex, shePotsLineTest3ElementInsulationResTestControlStatus, shePotsLineTest3ElementInsulationResTestControlTimer, shePotsLineTest3ElementInsulationResTestControlTimeStamp, shePotsLineTest3ElementInsulationResTestControlReqResult, 
				shePotsLineTest3ElementInsulationResTestControlHighImpedanceTest, shePotsLineTest3ElementInsulationResTestControlMeasureForeignVI, shePotsLineTest3ElementInsulationCapacitanceTestControlRequest, shePotsLineTest3ElementInsulationCapacitanceTestControlIndex, shePotsLineTest3ElementInsulationCapacitanceTestControlStatus, 
				shePotsLineTest3ElementInsulationCapacitanceTesControlTimer, shePotsLineTest3ElementInsulationCapacitanceTestControlTimeStamp, shePotsLineTest3ElementInsulationCapacitanceTestControlReqResult, shePotsLineTest3ElementInsulationCapacitanceTestControlvDiffMax, shePotsLineTestReceiverOffHookTestControlRequest, 
				shePotsLineTestReceiverOffHookTestControlIndex, shePotsLineTestReceiverOffHookTestControlStatus, shePotsLineTestReceiverOffHookTestControlTimer, shePotsLineTestReceiverOffHookTestControlTimeStamp, shePotsLineTestReceiverOffHookTestControlReqResult, 
				shePotsLineTestDistanceToOpenTestControlRequest, shePotsLineTestDistanceToOpenTestControlIndex, shePotsLineTestDistanceToOpenTestControlStatus, shePotsLineTestDistanceToOpenTestControlTimer, shePotsLineTestDistanceToOpenTestControlTimeStamp, 
				shePotsLineTestDistanceToOpenTestControlReqResult, shePotsLineTestRingerEquivalencyNumberTestControlRequest, shePotsLineTestRingerEquivalencyNumberTestControlIndex, shePotsLineTestRingerEquivalencyNumberTestControlStatus, shePotsLineTestRingerEquivalencyNumberTestControlTimer, 
				shePotsLineTestRingerEquivalencyNumberTestControlTimeStamp, shePotsLineTestRingerEquivalencyNumberTestControlReqResult, shePotsLineTestRingerEquivalencyNumberTestControlRentestType, shePotsLineTestDTMFandPulseDigitMeasureTestControlRequest, shePotsLineTestDTMFandPulseDigitMeasureTestControlIndex, 
				shePotsLineTestDTMFandPulseDigitMeasureTestControlStatus, shePotsLineTestDTMFandPulseDigitMeasureTestControlTimer, shePotsLineTestDTMFandPulseDigitMeasureTestControlTimeStamp, shePotsLineTestDTMFandPulseDigitMeasureTestControlReqResult, shePotsLineTestDTMFandPulseDigitMeasureTestControlTestType, 
				shePotsLineTestToneGenerationTestControlRequest, shePotsLineTestToneGenerationTestControlIndex, shePotsLineTestToneGenerationTestControlStatus, shePotsLineTestToneGenerationTestControlTimer, shePotsLineTestToneGenerationTestControlTimeStamp, 
				shePotsLineTestToneGenerationTestControlReqResult, shePotsLineTestToneGenerationTestControlTestFreq0, shePotsLineTestToneGenerationTestControlTestLevel0, shePotsLineTestToneGenerationTestControlTestFreq1, shePotsLineTestToneGenerationTestControlTestLevel1, 
				shePotsLineTestToneGenerationTestControlTestFreq2, shePotsLineTestToneGenerationTestControlTestLevel2, shePotsLineTestToneGenerationTestControlTestFreq3, shePotsLineTestToneGenerationTestControlTestLevel3, shePotsLineTestToneGenerationTestControlDuration, 
				shePotsLineTestReadLoopandBatteryConditionsTestControlRequest, shePotsLineTestReadLoopandBatteryConditionsTestControlIndex, shePotsLineTestReadLoopandBatteryConditionsTestControlStatus, shePotsLineTestReadLoopandBatteryConditionsTestControlTimer, shePotsLineTestReadLoopandBatteryConditionsTestControlTimeStamp, 
				shePotsLineTestReadLoopandBatteryConditionsTestControlReqResult, shePotsLineTestMeteringSelfTestControlRequest, shePotsLineTestMeteringSelfTestControlIndex, shePotsLineTestMeteringSelfTestControlStatus, shePotsLineTestMeteringSelfTestControlTimer, 
				shePotsLineTestMeteringSelfTestControlTimeStamp, shePotsLineTestMeteringSelfTestControlReqResult, shePotsLineTestForeignACcurrentsTestControlRequest, shePotsLineTestForeignACcurrentsTestControlIndex, shePotsLineTestForeignACcurrentsTestControlStatus, 
				shePotsLineTestForeignACcurrentsTestControlTimer, shePotsLineTestForeignACcurrentsTestControlTimeStamp, shePotsLineTestForeignACcurrentsTestControlReqResult, shePotsLineTestHowlerTestControlRequest, shePotsLineTestHowlerTestControlIndex, 
				shePotsLineTestHowlerTestControlStatus, shePotsLineTestHowlerTestControlTimer, shePotsLineTestHowlerTestControlTimeStamp, shePotsLineTestHowlerTestControlReqResult, shePotsLineTestHowlerTestControlToneType, 
				shePotsLineTestReversalTestControlRequest, shePotsLineTestReversalTestControlIndex, shePotsLineTestReversalTestControlStatus, shePotsLineTestReversalTestControlTimer, shePotsLineTestReversalTestControlTimeStamp, 
				shePotsLineTestAutoMeasureControlAlarmTimeRange, shePotsLineTestReversalTestControlReqResult, shePotsLineTestForeignACVoltageTestControlTimeStamp }
			STATUS current
			DESCRIPTION 
				"Description."
			::= { shePotsGroups 11 }

		
		shePotsLineTestNotificationConformanceGroup NOTIFICATION-GROUP
			NOTIFICATIONS { shePotsLineTestpat3EleResFltAlm, shePotsLineTestpat3EleCapFltAlm, shePotsLineTestpatNoiseFltAlm, shePotsLineTestpatDcFeedFltAlm, shePotsLineTestAcAlarms, 
				shePotsLineTestDcAlarms, shePotsLineTestGkAlarms, shePotsLineTestThermAlalarms, shePotsLineTestVptlTidOnOffHookSelfTestTrap, shePotsLineTestDCFeedSelfTestTrap, 
				shePotsLineTestRingingSelfTestTrap, shePotsLineTestTransmitionSelfTestTrap, shePotsLineTestTransHybridLossTestTrap, shePotsLineTestNoiseMeasurementTestTrap, shePotsLineTestForeignDCVoltageTestTrap, 
				shePotsLineTestForeignACVoltageTestTrap, shePotsLineTestDcLoopResistanceTestTrap, shePotsLineTest3ElementInsulationResistanceTestTrap, shePotsLineTest3ElementInsulationCapacitanceTestTrap, shePotsLineTestReceiverOffHookTestTrap, 
				shePotsLineTestDistanceToOpenTestTrap, shePotsLineTestRingerEquivalencyNumberTestTrap, shePotsLineTestDTMFandPulseDigitMeasurementTestTrap, shePotsLineTestToneGenerationTestTrap, shePotsLineTestReadLoopandBatteryConditionsTestTrap, 
				shePotsLineTestMeteringSelfTestTrap, shePotsLineTestForeignACcurrentsTestTrap, shePotsLineTestHowlerTestTrap, shePotsLineTestReversalTestTrap, shePotsLineTestMibSwitchModified, 
				sheAutoMeasureSwitchModified, shePatThresholdsModified, shePatSwitchModified, sheDeployTestListModified, sheDeploySwitchModified, 
				sheAutoMeasureTestListModified }
			STATUS current
			DESCRIPTION 
				"Description."
			::= { shePotsGroups 12 }

		
	
	END

--
-- she-pots-linetest-mib.mib
--
