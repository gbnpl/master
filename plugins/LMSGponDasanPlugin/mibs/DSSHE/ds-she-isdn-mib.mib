--
-- she-isdn-mib.mib
-- MIB generated by MG-SOFT Visual MIB Builder Version 6.0  Build 88
-- Friday, February 22, 2008 at 08:37:39
--

	DS-SHE-ISDN-MIB DEFINITIONS ::= BEGIN
 
		IMPORTS
			she			
				FROM AN-MIB
			dsShe
				FROM DASAN-SMI							
			ifIndex, InterfaceIndex			
				FROM IF-MIB			
			sheAlarmTimeAndDate, sheAlarmReportingSource, sheAlarmReportingSourceType, sheAlarmSeverity			
				FROM DS-SHE-ALARMING-MIB			
			SheControlStatusType			
				FROM DS-SHE-TC-MIB			
			OBJECT-GROUP, MODULE-COMPLIANCE, NOTIFICATION-GROUP			
				FROM SNMPv2-CONF			
			IpAddress, Integer32, Unsigned32, Gauge32, Counter32, 
			Counter64, OBJECT-TYPE, MODULE-IDENTITY, NOTIFICATION-TYPE			
				FROM SNMPv2-SMI			
			TimeStamp, TruthValue, DisplayString			
				FROM SNMPv2-TC;
	
	
		sheIsdnMib MODULE-IDENTITY 
			LAST-UPDATED "200802221205Z"		-- February 22, 2008 at 12:05 GMT
			ORGANIZATION 
				"Nokia Siemens Networks"
			CONTACT-INFO 
				"Wang Yingxia
				Com CD/FN RDC BJ
				yingxia.wang@siemens.com
				+0086 58671387
				    "
			DESCRIPTION 
				"This module defines the management information base (MIB) for managing
				of the ISDN user ports of the network element. "
			REVISION "200801301032Z"		-- January 30, 2008 at 10:32 GMT
			DESCRIPTION 
				"Initial version."
			REVISION "200802220936Z"		-- February 22, 2008 at 09:36 GMT
			DESCRIPTION 
				"Updated version from Mr. Wang YingXia.
				"
			::= { dsShe 25 }

		
	
--
-- Type definitions
--
	
		SheIsdnPortBasicType ::= INTEGER
			{
			isdns(75),
			isdnu(76)
			}

		SheIsdnPortLineTopo ::= INTEGER
			{
			pointToPoint(0),
			pointToMultipoint(1)
			}

		SheIsdnPortIfMode ::= INTEGER
			{
			te(1),
			nt(2)
			}

		SheIsdnActiveType ::= INTEGER
			{
			deactive(0),
			active(1)
			}

		SheIsdnPermanentType ::= INTEGER
			{
			nonPermanent(0),
			permanent(1)
			}

		SheIsdnPortPowerFeedStatus ::= INTEGER
			{
			off(0),
			openCircuit(1),
			overload(2),
			okay(3)
			}

		SheIsdnResultType ::= INTEGER
			{
			ok(0),
			failed(1),
			performing(2)
			}

		SheIsdnControlRequestType ::= INTEGER
			{
			modifyisdnBasicRateLineTopology(1),
			setIsdnLayer1Permanent(2),
			setIsdnLayer2Permanent(3),
			resetIsdnPort(4),
			modifyIsdnPowerFeed(5),
			modifyIsdnL2out(6),
			setIsdnPortQuickTestStart(7),
			setIsdnLineTestMode(8),
			setIsdnOutWardTest(9),
			setIsdnPMBSIID(10),
			setIsdnPMBSConnect(11),
			setIsdnPMBSSourceIp(12),
			setIsdnPMBSSourcePort(13),
			createPHWhiteList(14),
			deletePHWhiteList(15),
			createIsdnPMThreshold(16),
			modifyIsdnPMThreshold(17),
			deleteIsdnPMThreshold(18),
			setIsdnPMActive(19),
			setIsdnPmGlobalActive(20),
			setIsdnPortPMThresholdCheck(21),
			setIsdnThresProfileIndex(22),
			setIsdnPmAlarmSev(23),
			setIsdnber10e3Threshold(24),
			setIsdnber10e6Threshold(25),
			setLineTestTrapEnable(26),
			setQuickCheckTrapEnable(27)
			}

		SheIsdnControlReqResultType ::= INTEGER
			{
			noRequest(1),
			portIsActive(4),
			portIsNotIsdn(5),
			portIsNotInTeststate(6),
			duplicatedName(7),
			duplicatedIp(8),
			duplicatedIndex(9),
			tooLongName(10),
			indexNotExist(11),
			cannotDeldefProfile(12),
			cannotModdefProfileName(13),
			profileIsInUse(14),
			profileNotExist(15),
			profileIdUsed(16),
			profileIsFull(17),
			linetestOnGoing(18),
			linetestOnGoingquickcheckOnGoing(19),
			resetPortOnGoing(20),
			resetPortOnGoinguserOnline(21),
			iidNotConfig(22),
			pmbsIsEnabled(23),
			iuaServerIsActive(24),
			comExecStarted(30),
			paramFaulty(31),
			requestBusy(32),
			setDataFailed(34),
			aswTimeout(35),
			commandFailed(36),
			commandSucceeded(37)
			}

		SheIsdnSwitch ::= INTEGER
			{
			off(0),
			on(1)
			}

		SheIsdnLapdOperStatus ::= INTEGER
			{
			inactive(1),
			l1Active(2),
			l2Active(3)
			}

		SheIsdnBearerOperStatus ::= INTEGER
			{
			released(1),
			disconnect(2),
			connect(3)
			}

		SheIsdnPortLineTestMode ::= INTEGER
			{
			internalLoop(0),
			ntLoop(1),
			forcedActivatin(2)
			}

		SheIsdnEnableStatus ::= INTEGER
			{
			disable(0),
			enable(1)
			}

		SheIsdnPHStatus ::= INTEGER
			{
			inactive(0),
			active(1),
			down(2)
			}

-- Values 3..17 represent the error codes A..O from ETS 300 125, appendix II, Table II-1/Q.921. 
		SheIsdnLayer2EventsType ::= INTEGER
			{
			errorCodeA(3),
			errorCodeB(4),
			errorCodeC(5),
			errorCodeD(6),
			errorCodeE(7),
			errorCodeF(8),
			errorCodeG(9),
			errorCodeH(10),
			errorCodeI(11),
			errorCodeJ(12),
			errorCodeK(13),
			errorCodeL(14),
			errorCodeM(15),
			errorCodeN(16),
			errorCodeO(17)
			}

	
	
--
-- Node definitions
--
	
		sheIsdnPortConfigObjects OBJECT IDENTIFIER ::= { sheIsdnMib 1 }

		
		sheIsdnPortConfigTable OBJECT-TYPE
			SYNTAX SEQUENCE OF SheIsdnPortConfigEntry
			MAX-ACCESS not-accessible
			STATUS current
			DESCRIPTION
				"the configuration information about the ISDN port."
			::= { sheIsdnPortConfigObjects 1 }

		
		sheIsdnPortConfigEntry OBJECT-TYPE
			SYNTAX SheIsdnPortConfigEntry
			MAX-ACCESS not-accessible
			STATUS current
			DESCRIPTION
				"An entry in the sheIsdnPortConfigTable."
			INDEX { ifIndex }
			::= { sheIsdnPortConfigTable 1 }

		
		SheIsdnPortConfigEntry ::=
			SEQUENCE { 
				sheIsdnPortConfigBasicRateIfType
					SheIsdnPortBasicType,
				sheIsdnPortConfigBasicRateLineTopology
					SheIsdnPortLineTopo,
				sheIsdnPortConfigBasicRateIfMode
					SheIsdnPortIfMode,
				sheIsdnPortConfigBasicRateSignalMode
					SheIsdnActiveType,
				sheIsdnPortConfigL1PermanentActive
					SheIsdnPermanentType,
				sheIsdnPortConfigPowerFeedingStatus
					SheIsdnPortPowerFeedStatus,
				sheIsdnPortConfigL2PermanentActive
					SheIsdnPermanentType,
				sheIsdnPortConfigL2Out
					Unsigned32,
				sheIsdnPortConfigResetResult
					SheIsdnResultType
			 }

		sheIsdnPortConfigBasicRateIfType OBJECT-TYPE
			SYNTAX SheIsdnPortBasicType
			MAX-ACCESS read-only
			STATUS current
			DESCRIPTION
				"The physical interface type. For 'S/T' interfaces,
				also called 'Four-wire Basic Access Interface',
				the value of this object is isdns(75).
				For 'U' interfaces, also called 'Two-wire Basic
				Access Interface', the value of this object is isdnu(76).
				on MSAN, it must be isdnu"
			DEFVAL { isdnu }
			::= { sheIsdnPortConfigEntry 1 }

		
		sheIsdnPortConfigBasicRateLineTopology OBJECT-TYPE
			SYNTAX SheIsdnPortLineTopo
			MAX-ACCESS read-only
			STATUS current
			DESCRIPTION
				"The line topology to be used for this interface.
				Note that setting isdnBasicRateIfType to isdns(75)
				does not necessarily mean a line topology of	
				point-to-multipoint."
			DEFVAL { pointToMultipoint }
			::= { sheIsdnPortConfigEntry 2 }

		
		sheIsdnPortConfigBasicRateIfMode OBJECT-TYPE
			SYNTAX SheIsdnPortIfMode
			MAX-ACCESS read-only
			STATUS current
			DESCRIPTION
				"The physical interface mode. For TE mode, the value
				of this object is te(1). For NT mode, the value
				of this object is nt(2)."
			DEFVAL { nt }
			::= { sheIsdnPortConfigEntry 3 }

		
		sheIsdnPortConfigBasicRateSignalMode OBJECT-TYPE
			SYNTAX SheIsdnActiveType
			MAX-ACCESS read-only
			STATUS current
			DESCRIPTION
				"The signaling channel operational mode for this interface.
				If active there is a signaling channel on this
				interface. If deactive a signaling channel is
				not available."
			::= { sheIsdnPortConfigEntry 4 }

		
		sheIsdnPortConfigL1PermanentActive OBJECT-TYPE
			SYNTAX SheIsdnPermanentType
			MAX-ACCESS read-only
			STATUS current
			DESCRIPTION
				"Status of ISDN port Layer-1, If 'permanent layer1' is configured for a specific port, the deactivation Layer-1
				primitive will be discarded."
			DEFVAL { 0 }
			::= { sheIsdnPortConfigEntry 5 }

		
		sheIsdnPortConfigPowerFeedingStatus OBJECT-TYPE
			SYNTAX SheIsdnPortPowerFeedStatus
			MAX-ACCESS read-only
			STATUS current
			DESCRIPTION
				"Actual power status of the port."
			DEFVAL { off }
			::= { sheIsdnPortConfigEntry 6 }

		
		sheIsdnPortConfigL2PermanentActive OBJECT-TYPE
			SYNTAX SheIsdnPermanentType
			MAX-ACCESS read-only
			STATUS current
			DESCRIPTION
				"Status of the ISDN port Layer-2."
			DEFVAL { 0 }
			::= { sheIsdnPortConfigEntry 7 }

		
		sheIsdnPortConfigL2Out OBJECT-TYPE
			SYNTAX Unsigned32
			UNITS "seconds"
			MAX-ACCESS read-only
			STATUS current
			DESCRIPTION
				"Timer describing the time between two L2 reestablishment request, 
				if in L2 permanent mode."
			DEFVAL { 0 }
			::= { sheIsdnPortConfigEntry 8 }

		
		sheIsdnPortConfigResetResult OBJECT-TYPE
			SYNTAX SheIsdnResultType
			MAX-ACCESS read-only
			STATUS current
			DESCRIPTION
				"The reset result of resetting the ISDN line towards the NTBA. Only the value 0 is significative. "
			DEFVAL { 2 }
			::= { sheIsdnPortConfigEntry 9 }

		
		sheIsdnPortConfigControl OBJECT IDENTIFIER ::= { sheIsdnPortConfigObjects 3 }

		
		sheIsdnPortConfigControlRequest OBJECT-TYPE
			SYNTAX SheIsdnControlRequestType
			MAX-ACCESS read-write
			STATUS current
			DESCRIPTION
				"The request of a user command.
				
				modifyisdnBasicRateLineTopology
				Must:sheIsdnPortConfigControlIndex
				     sheIsdnPortConfigControlBasicRateLineTopology
				
				setIsdnLayer1Permanent
				Must:sheIsdnPortConfigControlIndex
				     sheIsdnPortConfigControlL1PermanentActive
				
				setIsdnLayer2Permanent
				Must:sheIsdnPortConfigControlIndex
				      sheIsdnPortConfigControlL2PermanentActive
				
				resetIsdnPort: set ISDN line towards the NTBA, this command is a long running command, 
				the reset result will be updated to sheIsdnPortConfigResetResult after the 
				sheIsdnPortConfigControlTimer is exceeded.  
				resetIsdnPort:
				Must:sheIsdnPortConfigControlIndex
				
				modifyIsdnPowerFeed
				Must:sheIsdnPortConfigControlIndex
				     sheIsdnPortConfigControlPowerFeeding
				
				modifyIsdnL2out
				Must:sheIsdnPortConfigControlIndex
				     sheIsdnPortConfigControlL2Out"
			::= { sheIsdnPortConfigControl 1 }

		
		sheIsdnPortConfigControlIndex OBJECT-TYPE
			SYNTAX InterfaceIndex
			MAX-ACCESS read-write
			STATUS current
			DESCRIPTION
				"The index indicates the sheIsdnPortConfigEntry.
				"
			::= { sheIsdnPortConfigControl 2 }

		
		sheIsdnPortConfigControlReqResult OBJECT-TYPE
			SYNTAX SheIsdnControlReqResultType
			MAX-ACCESS read-only
			STATUS current
			DESCRIPTION
				"The result of the last user command."
			::= { sheIsdnPortConfigControl 3 }

		
		sheIsdnPortConfigControlBasicRateLineTopology OBJECT-TYPE
			SYNTAX SheIsdnPortLineTopo
			MAX-ACCESS read-write
			STATUS current
			DESCRIPTION
				"The line topology to be used for this interface.
				Note that setting isdnBasicRateIfType to isdns(75)
				does not necessarily mean a line topology of
				point-to-multipoint."
			::= { sheIsdnPortConfigControl 4 }

		
		sheIsdnPortConfigControlL1PermanentActive OBJECT-TYPE
			SYNTAX SheIsdnPermanentType
			MAX-ACCESS read-write
			STATUS current
			DESCRIPTION
				"Set permanent or no-permanemt active status of Layer-1, If 'permanent layer1' is configured for
				a specific port, the deactivation Layer-1 primitive will be discarded ."
			::= { sheIsdnPortConfigControl 5 }

		
		sheIsdnPortConfigControlPowerFeeding OBJECT-TYPE
			SYNTAX SheIsdnSwitch
			MAX-ACCESS read-write
			STATUS current
			DESCRIPTION
				"switch on/off the feeding."
			::= { sheIsdnPortConfigControl 6 }

		
		sheIsdnPortConfigControlL2PermanentActive OBJECT-TYPE
			SYNTAX SheIsdnPermanentType
			MAX-ACCESS read-write
			STATUS current
			DESCRIPTION
				"set permanent or no-permanemt active status of ISDN port Layer-2."
			::= { sheIsdnPortConfigControl 7 }

		
		sheIsdnPortConfigControlL2Out OBJECT-TYPE
			SYNTAX Unsigned32
			UNITS "seconds"
			MAX-ACCESS read-write
			STATUS current
			DESCRIPTION
				"Timer describing the time between two L2 reestablishment request, 
				if in L2 permanent mode."
			::= { sheIsdnPortConfigControl 8 }

		
		sheIsdnPortConfigControlTimeStamp OBJECT-TYPE
			SYNTAX TimeStamp
			MAX-ACCESS read-only
			STATUS current
			DESCRIPTION
				"The time stamp of the last command (end of command)."
			::= { sheIsdnPortConfigControl 9 }

		
		sheIsdnPortConfigControStatus OBJECT-TYPE
			SYNTAX SheControlStatusType
			MAX-ACCESS read-only
			STATUS current
			DESCRIPTION
				"The status of a user command."
			::= { sheIsdnPortConfigControl 10 }

		
		sheIsdnPortConfigControlTimer OBJECT-TYPE
			SYNTAX Gauge32
			MAX-ACCESS read-only
			STATUS current
			DESCRIPTION
				"The maximum wait time for the manager for a long running user command."
			::= { sheIsdnPortConfigControl 11 }

		
		sheIsdnChannelObjects OBJECT IDENTIFIER ::= { sheIsdnMib 2 }

		
		sheIsdnChannelSignalingStatsTable OBJECT-TYPE
			SYNTAX SEQUENCE OF SheIsdnChannelSignalingStatsEntry
			MAX-ACCESS not-accessible
			STATUS current
			DESCRIPTION
				"ISDN signaling table containing statistics
				information for all ISDN signaling channels
				on this managed device.
				"
			::= { sheIsdnChannelObjects 1 }

		
		sheIsdnChannelSignalingStatsEntry OBJECT-TYPE
			SYNTAX SheIsdnChannelSignalingStatsEntry
			MAX-ACCESS not-accessible
			STATUS current
			DESCRIPTION
				"An entry in the sheIsdnChannelSignalingStatsTable."
			INDEX { ifIndex }
			::= { sheIsdnChannelSignalingStatsTable 1 }

		
		SheIsdnChannelSignalingStatsEntry ::=
			SEQUENCE { 
				sheIsdnChannelSigStatsInCalls
					Counter32,
				sheIsdnChannelSigStatsInConnected
					Counter32,
				sheIsdnChannelSigStatsOutCalls
					Counter32,
				sheIsdnChannelSigStatsOutConnected
					Counter32,
				sheIsdnChannelSigStatsChargedUnits
					Counter32
			 }

		sheIsdnChannelSigStatsInCalls OBJECT-TYPE
			SYNTAX Counter32
			MAX-ACCESS read-only
			STATUS current
			DESCRIPTION
				"The number of incoming calls on this interface.
				"
			::= { sheIsdnChannelSignalingStatsEntry 1 }

		
		sheIsdnChannelSigStatsInConnected OBJECT-TYPE
			SYNTAX Counter32
			MAX-ACCESS read-only
			STATUS current
			DESCRIPTION
				"The number of incoming calls on this interface
				which were actually connected.
				"
			::= { sheIsdnChannelSignalingStatsEntry 2 }

		
		sheIsdnChannelSigStatsOutCalls OBJECT-TYPE
			SYNTAX Counter32
			MAX-ACCESS read-only
			STATUS current
			DESCRIPTION
				"The number of outgoing calls on this interface.
				"
			::= { sheIsdnChannelSignalingStatsEntry 3 }

		
		sheIsdnChannelSigStatsOutConnected OBJECT-TYPE
			SYNTAX Counter32
			MAX-ACCESS read-only
			STATUS current
			DESCRIPTION
				"The number of outgoing calls on this interface
				which were actually connected.
				"
			::= { sheIsdnChannelSignalingStatsEntry 4 }

		
		sheIsdnChannelSigStatsChargedUnits OBJECT-TYPE
			SYNTAX Counter32
			MAX-ACCESS read-only
			STATUS current
			DESCRIPTION
				"The number of charging units on this interface since
				system startup.
				Only the charging units applying to the local interface,
				i.e. for originated calls or for calls with 'Reverse
				charging' being active, are counted here.
				"
			::= { sheIsdnChannelSignalingStatsEntry 5 }

		
		sheIsdnChannelLapdTable OBJECT-TYPE
			SYNTAX SEQUENCE OF SheIsdnChannelLapdEntry
			MAX-ACCESS not-accessible
			STATUS current
			DESCRIPTION
				"Table containing statistics information for all LAPD (D channel Data Link)
				interfaces on this managed device.
				"
			::= { sheIsdnChannelObjects 2 }

		
		sheIsdnChannelLapdEntry OBJECT-TYPE
			SYNTAX SheIsdnChannelLapdEntry
			MAX-ACCESS not-accessible
			STATUS current
			DESCRIPTION
				"An entry in the sheIsdnChannelLapdTable."
			INDEX { ifIndex }
			::= { sheIsdnChannelLapdTable 1 }

		
		SheIsdnChannelLapdEntry ::=
			SEQUENCE { 
				sheIsdnChannelLapdPrimary
					TruthValue,
				sheIsdnChannelLapdOperStatus
					SheIsdnLapdOperStatus,
				sheIsdnChannelLapdPeerSabme
					Counter32,
				sheIsdnChannelLapdRecvdFrmr
					Counter32,
				sheIsdnChannelLapdInOctets
					Counter64,
				sheIsdnChannelLapdInUcastPkts
					Counter64,
				sheIsdnChannelLapdInBroadcastPkts
					Counter64,
				sheIsdnChannelLapdInDiscards
					Counter32,
				sheIsdnChannelLapdInErrors
					Counter32,
				sheIsdnChannelLapdInUnknownProtos
					Counter32,
				sheIsdnChannelLapdOutOctets
					Counter64,
				sheIsdnChannelLapdOutUcastPkts
					Counter64,
				sheIsdnChannelLapdOutBroadcastPkts
					Counter64,
				sheIsdnChannelLapdOutDiscards
					Counter32,
				sheIsdnChannelLapdOutErrors
					Counter32
			 }

		sheIsdnChannelLapdPrimary OBJECT-TYPE
			SYNTAX TruthValue
			MAX-ACCESS read-only
			STATUS current
			DESCRIPTION
				"If set to true(1), this D channel is the designated
				primary D channel if D channel backup is active.
				 	
				There must be exactly one primary D channel
				configured. If D channel backup is not used, this
				object has a value of true(1).
				"
			::= { sheIsdnChannelLapdEntry 1 }

		
		sheIsdnChannelLapdOperStatus OBJECT-TYPE
			SYNTAX SheIsdnLapdOperStatus
			MAX-ACCESS read-only
			STATUS current
			DESCRIPTION
				"The operational status of this interface:
				
				inactive all layers are inactive
				l1Active layer 1 is activated,
				layer 2 datalink not established
				l2Active layer 1 is activated,
				layer 2 datalink established."
			DEFVAL { inactive }
			::= { sheIsdnChannelLapdEntry 2 }

		
		sheIsdnChannelLapdPeerSabme OBJECT-TYPE
			SYNTAX Counter32
			MAX-ACCESS read-only
			STATUS current
			DESCRIPTION
				"The number of peer SABME frames received on this
				interface. This is the number of peer-initiated
				new connections on this interface."
			::= { sheIsdnChannelLapdEntry 3 }

		
		sheIsdnChannelLapdRecvdFrmr OBJECT-TYPE
			SYNTAX Counter32
			MAX-ACCESS read-only
			STATUS current
			DESCRIPTION
				"The number of LAPD FRMR response frames received.
				This is the number of framing errors on this
				interface.
				"
			::= { sheIsdnChannelLapdEntry 4 }

		
		sheIsdnChannelLapdInOctets OBJECT-TYPE
			SYNTAX Counter64
			MAX-ACCESS read-only
			STATUS current
			DESCRIPTION
				"The total number of octets received on this interface."
			::= { sheIsdnChannelLapdEntry 5 }

		
		sheIsdnChannelLapdInUcastPkts OBJECT-TYPE
			SYNTAX Counter64
			MAX-ACCESS read-only
			STATUS current
			DESCRIPTION
				"The number of frames received on this interface whose address is not TEI=127."
			::= { sheIsdnChannelLapdEntry 6 }

		
		sheIsdnChannelLapdInBroadcastPkts OBJECT-TYPE
			SYNTAX Counter64
			MAX-ACCESS read-only
			STATUS current
			DESCRIPTION
				"The number of frames received on this interface with TEI=127."
			::= { sheIsdnChannelLapdEntry 7 }

		
		sheIsdnChannelLapdInDiscards OBJECT-TYPE
			SYNTAX Counter32
			MAX-ACCESS read-only
			STATUS current
			DESCRIPTION
				"The total number of received frames which have been discarded. The possible reasons 
				are: buffer shortage."
			::= { sheIsdnChannelLapdEntry 8 }

		
		sheIsdnChannelLapdInErrors OBJECT-TYPE
			SYNTAX Counter32
			MAX-ACCESS read-only
			STATUS current
			DESCRIPTION
				"The number of inbound frames that contained errors preventing them 
				from being deliverable to LAPD."
			::= { sheIsdnChannelLapdEntry 9 }

		
		sheIsdnChannelLapdInUnknownProtos OBJECT-TYPE
			SYNTAX Counter32
			MAX-ACCESS read-only
			STATUS current
			DESCRIPTION
				"The number of frames with known TEI, but unknown SAPI."
			::= { sheIsdnChannelLapdEntry 10 }

		
		sheIsdnChannelLapdOutOctets OBJECT-TYPE
			SYNTAX Counter64
			MAX-ACCESS read-only
			STATUS current
			DESCRIPTION
				"The total number of octets transmitted on this interface."
			::= { sheIsdnChannelLapdEntry 11 }

		
		sheIsdnChannelLapdOutUcastPkts OBJECT-TYPE
			SYNTAX Counter64
			MAX-ACCESS read-only
			STATUS current
			DESCRIPTION
				"The number of frames transmitted on this interface whose address is not TEI=127."
			::= { sheIsdnChannelLapdEntry 12 }

		
		sheIsdnChannelLapdOutBroadcastPkts OBJECT-TYPE
			SYNTAX Counter64
			MAX-ACCESS read-only
			STATUS current
			DESCRIPTION
				"The number of frames transmitted on this interface with TEI=127."
			::= { sheIsdnChannelLapdEntry 13 }

		
		sheIsdnChannelLapdOutDiscards OBJECT-TYPE
			SYNTAX Counter32
			MAX-ACCESS read-only
			STATUS current
			DESCRIPTION
				"The total number of outbound frames which were discarded. Possible reasons are: buffer shortage."
			::= { sheIsdnChannelLapdEntry 14 }

		
		sheIsdnChannelLapdOutErrors OBJECT-TYPE
			SYNTAX Counter32
			MAX-ACCESS read-only
			STATUS current
			DESCRIPTION
				"The number of frames which could not be transmitted due to errors."
			::= { sheIsdnChannelLapdEntry 15 }

		
		sheIsdnChannelBearerTable OBJECT-TYPE
			SYNTAX SEQUENCE OF SheIsdnChannelBearerEntry
			MAX-ACCESS not-accessible
			STATUS current
			DESCRIPTION
				"The table contains the operational status for each B channel."
			::= { sheIsdnChannelObjects 3 }

		
		sheIsdnChannelBearerEntry OBJECT-TYPE
			SYNTAX SheIsdnChannelBearerEntry
			MAX-ACCESS not-accessible
			STATUS current
			DESCRIPTION
				"An entry in the sheIsdnChannelBearerTable."
			INDEX { ifIndex, sheIsdnChannelBearerChannelID }
			::= { sheIsdnChannelBearerTable 1 }

		
		SheIsdnChannelBearerEntry ::=
			SEQUENCE { 
				sheIsdnChannelBearerChannelID
					Integer32,
				sheIsdnChannelBearerOperStatus
					SheIsdnBearerOperStatus
			 }

		sheIsdnChannelBearerChannelID OBJECT-TYPE
			SYNTAX Integer32 (1..64)
			MAX-ACCESS read-only
			STATUS current
			DESCRIPTION
				"The channel ID specified each B channel in the some port.
				Second tableindex."
			::= { sheIsdnChannelBearerEntry 2 }

		
		sheIsdnChannelBearerOperStatus OBJECT-TYPE
			SYNTAX SheIsdnBearerOperStatus
			MAX-ACCESS read-only
			STATUS current
			DESCRIPTION
				"operational port status for each B channel."
			DEFVAL { disconnect }
			::= { sheIsdnChannelBearerEntry 3 }

		
		sheIsdnTestObjects OBJECT IDENTIFIER ::= { sheIsdnMib 3 }

		
		sheIsdnLineTestTable OBJECT-TYPE
			SYNTAX SEQUENCE OF SheIsdnLineTestEntry
			MAX-ACCESS not-accessible
			STATUS current
			DESCRIPTION
				"The table contains the line test result."
			::= { sheIsdnTestObjects 4 }

		
		sheIsdnLineTestEntry OBJECT-TYPE
			SYNTAX SheIsdnLineTestEntry
			MAX-ACCESS not-accessible
			STATUS current
			DESCRIPTION
				"An entry in the sheIsdnLineTestTable."
			INDEX { ifIndex }
			::= { sheIsdnLineTestTable 1 }

		
		SheIsdnLineTestEntry ::=
			SEQUENCE { 
				sheIsdnLineTestResult
					SheIsdnResultType,
				sheIsdnLineTestOutwardTest
					SheIsdnActiveType,
				sheIsdnLineTestMode
					SheIsdnPortLineTestMode
			 }

		sheIsdnLineTestResult OBJECT-TYPE
			SYNTAX SheIsdnResultType
			MAX-ACCESS read-only
			STATUS current
			DESCRIPTION
				"The result of the ISDN line test."
			::= { sheIsdnLineTestEntry 1 }

		
		sheIsdnLineTestOutwardTest OBJECT-TYPE
			SYNTAX SheIsdnActiveType
			MAX-ACCESS read-only
			STATUS current
			DESCRIPTION
				"active means that the ISDN line is swtiched to external test device (outward test).
				deactive means that the ISDN line is not swtiched to external test device (outward test)."
			::= { sheIsdnLineTestEntry 2 }

		
		sheIsdnLineTestMode OBJECT-TYPE
			SYNTAX SheIsdnPortLineTestMode
			MAX-ACCESS read-only
			STATUS current
			DESCRIPTION
				"The line test mode."
			::= { sheIsdnLineTestEntry 3 }

		
		sheIsdnLineTestControl OBJECT IDENTIFIER ::= { sheIsdnTestObjects 7 }

		
		sheIsdnLineTestControRequest OBJECT-TYPE
			SYNTAX SheIsdnControlRequestType
			MAX-ACCESS read-write
			STATUS current
			DESCRIPTION
				"the request of a user command.
				
				setIsdnLineTestMode: 
				this command is a long running command, sheIsdnLineTestCompletedTrap will be send
				after the test finished, or get the sheIsdnLineTestResult's value after sheIsdnLineTestControlTimer
				is exceeded. Only one port can have line test on a certain slot each time.
				
				setIsdnLineTestMode:
				Must:sheIsdnLineTestControIndex
				     sheIsdnLineTestControlMode
				
				setIsdnOutWardTest:
				    Only one port can be set to outward test on a certain slot each time.
				Must:sheIsdnLineTestControIndex
				     sheIsdnLineTestControlOutwardTest			"
			::= { sheIsdnLineTestControl 1 }

		
		sheIsdnLineTestControReqResult OBJECT-TYPE
			SYNTAX SheIsdnControlReqResultType
			MAX-ACCESS read-only
			STATUS current
			DESCRIPTION
				"the request result of a user command.	"
			::= { sheIsdnLineTestControl 2 }

		
		sheIsdnLineTestControIndex OBJECT-TYPE
			SYNTAX InterfaceIndex
			MAX-ACCESS read-write
			STATUS current
			DESCRIPTION
				"The ifIndex specifies a ISDN port."
			::= { sheIsdnLineTestControl 3 }

		
		sheIsdnLineTestControlOutwardTest OBJECT-TYPE
			SYNTAX SheIsdnActiveType
			MAX-ACCESS read-write
			STATUS current
			DESCRIPTION
				"active means switch the ISDN line to an external test device (outward test).
				deactive means swith the ISDN line to normal test."
			::= { sheIsdnLineTestControl 4 }

		
		sheIsdnLineTestControlMode OBJECT-TYPE
			SYNTAX SheIsdnPortLineTestMode
			MAX-ACCESS read-write
			STATUS current
			DESCRIPTION
				"configure internalLoop, NtLoop or forcedActivatin test mode of the test.
				"
			::= { sheIsdnLineTestControl 5 }

		
		sheIsdnLineTestControlTimeStamp OBJECT-TYPE
			SYNTAX TimeStamp
			MAX-ACCESS read-only
			STATUS current
			DESCRIPTION
				"The time stamp of the last command (end of command)."
			::= { sheIsdnLineTestControl 6 }

		
		sheIsdnLineTestControlTimer OBJECT-TYPE
			SYNTAX Gauge32
			MAX-ACCESS read-only
			STATUS current
			DESCRIPTION
				"The maximum wait time for the manager for a long running user command."
			::= { sheIsdnLineTestControl 7 }

		
		sheIsdnLineTestControlStatus OBJECT-TYPE
			SYNTAX SheControlStatusType
			MAX-ACCESS read-only
			STATUS current
			DESCRIPTION
				"The status of a user command."
			::= { sheIsdnLineTestControl 8 }

		
		sheIsdnPdataObjects OBJECT IDENTIFIER ::= { sheIsdnMib 7 }

		
		sheIsdnPMBSGlobal OBJECT IDENTIFIER ::= { sheIsdnPdataObjects 1 }

		
		sheIsdnPMBSSourceIP OBJECT-TYPE
			SYNTAX IpAddress
			MAX-ACCESS read-only
			STATUS current
			DESCRIPTION
				"IP address of local IUA stack."
			::= { sheIsdnPMBSGlobal 1 }

		
		sheIsdnPMBSSourcePort OBJECT-TYPE
			SYNTAX Integer32 (1024..65535)
			MAX-ACCESS read-only
			STATUS current
			DESCRIPTION
				"Port of local IUA stack."
			::= { sheIsdnPMBSGlobal 2 }

		
		sheIsdnPMBSTable OBJECT-TYPE
			SYNTAX SEQUENCE OF SheIsdnPMBSEntry
			MAX-ACCESS not-accessible
			STATUS current
			DESCRIPTION
				"This table contains IUA information and PMBS connection status."
			::= { sheIsdnPdataObjects 2 }

		
		sheIsdnPMBSEntry OBJECT-TYPE
			SYNTAX SheIsdnPMBSEntry
			MAX-ACCESS not-accessible
			STATUS current
			DESCRIPTION
				"An entry in the sheIsdnPMBSTable."
			INDEX { ifIndex }
			::= { sheIsdnPMBSTable 1 }

		
		SheIsdnPMBSEntry ::=
			SEQUENCE { 
				sheIsdnPMBSIUAInterfaceIID
					Unsigned32,
				sheIsdnPMBSAdminStatus
					SheIsdnEnableStatus
			 }

		sheIsdnPMBSIUAInterfaceIID OBJECT-TYPE
			SYNTAX Unsigned32
			MAX-ACCESS read-only
			STATUS current
			DESCRIPTION
				"IID of IUA. 0 is an invalid value if the IID is not configured. "
			DEFVAL { 0 }
			::= { sheIsdnPMBSEntry 1 }

		
		sheIsdnPMBSAdminStatus OBJECT-TYPE
			SYNTAX SheIsdnEnableStatus
			MAX-ACCESS read-only
			STATUS current
			DESCRIPTION
				"PMBS connection status. If the value of sheIsdnPMBSIUAInterfaceIID is 0, the sheIsdnPMBSAdminStatus
				can not be set to enable. "
			DEFVAL { 0 }
			::= { sheIsdnPMBSEntry 2 }

		
		sheIsdnPMBSControl OBJECT IDENTIFIER ::= { sheIsdnPdataObjects 3 }

		
		sheISDNPMBSControlRequest OBJECT-TYPE
			SYNTAX SheIsdnControlRequestType
			MAX-ACCESS read-write
			STATUS current
			DESCRIPTION
				"The request of a user command.
				
				setIsdnPMBSIID:
				Must:sheISDNPMBSControlIndex
				     sheISDNPMBSControlInterfaceIID			
				
				setIsdnPMBSConnect:
				Must:sheISDNPMBSControlIndex
				     sheISDNPMBSControlAdminStatus
				
				setIsdnPMBSSourceIp:
				Must:sheIsdnPMBSControlSourceIP
				
				setIsdnPMBSSourcePort:
				Must:sheIsdnPMBSControlSourcePort"
			::= { sheIsdnPMBSControl 1 }

		
		sheISDNPMBSControlReqResult OBJECT-TYPE
			SYNTAX SheIsdnControlReqResultType
			MAX-ACCESS read-only
			STATUS current
			DESCRIPTION
				"The result of a user command."
			::= { sheIsdnPMBSControl 2 }

		
		sheISDNPMBSControlIndex OBJECT-TYPE
			SYNTAX InterfaceIndex
			MAX-ACCESS read-write
			STATUS current
			DESCRIPTION
				"The index specifies a sheIsdnPMBSEntry."
			::= { sheIsdnPMBSControl 3 }

		
		sheISDNPMBSControlInterfaceIID OBJECT-TYPE
			SYNTAX Unsigned32 (1..4294967295)
			MAX-ACCESS read-write
			STATUS current
			DESCRIPTION
				"IID of IUA.
				"
			::= { sheIsdnPMBSControl 4 }

		
		sheISDNPMBSControlAdminStatus OBJECT-TYPE
			SYNTAX SheIsdnEnableStatus
			MAX-ACCESS read-write
			STATUS current
			DESCRIPTION
				"enable or disable PMBS connection.
				"
			::= { sheIsdnPMBSControl 5 }

		
		sheIsdnPMBSControlSourceIP OBJECT-TYPE
			SYNTAX IpAddress
			MAX-ACCESS read-write
			STATUS current
			DESCRIPTION
				"IP address of local IUA stack."
			::= { sheIsdnPMBSControl 6 }

		
		sheIsdnPMBSControlSourcePort OBJECT-TYPE
			SYNTAX Integer32 (1024..65535)
			MAX-ACCESS read-write
			STATUS current
			DESCRIPTION
				"Port of local IUA stack."
			::= { sheIsdnPMBSControl 7 }

		
		sheIsdnPMBSControlStatus OBJECT-TYPE
			SYNTAX SheControlStatusType
			MAX-ACCESS read-only
			STATUS current
			DESCRIPTION
				"The status of a user command."
			::= { sheIsdnPMBSControl 8 }

		
		sheIsdnPMBSControlTimeStamp OBJECT-TYPE
			SYNTAX TimeStamp
			MAX-ACCESS read-only
			STATUS current
			DESCRIPTION
				"The time stamp of the last command (end of command)."
			::= { sheIsdnPMBSControl 9 }

		
		sheIsdnPMBSControlTimer OBJECT-TYPE
			SYNTAX Gauge32
			MAX-ACCESS read-only
			STATUS current
			DESCRIPTION
				"TThe maximum wait time for the manager for a long running user command."
			::= { sheIsdnPMBSControl 10 }

		
		sheIsdnQuickTestTable OBJECT-TYPE
			SYNTAX SEQUENCE OF SheIsdnQuickTestEntry
			MAX-ACCESS not-accessible
			STATUS current
			DESCRIPTION
				"This table contains the port quick check configuration and check result."
			::= { sheIsdnPdataObjects 4 }

		
		sheIsdnQuickTestEntry OBJECT-TYPE
			SYNTAX SheIsdnQuickTestEntry
			MAX-ACCESS not-accessible
			STATUS current
			DESCRIPTION
				"An entry in the sheIsdnQuickTestTable."
			INDEX { ifIndex }
			::= { sheIsdnQuickTestTable 1 }

		
		SheIsdnQuickTestEntry ::=
			SEQUENCE { 
				sheIsdnQuickTestNtLoopbackResult
					SheIsdnResultType,
				sheIsdnQuickTestLayer1ActivationResult
					SheIsdnResultType
			 }

		sheIsdnQuickTestNtLoopbackResult OBJECT-TYPE
			SYNTAX SheIsdnResultType
			MAX-ACCESS read-only
			STATUS current
			DESCRIPTION
				"Result of the NT loopback."
			::= { sheIsdnQuickTestEntry 1 }

		
		sheIsdnQuickTestLayer1ActivationResult OBJECT-TYPE
			SYNTAX SheIsdnResultType
			MAX-ACCESS read-only
			STATUS current
			DESCRIPTION
				"Result of the layer 1 activation check."
			::= { sheIsdnQuickTestEntry 2 }

		
		sheIsdnQuickTestControl OBJECT IDENTIFIER ::= { sheIsdnPdataObjects 5 }

		
		sheIsdnQuickTestControlRequest OBJECT-TYPE
			SYNTAX SheIsdnControlRequestType
			MAX-ACCESS read-write
			STATUS current
			DESCRIPTION
				"The request of a user command.
				setIsdnPortQuickTestStart
				Must:sheIsdnQuickTestControlIndex
				"
			::= { sheIsdnQuickTestControl 1 }

		
		sheIsdnQuickTestControlReqResult OBJECT-TYPE
			SYNTAX SheIsdnControlReqResultType
			MAX-ACCESS read-only
			STATUS current
			DESCRIPTION
				"The request result of a user command."
			::= { sheIsdnQuickTestControl 2 }

		
		sheIsdnQuickTestControlIndex OBJECT-TYPE
			SYNTAX InterfaceIndex
			MAX-ACCESS read-write
			STATUS current
			DESCRIPTION
				"The index represents a ISDN port."
			::= { sheIsdnQuickTestControl 3 }

		
		sheIsdnQuickCheckControlTimeStamp OBJECT-TYPE
			SYNTAX TimeStamp
			MAX-ACCESS read-only
			STATUS current
			DESCRIPTION
				"The time stamp of the last command (end of command)."
			::= { sheIsdnQuickTestControl 4 }

		
		sheIsdnQuickCheckControlStatus OBJECT-TYPE
			SYNTAX SheControlStatusType
			MAX-ACCESS read-only
			STATUS current
			DESCRIPTION
				"The status of a user command."
			::= { sheIsdnQuickTestControl 5 }

		
		sheIsdnQuickCheckControlTimer OBJECT-TYPE
			SYNTAX Gauge32
			MAX-ACCESS read-only
			STATUS current
			DESCRIPTION
				"TThe maximum wait time for the manager for a long running user command."
			::= { sheIsdnQuickTestControl 6 }

		
		sheIsdnPMBSPLLTable OBJECT-TYPE
			SYNTAX SEQUENCE OF SheIsdnPMBSPLLEntry
			MAX-ACCESS not-accessible
			STATUS current
			DESCRIPTION
				"The table contains the PMBS statistics and PLL status after port quick check."
			::= { sheIsdnPdataObjects 6 }

		
		sheIsdnPMBSPLLEntry OBJECT-TYPE
			SYNTAX SheIsdnPMBSPLLEntry
			MAX-ACCESS not-accessible
			STATUS current
			DESCRIPTION
				"An entry in the sheIsdnPMBSPLLTable."
			INDEX { ifIndex, sheIsdnPMBSPLLIndex }
			::= { sheIsdnPMBSPLLTable 1 }

		
		SheIsdnPMBSPLLEntry ::=
			SEQUENCE { 
				sheIsdnPMBSPLLIndex
					Integer32,
				sheIsdnPMBSPLLTEINum
					Integer32,
				sheIsdnPMBSConnectionTime
					TimeStamp,
				sheIsdnPMBSPLLSentFrame
					Counter32,
				sheISDNPMBSPLLReceiveFrames
					Counter32
			 }

		sheIsdnPMBSPLLIndex OBJECT-TYPE
			SYNTAX Integer32 (1..8)
			MAX-ACCESS read-only
			STATUS current
			DESCRIPTION
				"PMBS PLL number, specified different PMBS connection in the same port. "
			::= { sheIsdnPMBSPLLEntry 1 }

		
		sheIsdnPMBSPLLTEINum OBJECT-TYPE
			SYNTAX Integer32
			MAX-ACCESS read-only
			STATUS current
			DESCRIPTION
				"TEI number. The value 255 means the corresponding PMBS PLL is inactive."
			::= { sheIsdnPMBSPLLEntry 2 }

		
		sheIsdnPMBSConnectionTime OBJECT-TYPE
			SYNTAX TimeStamp
			MAX-ACCESS read-only
			STATUS current
			DESCRIPTION
				"the time stamp for the PMBS connection setup."
			::= { sheIsdnPMBSPLLEntry 3 }

		
		sheIsdnPMBSPLLSentFrame OBJECT-TYPE
			SYNTAX Counter32
			MAX-ACCESS read-only
			STATUS current
			DESCRIPTION
				"Send I-Frame counters for each PLL."
			::= { sheIsdnPMBSPLLEntry 4 }

		
		sheISDNPMBSPLLReceiveFrames OBJECT-TYPE
			SYNTAX Counter32
			MAX-ACCESS read-only
			STATUS current
			DESCRIPTION
				"Received I-Frame counters for each PLL."
			::= { sheIsdnPMBSPLLEntry 5 }

		
		sheIsdnPdataPHTable OBJECT-TYPE
			SYNTAX SEQUENCE OF SheIsdnPdataPHEntry
			MAX-ACCESS not-accessible
			STATUS current
			DESCRIPTION
				"The table contains the information for each NGN-PHs currently connecting to MSAN."
			::= { sheIsdnPdataObjects 7 }

		
		sheIsdnPdataPHEntry OBJECT-TYPE
			SYNTAX SheIsdnPdataPHEntry
			MAX-ACCESS not-accessible
			STATUS current
			DESCRIPTION
				"An entry for each sheIsdnPdataPHTable."
			INDEX { sheIsdnPdataPHNumIndex }
			::= { sheIsdnPdataPHTable 1 }

		
		SheIsdnPdataPHEntry ::=
			SEQUENCE { 
				sheIsdnPdataPHNumIndex
					Integer32,
				sheIsdnPdataPHIPAdd
					IpAddress,
				sheIsdnPdataPHPortNum
					Integer32,
				sheIsdnPdataPHStatus
					SheIsdnPHStatus
			 }

		sheIsdnPdataPHNumIndex OBJECT-TYPE
			SYNTAX Integer32 (1..2)
			MAX-ACCESS read-only
			STATUS current
			DESCRIPTION
				"The NGN-PH number."
			::= { sheIsdnPdataPHEntry 1 }

		
		sheIsdnPdataPHIPAdd OBJECT-TYPE
			SYNTAX IpAddress
			MAX-ACCESS read-only
			STATUS current
			DESCRIPTION
				"SCTP IP address for NGN-PH."
			::= { sheIsdnPdataPHEntry 2 }

		
		sheIsdnPdataPHPortNum OBJECT-TYPE
			SYNTAX Integer32
			MAX-ACCESS read-only
			STATUS current
			DESCRIPTION
				"SCTP Port Number for NGN-PH. "
			::= { sheIsdnPdataPHEntry 3 }

		
		sheIsdnPdataPHStatus OBJECT-TYPE
			SYNTAX SheIsdnPHStatus
			MAX-ACCESS read-only
			STATUS current
			DESCRIPTION
				"SCTP connection status.The value is inactive if the NGN-PH is not available."
			::= { sheIsdnPdataPHEntry 4 }

		
		sheIsdnPdataWhiteListTable OBJECT-TYPE
			SYNTAX SEQUENCE OF SheIsdnPdataWhiteListEntry
			MAX-ACCESS not-accessible
			STATUS current
			DESCRIPTION
				"The table contains the information of NGN-PH whitelist ."
			::= { sheIsdnPdataObjects 8 }

		
		sheIsdnPdataWhiteListEntry OBJECT-TYPE
			SYNTAX SheIsdnPdataWhiteListEntry
			MAX-ACCESS not-accessible
			STATUS current
			DESCRIPTION
				"An entry for each sheIsdnPdataWhiteListTable."
			INDEX { sheIsdnPdataWhiteListIndex }
			::= { sheIsdnPdataWhiteListTable 1 }

		
		SheIsdnPdataWhiteListEntry ::=
			SEQUENCE { 
				sheIsdnPdataWhiteListIndex
					Integer32,
				sheIsdnPdataWhiteListIPAdd
					IpAddress,
				sheIsdnPdataWhiteListIPMask
					IpAddress,
				sheIsdnPdataWhiteListPortNum
					Integer32
			 }

		sheIsdnPdataWhiteListIndex OBJECT-TYPE
			SYNTAX Integer32 (1..64)
			MAX-ACCESS read-only
			STATUS current
			DESCRIPTION
				"Table index. each index uniquely identifies one white list."
			::= { sheIsdnPdataWhiteListEntry 1 }

		
		sheIsdnPdataWhiteListIPAdd OBJECT-TYPE
			SYNTAX IpAddress
			MAX-ACCESS read-only
			STATUS current
			DESCRIPTION
				"The IP address that the MSAN will allow to permit."
			::= { sheIsdnPdataWhiteListEntry 2 }

		
		sheIsdnPdataWhiteListIPMask OBJECT-TYPE
			SYNTAX IpAddress
			MAX-ACCESS read-only
			STATUS current
			DESCRIPTION
				"The mask of sheIsdnPdataWhiteListIPAdd."
			::= { sheIsdnPdataWhiteListEntry 3 }

		
		sheIsdnPdataWhiteListPortNum OBJECT-TYPE
			SYNTAX Integer32 (1024..65535)
			MAX-ACCESS read-only
			STATUS current
			DESCRIPTION
				"The Port that the MSAN will allow to permit."
			::= { sheIsdnPdataWhiteListEntry 4 }

		
		sheIsdnPdataWhiteListControl OBJECT IDENTIFIER ::= { sheIsdnPdataObjects 9 }

		
		sheIsdnPdataWhiteListControlRequest OBJECT-TYPE
			SYNTAX SheIsdnControlRequestType
			MAX-ACCESS read-write
			STATUS current
			DESCRIPTION
				"the request of a user command.
				createPHWhiteList:
				   Must:
				        sheIsdnPdataWhiteListControlIP
				        sheIsdnPdataWhiteListControlMask
				        sheIsdnPdataWhiteListControlPort
				
				   deletePHWhiteList:
				   Must:sheIsdnPdataWhiteListControlIndex
				"
			::= { sheIsdnPdataWhiteListControl 1 }

		
		sheIsdnPdataWhiteListControlReqResult OBJECT-TYPE
			SYNTAX SheIsdnControlReqResultType
			MAX-ACCESS read-only
			STATUS current
			DESCRIPTION
				"The result of a user command."
			::= { sheIsdnPdataWhiteListControl 2 }

		
		sheIsdnPdataWhiteListControlIndex OBJECT-TYPE
			SYNTAX Integer32 (1..64)
			MAX-ACCESS read-write
			STATUS current
			DESCRIPTION
				"The vaule represents a sheIsdnPdataPHEntry."
			::= { sheIsdnPdataWhiteListControl 3 }

		
		sheIsdnPdataWhiteListControlIP OBJECT-TYPE
			SYNTAX IpAddress
			MAX-ACCESS read-write
			STATUS current
			DESCRIPTION
				"The IP address that the MSAN will allow to permit."
			::= { sheIsdnPdataWhiteListControl 4 }

		
		sheIsdnPdataWhiteListControlMask OBJECT-TYPE
			SYNTAX IpAddress
			MAX-ACCESS read-write
			STATUS current
			DESCRIPTION
				"The mask of the sheIsdnPdataWhiteListControlIP."
			::= { sheIsdnPdataWhiteListControl 5 }

		
		sheIsdnPdataWhiteListControlPort OBJECT-TYPE
			SYNTAX Integer32 (1024..65535)
			MAX-ACCESS read-write
			STATUS current
			DESCRIPTION
				"The Port that the MSAN will allow to permit."
			::= { sheIsdnPdataWhiteListControl 6 }

		
		sheIsdnPdataWhiteListControlTimeStamp OBJECT-TYPE
			SYNTAX TimeStamp
			MAX-ACCESS read-only
			STATUS current
			DESCRIPTION
				"The time stamp of the last command (end of command)."
			::= { sheIsdnPdataWhiteListControl 7 }

		
		sheIsdnPdataWhiteListControlStatus OBJECT-TYPE
			SYNTAX SheControlStatusType
			MAX-ACCESS read-only
			STATUS current
			DESCRIPTION
				"The status of a user command."
			::= { sheIsdnPdataWhiteListControl 8 }

		
		sheIsdnPdataWhiteListControlTimer OBJECT-TYPE
			SYNTAX Gauge32
			MAX-ACCESS read-only
			STATUS current
			DESCRIPTION
				"TThe maximum wait time for the manager for a long running user command."
			::= { sheIsdnPdataWhiteListControl 9 }

		
		sheIsdnPMObjects OBJECT IDENTIFIER ::= { sheIsdnMib 8 }

		
		sheIsdnPmThresholdProfileTable OBJECT-TYPE
			SYNTAX SEQUENCE OF SheIsdnPmThresholdProfileEntry
			MAX-ACCESS not-accessible
			STATUS current
			DESCRIPTION
				"The table contains the attributes of each PM threshold profile.		
				"
			::= { sheIsdnPMObjects 1 }

		
		sheIsdnPmThresholdProfileEntry OBJECT-TYPE
			SYNTAX SheIsdnPmThresholdProfileEntry
			MAX-ACCESS not-accessible
			STATUS current
			DESCRIPTION
				"An entry represents a set of profile configurations
				in sheIsdnPmThresholdProfileTable.default profile will always exist. 
				This profile's name will be set to `DEFVAL' and its parameters 
				will be set to vendor specific values."
			INDEX { sheIsdnPmThresholdProfileIndex }
			::= { sheIsdnPmThresholdProfileTable 1 }

		
		SheIsdnPmThresholdProfileEntry ::=
			SEQUENCE { 
				sheIsdnPmThresholdProfileIndex
					Integer32,
				sheIsdnPmThresholdProfilenName
					DisplayString,
				sheIsdnPmThresholdProfilePer15MinUS
					Unsigned32,
				sheIsdnPmThresholdProfilePer15MinES
					Unsigned32,
				sheIsdnPmThresholdProfilePer15MinSES
					Unsigned32,
				sheIsdnPmThresholdProfilePer15MinBBE
					Unsigned32,
				sheIsdnPmThresholdProfilePer24HourUS
					Unsigned32,
				sheIsdnPmThresholdProfilePer24HourES
					Unsigned32,
				sheIsdnPmThresholdProfilePer24HourSES
					Unsigned32,
				sheIsdnPmThresholdProfilePer24HourBBE
					Unsigned32
			 }

		sheIsdnPmThresholdProfileIndex OBJECT-TYPE
			SYNTAX Integer32 (1..16)
			MAX-ACCESS read-only
			STATUS current
			DESCRIPTION
				"Table index. Each index uniquely identifies one pm profile entry."
			::= { sheIsdnPmThresholdProfileEntry 1 }

		
		sheIsdnPmThresholdProfilenName OBJECT-TYPE
			SYNTAX DisplayString (SIZE (0..31))
			MAX-ACCESS read-only
			STATUS current
			DESCRIPTION
				"The profile name is user specified. A default profile 
				will always exist. This profile's name will be set to `DEFVAL'."
			::= { sheIsdnPmThresholdProfileEntry 2 }

		
		sheIsdnPmThresholdProfilePer15MinUS OBJECT-TYPE
			SYNTAX Unsigned32
			MAX-ACCESS read-only
			STATUS current
			DESCRIPTION
				"per 15 minutes US threshold."
			::= { sheIsdnPmThresholdProfileEntry 3 }

		
		sheIsdnPmThresholdProfilePer15MinES OBJECT-TYPE
			SYNTAX Unsigned32
			MAX-ACCESS read-only
			STATUS current
			DESCRIPTION
				"per 15 minutes ES threshold."
			::= { sheIsdnPmThresholdProfileEntry 4 }

		
		sheIsdnPmThresholdProfilePer15MinSES OBJECT-TYPE
			SYNTAX Unsigned32
			MAX-ACCESS read-only
			STATUS current
			DESCRIPTION
				"per 15 minutes SES threshold."
			::= { sheIsdnPmThresholdProfileEntry 5 }

		
		sheIsdnPmThresholdProfilePer15MinBBE OBJECT-TYPE
			SYNTAX Unsigned32
			MAX-ACCESS read-only
			STATUS current
			DESCRIPTION
				"per 15 minutes BBE threshold."
			::= { sheIsdnPmThresholdProfileEntry 6 }

		
		sheIsdnPmThresholdProfilePer24HourUS OBJECT-TYPE
			SYNTAX Unsigned32
			MAX-ACCESS read-only
			STATUS current
			DESCRIPTION
				"per 24 hour US threshold."
			::= { sheIsdnPmThresholdProfileEntry 7 }

		
		sheIsdnPmThresholdProfilePer24HourES OBJECT-TYPE
			SYNTAX Unsigned32
			MAX-ACCESS read-only
			STATUS current
			DESCRIPTION
				"per 24 hour ES threshold."
			::= { sheIsdnPmThresholdProfileEntry 8 }

		
		sheIsdnPmThresholdProfilePer24HourSES OBJECT-TYPE
			SYNTAX Unsigned32
			MAX-ACCESS read-only
			STATUS current
			DESCRIPTION
				"per 24 hour SES threshold."
			::= { sheIsdnPmThresholdProfileEntry 9 }

		
		sheIsdnPmThresholdProfilePer24HourBBE OBJECT-TYPE
			SYNTAX Unsigned32
			MAX-ACCESS read-only
			STATUS current
			DESCRIPTION
				"per 24 hour BBE threshold."
			::= { sheIsdnPmThresholdProfileEntry 10 }

		
		sheIsdnPmThresholdProfileControl OBJECT IDENTIFIER ::= { sheIsdnPMObjects 2 }

		
		sheIsdnPmThresholdProfileControlRequest OBJECT-TYPE
			SYNTAX SheIsdnControlRequestType
			MAX-ACCESS read-write
			STATUS current
			DESCRIPTION
				"The request of a user command.
				
				createIsdnPMThreshold:
				Must:sheIsdnPmThresholdProfileControlName
				optional:sheIsdnPmThresholdProfileControlPer15MinUS
				         sheIsdnPmThresholdProfileControlPer15MinES
				         sheIsdnPmThresholdProfileControlPer15MinSES
				         sheIsdnPmThresholdProfileControlPer15MinBBE
				         sheIsdnPmThresholdProfileControlPer24HourUS
				         sheIsdnPmThresholdProfileControlPer24HourES
				         sheIsdnPmThresholdProfileControlPer24HourSES
				         sheIsdnPmThresholdProfileControlPer24HourBBE
				
				deleteIsdnPMThreshold:
				Must:sheIsdnPmThresholdProfileControlIndex
				
				modifyIsdnPMThreshold:
				Must:sheIsdnPmThresholdProfileControlIndex  
				optional:sheIsdnPmThresholdProfileControlName
				         sheIsdnPmThresholdProfileControlPer15MinUS
				         sheIsdnPmThresholdProfileControlPer15MinES
				         sheIsdnPmThresholdProfileControlPer15MinSES
				         sheIsdnPmThresholdProfileControlPer15MinBBE
				         sheIsdnPmThresholdProfileControlPer24HourUS
				         sheIsdnPmThresholdProfileControlPer24HourES
				         sheIsdnPmThresholdProfileControlPer24HourSES
				         sheIsdnPmThresholdProfileControlPer24HourBBE
				"
			::= { sheIsdnPmThresholdProfileControl 1 }

		
		sheIsdnPmThresholdProfileControlReqResult OBJECT-TYPE
			SYNTAX SheIsdnControlReqResultType
			MAX-ACCESS read-only
			STATUS current
			DESCRIPTION
				"The request result of a user command."
			::= { sheIsdnPmThresholdProfileControl 2 }

		
		sheIsdnPmThresholdProfileControlName OBJECT-TYPE
			SYNTAX DisplayString (SIZE (0..31))
			MAX-ACCESS read-write
			STATUS current
			DESCRIPTION
				"A describable name that uniquely identifies a profile entry of 
				this table.The profile name is user specified. A default profile 
				will always exist. This profile's name will be set to `DEFVAL'.
				"
			::= { sheIsdnPmThresholdProfileControl 3 }

		
		sheIsdnPmThresholdProfileControlIndex OBJECT-TYPE
			SYNTAX Integer32 (1..16)
			MAX-ACCESS read-write
			STATUS current
			DESCRIPTION
				"The same as the sheIsdnPmThresholdProfileIndex."
			::= { sheIsdnPmThresholdProfileControl 4 }

		
		sheIsdnPmThresholdProfileControlPer15MinUS OBJECT-TYPE
			SYNTAX Unsigned32
			MAX-ACCESS read-write
			STATUS current
			DESCRIPTION
				"Set the per 15 minutes US threshold."
			::= { sheIsdnPmThresholdProfileControl 5 }

		
		sheIsdnPmThresholdProfileControlPer15MinES OBJECT-TYPE
			SYNTAX Unsigned32
			MAX-ACCESS read-write
			STATUS current
			DESCRIPTION
				"Set the per 15 minutes ES threshold"
			::= { sheIsdnPmThresholdProfileControl 6 }

		
		sheIsdnPmThresholdProfileControlPer15MinSES OBJECT-TYPE
			SYNTAX Unsigned32
			MAX-ACCESS read-write
			STATUS current
			DESCRIPTION
				"Set the per 15 minutes SES threshold"
			::= { sheIsdnPmThresholdProfileControl 7 }

		
		sheIsdnPmThresholdProfileControlPer15MinBBE OBJECT-TYPE
			SYNTAX Unsigned32
			MAX-ACCESS read-write
			STATUS current
			DESCRIPTION
				"set the per 15 minutes BBE threshold"
			::= { sheIsdnPmThresholdProfileControl 8 }

		
		sheIsdnPmThresholdProfileControlPer24HourUS OBJECT-TYPE
			SYNTAX Unsigned32
			MAX-ACCESS read-write
			STATUS current
			DESCRIPTION
				"set the per 24 hour US threshold."
			::= { sheIsdnPmThresholdProfileControl 9 }

		
		sheIsdnPmThresholdProfileControlPer24HourES OBJECT-TYPE
			SYNTAX Unsigned32
			MAX-ACCESS read-write
			STATUS current
			DESCRIPTION
				"set the per 24 hour ES threshold."
			::= { sheIsdnPmThresholdProfileControl 10 }

		
		sheIsdnPmThresholdProfileControlPer24HourSES OBJECT-TYPE
			SYNTAX Unsigned32
			MAX-ACCESS read-write
			STATUS current
			DESCRIPTION
				"set the per 24 hour SES threshold."
			::= { sheIsdnPmThresholdProfileControl 11 }

		
		sheIsdnPmThresholdProfileControlPer24HourBBE OBJECT-TYPE
			SYNTAX Unsigned32
			MAX-ACCESS read-write
			STATUS current
			DESCRIPTION
				"set the per 24 hour BBE threshold."
			::= { sheIsdnPmThresholdProfileControl 12 }

		
		sheIsdnPmThresholdProfileControlTimeStamp OBJECT-TYPE
			SYNTAX TimeStamp
			MAX-ACCESS read-only
			STATUS current
			DESCRIPTION
				"The time stamp of the last command (end of command)."
			::= { sheIsdnPmThresholdProfileControl 13 }

		
		sheIsdnPmThresholdProfileControlStatus OBJECT-TYPE
			SYNTAX SheControlStatusType
			MAX-ACCESS read-only
			STATUS current
			DESCRIPTION
				"The status of a user command."
			::= { sheIsdnPmThresholdProfileControl 14 }

		
		sheIsdnPmThresholdProfileControlTimer OBJECT-TYPE
			SYNTAX Gauge32
			MAX-ACCESS read-only
			STATUS current
			DESCRIPTION
				"TThe maximum wait time for the manager for a long running user command."
			::= { sheIsdnPmThresholdProfileControl 15 }

		
		sheIsdnPmConfigGroup OBJECT IDENTIFIER ::= { sheIsdnPMObjects 3 }

		
		sheIsdnPmConfigTable OBJECT-TYPE
			SYNTAX SEQUENCE OF SheIsdnPmConfigEntry
			MAX-ACCESS not-accessible
			STATUS current
			DESCRIPTION
				"The table contains the configuration of the performance monitoring."
			::= { sheIsdnPmConfigGroup 1 }

		
		sheIsdnPmConfigEntry OBJECT-TYPE
			SYNTAX SheIsdnPmConfigEntry
			MAX-ACCESS not-accessible
			STATUS current
			DESCRIPTION
				"An entry in the sheIsdnPmConfigTable."
			INDEX { ifIndex }
			::= { sheIsdnPmConfigTable 1 }

		
		SheIsdnPmConfigEntry ::=
			SEQUENCE { 
				sheIsdnPmConfigActive
					SheIsdnActiveType,
				sheIsdnPmConfigThresholdCheckActivated
					SheIsdnActiveType,
				sheIsdnPmConfigThresholdProfileIndex
					Integer32
			 }

		sheIsdnPmConfigActive OBJECT-TYPE
			SYNTAX SheIsdnActiveType
			MAX-ACCESS read-only
			STATUS current
			DESCRIPTION
				"activate/deactivate the performance monitoring function."
			::= { sheIsdnPmConfigEntry 1 }

		
		sheIsdnPmConfigThresholdCheckActivated OBJECT-TYPE
			SYNTAX SheIsdnActiveType
			MAX-ACCESS read-only
			STATUS current
			DESCRIPTION
				"activate/deactivate the performace monitoring threshold of the 
				ISDN port."
			::= { sheIsdnPmConfigEntry 2 }

		
		sheIsdnPmConfigThresholdProfileIndex OBJECT-TYPE
			SYNTAX Integer32 (1..16)
			MAX-ACCESS read-only
			STATUS current
			DESCRIPTION
				"The value is the same as sheIsdnPmThresholdProfileIndex ."
			DEFVAL { 1 }
			::= { sheIsdnPmConfigEntry 3 }

		
		sheIsdnPmConfigControl OBJECT IDENTIFIER ::= { sheIsdnPmConfigGroup 2 }

		
		sheIsdnPmConfigControlRequest OBJECT-TYPE
			SYNTAX SheIsdnControlRequestType
			MAX-ACCESS read-write
			STATUS current
			DESCRIPTION
				"The request of a user command.
				setIsdnPMActive:
				Must:sheIsdnPmConfigControlIndex
				     sheIsdnPmConfigControlActive
				
				setIsdnPmGlobalActive:
				Must:sheIsdnPmConfigControlActive
				      
				setIsdnPortPMThresholdCheck
				Must:sheIsdnPmConfigControlIndex
				     sheIsdnPmConfigControlThresCheckActivated
				
				setIsdnThresProfileIndex:
				Must:sheIsdnPmConfigControlIndex  
				     sheIsdnPmConfigControlThresProfileIndex"
			::= { sheIsdnPmConfigControl 1 }

		
		sheIsdnPmConfigControlIndex OBJECT-TYPE
			SYNTAX InterfaceIndex
			MAX-ACCESS read-write
			STATUS current
			DESCRIPTION
				"Specifies a sheIsdnPmConfigEntry."
			::= { sheIsdnPmConfigControl 2 }

		
		sheIsdnPmConfigControlReqResult OBJECT-TYPE
			SYNTAX SheIsdnControlReqResultType
			MAX-ACCESS read-only
			STATUS current
			DESCRIPTION
				"The result of a user command."
			::= { sheIsdnPmConfigControl 3 }

		
		sheIsdnPmConfigControlActive OBJECT-TYPE
			SYNTAX SheIsdnActiveType
			MAX-ACCESS read-write
			STATUS current
			DESCRIPTION
				"activate/deactivate threshold watch."
			::= { sheIsdnPmConfigControl 4 }

		
		sheIsdnPmConfigControlThresProfileIndex OBJECT-TYPE
			SYNTAX Integer32 (1..16)
			MAX-ACCESS read-write
			STATUS current
			DESCRIPTION
				"The index specifies the sheIsdnPmThresholdProfileEntry."
			::= { sheIsdnPmConfigControl 5 }

		
		sheIsdnPmConfigControlThresCheckActivated OBJECT-TYPE
			SYNTAX SheIsdnActiveType
			MAX-ACCESS read-write
			STATUS current
			DESCRIPTION
				"Active/deactive the performance monitoring threshold check of the ISDN port."
			::= { sheIsdnPmConfigControl 6 }

		
		sheIsdnPmConfigControlTimeStamp OBJECT-TYPE
			SYNTAX TimeStamp
			MAX-ACCESS read-only
			STATUS current
			DESCRIPTION
				"The time stamp of the last command (end of command)."
			::= { sheIsdnPmConfigControl 7 }

		
		sheIsdnPmConfigControlStatus OBJECT-TYPE
			SYNTAX SheControlStatusType
			MAX-ACCESS read-only
			STATUS current
			DESCRIPTION
				"The status of a user command."
			::= { sheIsdnPmConfigControl 8 }

		
		sheIsdnPmConfigControlTimer OBJECT-TYPE
			SYNTAX Gauge32
			MAX-ACCESS read-only
			STATUS current
			DESCRIPTION
				"TThe maximum wait time for the manager for a long running user command."
			::= { sheIsdnPmConfigControl 9 }

		
		sheIsdnPmActual15MinTable OBJECT-TYPE
			SYNTAX SEQUENCE OF SheIsdnPmActual15MinEntry
			MAX-ACCESS not-accessible
			STATUS current
			DESCRIPTION
				"The table contains the performance data of the ISDN termination
				near end in the actual 15 Minutes."
			::= { sheIsdnPMObjects 5 }

		
		sheIsdnPmActual15MinEntry OBJECT-TYPE
			SYNTAX SheIsdnPmActual15MinEntry
			MAX-ACCESS not-accessible
			STATUS current
			DESCRIPTION
				"An entry in the sheIsdnPmActual15MinTable."
			INDEX { ifIndex }
			::= { sheIsdnPmActual15MinTable 1 }

		
		SheIsdnPmActual15MinEntry ::=
			SEQUENCE { 
				sheIsdnPmActual15MinUS
					Counter32,
				sheIsdnPmActual15MinES
					Counter32,
				sheIsdnPmActual15MinSES
					Counter32,
				sheIsdnPmActual15MinBBE
					Counter32
			 }

		sheIsdnPmActual15MinUS OBJECT-TYPE
			SYNTAX Counter32
			MAX-ACCESS read-only
			STATUS current
			DESCRIPTION
				"The US counter in the actual 15 Minutes."
			::= { sheIsdnPmActual15MinEntry 1 }

		
		sheIsdnPmActual15MinES OBJECT-TYPE
			SYNTAX Counter32
			MAX-ACCESS read-only
			STATUS current
			DESCRIPTION
				"The ES counter in the actual 15 Minutes."
			::= { sheIsdnPmActual15MinEntry 2 }

		
		sheIsdnPmActual15MinSES OBJECT-TYPE
			SYNTAX Counter32
			MAX-ACCESS read-only
			STATUS current
			DESCRIPTION
				"The SES counter in the actual 15 Minutes."
			::= { sheIsdnPmActual15MinEntry 3 }

		
		sheIsdnPmActual15MinBBE OBJECT-TYPE
			SYNTAX Counter32
			MAX-ACCESS read-only
			STATUS current
			DESCRIPTION
				"The BBE counter in the actual 15 Minutes."
			::= { sheIsdnPmActual15MinEntry 4 }

		
		sheIsdnPmActual24HourTable OBJECT-TYPE
			SYNTAX SEQUENCE OF SheIsdnPmActual24HourEntry
			MAX-ACCESS not-accessible
			STATUS current
			DESCRIPTION
				"The table contains the performance data of the ISDN termination near end in the 
				actual 24 hour."
			::= { sheIsdnPMObjects 6 }

		
		sheIsdnPmActual24HourEntry OBJECT-TYPE
			SYNTAX SheIsdnPmActual24HourEntry
			MAX-ACCESS not-accessible
			STATUS current
			DESCRIPTION
				"An entry in the sheIsdnPmActual24HourTable."
			INDEX { ifIndex }
			::= { sheIsdnPmActual24HourTable 1 }

		
		SheIsdnPmActual24HourEntry ::=
			SEQUENCE { 
				sheIsdnPmActual24HourUS
					Counter32,
				sheIsdnPmActual24HourES
					Counter32,
				sheIsdnPmActual24HourSES
					Counter32,
				sheIsdnPmActual24HourBBE
					Counter32
			 }

		sheIsdnPmActual24HourUS OBJECT-TYPE
			SYNTAX Counter32
			MAX-ACCESS read-only
			STATUS current
			DESCRIPTION
				"The US counter in the actual 24 hour."
			::= { sheIsdnPmActual24HourEntry 1 }

		
		sheIsdnPmActual24HourES OBJECT-TYPE
			SYNTAX Counter32
			MAX-ACCESS read-only
			STATUS current
			DESCRIPTION
				"The ES counter in the actual 24 hour."
			::= { sheIsdnPmActual24HourEntry 2 }

		
		sheIsdnPmActual24HourSES OBJECT-TYPE
			SYNTAX Counter32
			MAX-ACCESS read-only
			STATUS current
			DESCRIPTION
				"The SES counter in the actual 24 hour."
			::= { sheIsdnPmActual24HourEntry 3 }

		
		sheIsdnPmActual24HourBBE OBJECT-TYPE
			SYNTAX Counter32
			MAX-ACCESS read-only
			STATUS current
			DESCRIPTION
				"The BBE counter in the actual 24 hour."
			::= { sheIsdnPmActual24HourEntry 4 }

		
		sheIsdnPmPer15MinHistoryTable OBJECT-TYPE
			SYNTAX SEQUENCE OF SheIsdnPmPer15MinHistoryEntry
			MAX-ACCESS not-accessible
			STATUS current
			DESCRIPTION
				"The table contains the history performance data of the ISDN termination near end.
				"
			::= { sheIsdnPMObjects 7 }

		
		sheIsdnPmPer15MinHistoryEntry OBJECT-TYPE
			SYNTAX SheIsdnPmPer15MinHistoryEntry
			MAX-ACCESS not-accessible
			STATUS current
			DESCRIPTION
				"An entry in the sheIsdnPmPer15MinHistoryTable."
			INDEX { ifIndex, sheIsdnPmPer15MinHistroyIndex }
			::= { sheIsdnPmPer15MinHistoryTable 1 }

		
		SheIsdnPmPer15MinHistoryEntry ::=
			SEQUENCE { 
				sheIsdnPmPer15MinHistroyIndex
					Integer32,
				sheIsdnPmPre15MinHistroyUSCounters
					Counter32,
				sheIsdnPmPre15MinHistroyESCounters
					Counter32,
				sheIsdnPmPre15MinHistroySESCounters
					Counter32,
				sheIsdnPmPre15MinHistroyBBECounters
					Counter32
			 }

		sheIsdnPmPer15MinHistroyIndex OBJECT-TYPE
			SYNTAX Integer32 (1..96)
			MAX-ACCESS read-only
			STATUS current
			DESCRIPTION
				"indicates each 15 Minutes, at least 96 recent 15 minutes intervals."
			::= { sheIsdnPmPer15MinHistoryEntry 1 }

		
		sheIsdnPmPre15MinHistroyUSCounters OBJECT-TYPE
			SYNTAX Counter32
			MAX-ACCESS read-only
			STATUS current
			DESCRIPTION
				"The US history counter for each past 15 Minutes."
			::= { sheIsdnPmPer15MinHistoryEntry 2 }

		
		sheIsdnPmPre15MinHistroyESCounters OBJECT-TYPE
			SYNTAX Counter32
			MAX-ACCESS read-only
			STATUS current
			DESCRIPTION
				"The ES history counter for each past 15 Minutes."
			::= { sheIsdnPmPer15MinHistoryEntry 3 }

		
		sheIsdnPmPre15MinHistroySESCounters OBJECT-TYPE
			SYNTAX Counter32
			MAX-ACCESS read-only
			STATUS current
			DESCRIPTION
				"The SES history counter for each past 15 Minutes."
			::= { sheIsdnPmPer15MinHistoryEntry 4 }

		
		sheIsdnPmPre15MinHistroyBBECounters OBJECT-TYPE
			SYNTAX Counter32
			MAX-ACCESS read-only
			STATUS current
			DESCRIPTION
				"The BBE history counter for each past 15 Minutes."
			::= { sheIsdnPmPer15MinHistoryEntry 5 }

		
		sheIsdnPmPer24HourHistoryTable OBJECT-TYPE
			SYNTAX SEQUENCE OF SheIsdnPmPer24HourHistoryEntry
			MAX-ACCESS not-accessible
			STATUS current
			DESCRIPTION
				"The table contains the history performance data collect the 
				ISDN termination near end.
				"
			::= { sheIsdnPMObjects 8 }

		
		sheIsdnPmPer24HourHistoryEntry OBJECT-TYPE
			SYNTAX SheIsdnPmPer24HourHistoryEntry
			MAX-ACCESS not-accessible
			STATUS current
			DESCRIPTION
				"An entry in the sheIsdnPmPer24HourHistoryTable."
			INDEX { ifIndex, sheIsdnPmPer24HourHistroyIndex }
			::= { sheIsdnPmPer24HourHistoryTable 1 }

		
		SheIsdnPmPer24HourHistoryEntry ::=
			SEQUENCE { 
				sheIsdnPmPer24HourHistroyIndex
					Integer32,
				sheIsdnPmPre24HourHistroyUSCounters
					Counter32,
				sheIsdnPmPre24HourHistroyESCounters
					Counter32,
				sheIsdnPmPre24HourHistroySESCounters
					Counter32,
				sheIsdnPmPre24HourHistroyBBECounters
					Counter32
			 }

		sheIsdnPmPer24HourHistroyIndex OBJECT-TYPE
			SYNTAX Integer32 (1..3)
			MAX-ACCESS read-only
			STATUS current
			DESCRIPTION
				"indicates each 24 hour, at least 3 recent 24 hour intervals."
			::= { sheIsdnPmPer24HourHistoryEntry 1 }

		
		sheIsdnPmPre24HourHistroyUSCounters OBJECT-TYPE
			SYNTAX Counter32
			MAX-ACCESS read-only
			STATUS current
			DESCRIPTION
				"The US history counter for each past 24 hour."
			::= { sheIsdnPmPer24HourHistoryEntry 2 }

		
		sheIsdnPmPre24HourHistroyESCounters OBJECT-TYPE
			SYNTAX Counter32
			MAX-ACCESS read-only
			STATUS current
			DESCRIPTION
				"The ES history counter for each past 24 hour."
			::= { sheIsdnPmPer24HourHistoryEntry 3 }

		
		sheIsdnPmPre24HourHistroySESCounters OBJECT-TYPE
			SYNTAX Counter32
			MAX-ACCESS read-only
			STATUS current
			DESCRIPTION
				"The SES history counter for each past 24 hour."
			::= { sheIsdnPmPer24HourHistoryEntry 4 }

		
		sheIsdnPmPre24HourHistroyBBECounters OBJECT-TYPE
			SYNTAX Counter32
			MAX-ACCESS read-only
			STATUS current
			DESCRIPTION
				"The BBE history counter for each past 24 hour."
			::= { sheIsdnPmPer24HourHistoryEntry 5 }

		
		sheIsdnErrorInfoObjects OBJECT IDENTIFIER ::= { sheIsdnMib 9 }

		
		sheIsdnErrGlobalPara OBJECT IDENTIFIER ::= { sheIsdnErrorInfoObjects 1 }

		
		sheIsdnber10e3Threshold OBJECT-TYPE
			SYNTAX Unsigned32
			MAX-ACCESS read-only
			STATUS current
			DESCRIPTION
				"The 10E-3 BER threshold limits. "
			DEFVAL { 32 }
			::= { sheIsdnErrGlobalPara 1 }

		
		sheIsdnber10e6Threshold OBJECT-TYPE
			SYNTAX Unsigned32
			MAX-ACCESS read-only
			STATUS current
			DESCRIPTION
				"The 10E-6 BER threshold limits. "
			DEFVAL { 2 }
			::= { sheIsdnErrGlobalPara 2 }

		
		sheIsdnPowerFeedingStatusTimeStamp OBJECT-TYPE
			SYNTAX TimeStamp
			MAX-ACCESS read-only
			STATUS current
			DESCRIPTION
				"The timeStamp of the latest port PowerFeedingStatus changed."
			::= { sheIsdnErrGlobalPara 3 }

		
		sheIsdnErrGlobalControl OBJECT IDENTIFIER ::= { sheIsdnErrorInfoObjects 2 }

		
		sheIsdnErrControlRequest OBJECT-TYPE
			SYNTAX SheIsdnControlRequestType
			MAX-ACCESS read-write
			STATUS current
			DESCRIPTION
				"The request of a user command.
				
				setIsdnber10e3Threshold:
				Must:sheIsdnber10e3Threshold
				
				setIsdnber10e6Threshold:
				Must:sheIsdnber10e6Threshold"
			::= { sheIsdnErrGlobalControl 1 }

		
		sheIsdnErrControlReqResult OBJECT-TYPE
			SYNTAX SheIsdnControlReqResultType
			MAX-ACCESS read-only
			STATUS current
			DESCRIPTION
				"The result of a user command."
			::= { sheIsdnErrGlobalControl 2 }

		
		sheIsdnber10e3ControlThreshold OBJECT-TYPE
			SYNTAX Unsigned32
			MAX-ACCESS read-write
			STATUS current
			DESCRIPTION
				"setting 10E-3 BER threshold limits. "
			::= { sheIsdnErrGlobalControl 3 }

		
		sheIsdnber10e6ControlThreshold OBJECT-TYPE
			SYNTAX Unsigned32
			MAX-ACCESS read-write
			STATUS current
			DESCRIPTION
				"setting 10E-6 BER threshold limits. "
			::= { sheIsdnErrGlobalControl 4 }

		
		sheIsdnErrControlTimeStamp OBJECT-TYPE
			SYNTAX TimeStamp
			MAX-ACCESS read-only
			STATUS current
			DESCRIPTION
				"The time stamp of the last command (end of command)."
			::= { sheIsdnErrGlobalControl 5 }

		
		sheIsdnErrControlStatus OBJECT-TYPE
			SYNTAX SheControlStatusType
			MAX-ACCESS read-only
			STATUS current
			DESCRIPTION
				"The status of a user command."
			::= { sheIsdnErrGlobalControl 6 }

		
		sheIsdnErrControlTimer OBJECT-TYPE
			SYNTAX Gauge32
			MAX-ACCESS read-only
			STATUS current
			DESCRIPTION
				"TThe maximum wait time for the manager for a long running user command."
			::= { sheIsdnErrGlobalControl 7 }

		
		sheIsdnTimeStampQueryTable OBJECT-TYPE
			SYNTAX SEQUENCE OF SheIsdnTimeStampQueryEntry
			MAX-ACCESS not-accessible
			STATUS current
			DESCRIPTION
				"The table contains the timestamp when layer1 or layer2 alarm occurs."
			::= { sheIsdnErrorInfoObjects 3 }

		
		sheIsdnTimeStampQueryEntry OBJECT-TYPE
			SYNTAX SheIsdnTimeStampQueryEntry
			MAX-ACCESS not-accessible
			STATUS current
			DESCRIPTION
				"An entry in the sheIsdnTimeStampQueryTable."
			INDEX { ifIndex }
			::= { sheIsdnTimeStampQueryTable 1 }

		
		SheIsdnTimeStampQueryEntry ::=
			SEQUENCE { 
				sheIsdnTimeStampLastL1BreakDown
					TimeStamp,
				sheIsdnTimeStampLastL2Deactivation
					TimeStamp,
				sheIsdnTimeStampLastBerCrossing
					TimeStamp,
				sheISDNTimeStampLastPortDeactivation
					TimeStamp
			 }

		sheIsdnTimeStampLastL1BreakDown OBJECT-TYPE
			SYNTAX TimeStamp
			MAX-ACCESS read-only
			STATUS current
			DESCRIPTION
				"Time stamp of the last Layer 1 breakdown."
			::= { sheIsdnTimeStampQueryEntry 1 }

		
		sheIsdnTimeStampLastL2Deactivation OBJECT-TYPE
			SYNTAX TimeStamp
			MAX-ACCESS read-only
			STATUS current
			DESCRIPTION
				"Time stamp of the last layer 2 deactivation."
			::= { sheIsdnTimeStampQueryEntry 2 }

		
		sheIsdnTimeStampLastBerCrossing OBJECT-TYPE
			SYNTAX TimeStamp
			MAX-ACCESS read-only
			STATUS current
			DESCRIPTION
				"Time stamp of the last BER = 1E-6 crossing."
			::= { sheIsdnTimeStampQueryEntry 3 }

		
		sheISDNTimeStampLastPortDeactivation OBJECT-TYPE
			SYNTAX TimeStamp
			MAX-ACCESS read-only
			STATUS current
			DESCRIPTION
				"Time stamp of port deactivation (10 consecutive sec with BER worse 
				than 1E-3)."
			::= { sheIsdnTimeStampQueryEntry 4 }

		
		sheIsdnLayer2EventsTable OBJECT-TYPE
			SYNTAX SEQUENCE OF SheIsdnLayer2EventsEntry
			MAX-ACCESS not-accessible
			STATUS current
			DESCRIPTION
				"The table contains layer2 event type."
			::= { sheIsdnErrorInfoObjects 4 }

		
		sheIsdnLayer2EventsEntry OBJECT-TYPE
			SYNTAX SheIsdnLayer2EventsEntry
			MAX-ACCESS not-accessible
			STATUS current
			DESCRIPTION
				"An entry in the sheIsdnLayer2EventsTable."
			INDEX { ifIndex }
			::= { sheIsdnLayer2EventsTable 1 }

		
		SheIsdnLayer2EventsEntry ::=
			SEQUENCE { 
				sheIsdnLayer2EventsType
					SheIsdnLayer2EventsType,
				sheIsdnLayer2EventsTimeStamp
					TimeStamp
			 }

		sheIsdnLayer2EventsType OBJECT-TYPE
			SYNTAX SheIsdnLayer2EventsType
			MAX-ACCESS read-only
			STATUS current
			DESCRIPTION
				"Values 3..17 represent the error codes A..O from ETS 300 125, appendix II, Table II-1/Q.921. 
				These will be reported as events, i.e not alarms. In detail:
				    Value 3 means error code 'A'
				    Value 4 means error code 'B'
				    Value 5 means error code 'C'
				    Value 6 means error code 'D'
				    Value 7 means error code 'E'
				    Value 8 means error code 'F'
				    Value 9 means error code 'G'
				    Value 10 means error code 'H'
				    Value 11 means error code 'I'
				    Value 12 means error code 'J'
				    Value 13 means error code 'K'
				    Value 14 means error code 'L'
				    Value 15 means error code 'M'
				    Value 16 means error code 'N'
				    Value 17 means error code 'O'"
			::= { sheIsdnLayer2EventsEntry 1 }

		
		sheIsdnLayer2EventsTimeStamp OBJECT-TYPE
			SYNTAX TimeStamp
			MAX-ACCESS read-only
			STATUS current
			DESCRIPTION
				"TimeStamp of the Layer2 events."
			::= { sheIsdnLayer2EventsEntry 2 }

		
		sheIsdnNotifications OBJECT IDENTIFIER ::= { sheIsdnMib 10 }

		
		sheIsdnTrapEnableStatus OBJECT IDENTIFIER ::= { sheIsdnNotifications 1 }

		
		sheIsdnTrapEnableStatusLineTest OBJECT-TYPE
			SYNTAX SheIsdnEnableStatus
			MAX-ACCESS read-only
			STATUS current
			DESCRIPTION
				"enable:send trap to indicate the line test completed.
				disable:don't send trap to indicates line test completed."
			::= { sheIsdnTrapEnableStatus 1 }

		
		sheIsdnTrapEnableStatusQuickCheck OBJECT-TYPE
			SYNTAX SheIsdnEnableStatus
			MAX-ACCESS read-only
			STATUS current
			DESCRIPTION
				"enable:send trap to indicate the port quick check completed.
				disable:don't send trap to indicates port quick check completed."
			::= { sheIsdnTrapEnableStatus 2 }

		
		sheIsdnTrapEnableControl OBJECT IDENTIFIER ::= { sheIsdnNotifications 2 }

		
		sheIsdnTrapEnableControlRequest OBJECT-TYPE
			SYNTAX SheIsdnControlRequestType
			MAX-ACCESS read-write
			STATUS current
			DESCRIPTION
				"The request of a user command.
				
				setLineTestTrapEnable:
				Must:sheIsdnTrapEnableControlLineTest
				
				setQuickCheckTrapEnable:
				Must:sheIsdnTrapEnableControlQuickCheck"
			::= { sheIsdnTrapEnableControl 1 }

		
		sheIsdnTrapEnableControlReqResult OBJECT-TYPE
			SYNTAX SheIsdnControlReqResultType
			MAX-ACCESS read-only
			STATUS current
			DESCRIPTION
				"The result of a user command."
			::= { sheIsdnTrapEnableControl 2 }

		
		sheIsdnTrapEnableControlLineTest OBJECT-TYPE
			SYNTAX SheIsdnEnableStatus
			MAX-ACCESS read-write
			STATUS current
			DESCRIPTION
				"enable:send trap to indicate the line test completed.
				disable:don't send trap to indicates line test completed."
			::= { sheIsdnTrapEnableControl 3 }

		
		sheIsdnTrapEnableControlQuickCheck OBJECT-TYPE
			SYNTAX SheIsdnEnableStatus
			MAX-ACCESS read-write
			STATUS current
			DESCRIPTION
				"enable:send trap to indicate the port quick check completed.
				disable:don't send trap to indicates port quick check completed."
			::= { sheIsdnTrapEnableControl 4 }

		
		sheIsdnTrapEnableControlTimeStamp OBJECT-TYPE
			SYNTAX TimeStamp
			MAX-ACCESS read-only
			STATUS current
			DESCRIPTION
				"The time stamp of the last command (end of command)."
			::= { sheIsdnTrapEnableControl 5 }

		
		sheIsdnTrapEnableControlStatus OBJECT-TYPE
			SYNTAX SheControlStatusType
			MAX-ACCESS read-only
			STATUS current
			DESCRIPTION
				"The status of a user command."
			::= { sheIsdnTrapEnableControl 6 }

		
		sheIsdnTrapEnableControlTimer OBJECT-TYPE
			SYNTAX Gauge32
			MAX-ACCESS read-only
			STATUS current
			DESCRIPTION
				"TThe maximum wait time for the manager for a long running user command."
			::= { sheIsdnTrapEnableControl 7 }

		
		sheIsdnPMEvents OBJECT IDENTIFIER ::= { sheIsdnNotifications 3 }

		
		sheIsdnPMProfileEvents OBJECT IDENTIFIER ::= { sheIsdnPMEvents 1 }

		
		sheIsdnPmThresholdProfileCreatedTrap NOTIFICATION-TYPE
			OBJECTS { sheIsdnPmThresholdProfileIndex, sheIsdnPmThresholdProfilenName, sheIsdnPmThresholdProfilePer15MinUS, sheIsdnPmThresholdProfilePer15MinES, sheIsdnPmThresholdProfilePer15MinSES, 
				sheIsdnPmThresholdProfilePer15MinBBE, sheIsdnPmThresholdProfilePer24HourUS, sheIsdnPmThresholdProfilePer24HourES, sheIsdnPmThresholdProfilePer24HourSES, sheIsdnPmThresholdProfilePer24HourBBE, 
				sheIsdnPmThresholdProfileControlTimeStamp }
			STATUS current
			DESCRIPTION 
				"Indicates that PM threshold profile is created successfully."
			::= { sheIsdnPMProfileEvents 1 }

		
		sheIsdnPmThresholdProfileDeletedTrap NOTIFICATION-TYPE
			OBJECTS { sheIsdnPmThresholdProfileIndex, sheIsdnPmThresholdProfilenName, sheIsdnPmThresholdProfileControlTimeStamp }
			STATUS current
			DESCRIPTION 
				"Indicates that PM threshlod profile is deleted successfully."
			::= { sheIsdnPMProfileEvents 2 }

		
		sheIsdnPmThresholdProfileModifiedTrap NOTIFICATION-TYPE
			OBJECTS { sheIsdnPmThresholdProfileIndex, sheIsdnPmThresholdProfilenName, sheIsdnPmThresholdProfilePer15MinUS, sheIsdnPmThresholdProfilePer15MinES, sheIsdnPmThresholdProfilePer15MinSES, 
				sheIsdnPmThresholdProfilePer15MinBBE, sheIsdnPmThresholdProfilePer24HourUS, sheIsdnPmThresholdProfilePer24HourES, sheIsdnPmThresholdProfilePer24HourSES, sheIsdnPmThresholdProfilePer24HourBBE, 
				sheIsdnPmThresholdProfileControlTimeStamp }
			STATUS current
			DESCRIPTION 
				"Indicates that PM threshold profile is modified successfully."
			::= { sheIsdnPMProfileEvents 3 }

		
		sheIsdnPMConfigModifedEvents OBJECT IDENTIFIER ::= { sheIsdnPMEvents 2 }

		
		sheIsdnPmConfigModifiedTrap NOTIFICATION-TYPE
			OBJECTS { ifIndex, sheIsdnPmConfigActive, sheIsdnPmConfigThresholdCheckActivated, sheIsdnPmConfigThresholdProfileIndex, sheIsdnPmConfigControlTimeStamp
				 }
			STATUS current
			DESCRIPTION 
				"Indicates that PM config is modified successfully."
			::= { sheIsdnPMConfigModifedEvents 1 }

		
		sheIsdnPmGlobalConfigModifiedTrap NOTIFICATION-TYPE
			OBJECTS { sheIsdnPmConfigActive, sheIsdnPmConfigControlTimeStamp }
			STATUS current
			DESCRIPTION 
				"Indicates that PM global active/deactive successfully."
			::= { sheIsdnPMConfigModifedEvents 2 }

		
		sheIsdnErrGlobalEvents OBJECT IDENTIFIER ::= { sheIsdnNotifications 4 }

		
		sheIsdnErrGlobalModifiedTrap NOTIFICATION-TYPE
			OBJECTS { sheIsdnber10e3Threshold, sheIsdnber10e6Threshold, sheIsdnErrControlTimeStamp }
			STATUS current
			DESCRIPTION 
				"Indicates that the global error configuration modified successfully."
			::= { sheIsdnErrGlobalEvents 1 }

		
		sheIsdnTrapEnableEvents OBJECT IDENTIFIER ::= { sheIsdnNotifications 5 }

		
		sheIsdnTrapEnableModifiedTrap NOTIFICATION-TYPE
			OBJECTS { sheIsdnTrapEnableStatusLineTest, sheIsdnTrapEnableStatusQuickCheck, sheIsdnTrapEnableControlTimeStamp }
			STATUS current
			DESCRIPTION 
				"Indicates that the sheIsdnTrapEnableStatusLineTest or sheIsdnTrapEnableStatusQuickCheck is modified successfully."
			::= { sheIsdnTrapEnableEvents 1 }

		
		sheIsdnPdtaEvents OBJECT IDENTIFIER ::= { sheIsdnNotifications 6 }

		
		sheIsdnPMBSGlobalModifiedTrap NOTIFICATION-TYPE
			OBJECTS { sheIsdnPMBSSourceIP, sheIsdnPMBSSourcePort, sheIsdnPMBSControlTimeStamp }
			STATUS current
			DESCRIPTION 
				"Indicates that sheIsdnPMBSSourceIP or sheIsdnPMBSSourcePort is modified successfully"
			::= { sheIsdnPdtaEvents 1 }

		
		sheIsdnPMBSInterfaceModifiedTrap NOTIFICATION-TYPE
			OBJECTS { ifIndex, sheIsdnPMBSIUAInterfaceIID, sheIsdnPMBSAdminStatus, sheIsdnPMBSControlTimeStamp }
			STATUS current
			DESCRIPTION 
				"Indicates that sheIsdnPMBSIUAInterfaceIID or sheIsdnPMBSAdminStatus is modified successfully"
			::= { sheIsdnPdtaEvents 2 }

		
		sheIsdnPdataWhiteListCreatedTrap NOTIFICATION-TYPE
			OBJECTS { sheIsdnPdataWhiteListIndex, sheIsdnPdataWhiteListIPAdd, sheIsdnPdataWhiteListIPMask, sheIsdnPdataWhiteListPortNum, sheIsdnPdataWhiteListControlTimeStamp
				 }
			STATUS current
			DESCRIPTION 
				"Indicates that Pdata white list is created successfully"
			::= { sheIsdnPdtaEvents 3 }

		
		sheIsdnPdataWhiteListDeletedTrap NOTIFICATION-TYPE
			OBJECTS { sheIsdnPdataWhiteListIndex, sheIsdnPdataWhiteListControlTimeStamp }
			STATUS current
			DESCRIPTION 
				"Indicates that Pdata white list is deleted successfully"
			::= { sheIsdnPdtaEvents 4 }

		
		sheIsdnPortConfigEvents OBJECT IDENTIFIER ::= { sheIsdnNotifications 7 }

		
		sheIsdnPortConfigModifiedTrap NOTIFICATION-TYPE
			OBJECTS { ifIndex, sheIsdnPortConfigBasicRateLineTopology, sheIsdnPortConfigL1PermanentActive, sheIsdnPortConfigPowerFeedingStatus, sheIsdnPortConfigL2PermanentActive, 
				sheIsdnPortConfigL2Out, sheIsdnPortConfigControlTimeStamp }
			STATUS current
			DESCRIPTION 
				"Indicates that sheIsdnPortConfigEntry is modified successfully"
			::= { sheIsdnPortConfigEvents 1 }

		
		sheIsdnPortOutwardTestModifiedTrap NOTIFICATION-TYPE
			OBJECTS { ifIndex, sheIsdnLineTestOutwardTest, sheIsdnLineTestControlTimeStamp }
			STATUS current
			DESCRIPTION 
				"Indicates that sheIsdnLineTestControlOutwardTest is modified successfully"
			::= { sheIsdnPortConfigEvents 2 }

		
		sheIsdnPMAlarms OBJECT IDENTIFIER ::= { sheIsdnNotifications 8 }

		
		sheIsdnPMThreshold15MinESCrossAlarm NOTIFICATION-TYPE
			OBJECTS { sheAlarmTimeAndDate, sheAlarmReportingSource, sheAlarmReportingSourceType, sheAlarmSeverity }
			STATUS current
			DESCRIPTION 
				"Alarm raised when the 15 minutes ES threshold has been crossed."
			::= { sheIsdnPMAlarms 1 }

		
		sheIsdnPMThreshold15MinUSCrossAlarm NOTIFICATION-TYPE
			OBJECTS { sheAlarmTimeAndDate, sheAlarmReportingSource, sheAlarmReportingSourceType, sheAlarmSeverity }
			STATUS current
			DESCRIPTION 
				"Alarm raised when the 15 minutes US threshold has been crossed."
			::= { sheIsdnPMAlarms 2 }

		
		sheIsdnPMThreshold15MinSESCrossAlarm NOTIFICATION-TYPE
			OBJECTS { sheAlarmTimeAndDate, sheAlarmReportingSource, sheAlarmReportingSourceType, sheAlarmSeverity }
			STATUS current
			DESCRIPTION 
				"Alarm raised when the 15 minutes SES threshold has been crossed."
			::= { sheIsdnPMAlarms 3 }

		
		sheIsdnPMThreshold15MinBBECrossAlarm NOTIFICATION-TYPE
			OBJECTS { sheAlarmTimeAndDate, sheAlarmReportingSource, sheAlarmReportingSourceType, sheAlarmSeverity }
			STATUS current
			DESCRIPTION 
				"Alarm raised when the 15 minutes BBE threshold has been crossed."
			::= { sheIsdnPMAlarms 4 }

		
		sheIsdnPMThreshold24HrUSCrossAlarm NOTIFICATION-TYPE
			OBJECTS { sheAlarmTimeAndDate, sheAlarmReportingSource, sheAlarmReportingSourceType, sheAlarmSeverity }
			STATUS current
			DESCRIPTION 
				"Alarm raised when the 24 hour US threshold has been crossed."
			::= { sheIsdnPMAlarms 5 }

		
		sheIsdnPMThreshold24HrESCrossAlarm NOTIFICATION-TYPE
			OBJECTS { sheAlarmTimeAndDate, sheAlarmReportingSource, sheAlarmReportingSourceType, sheAlarmSeverity }
			STATUS current
			DESCRIPTION 
				"Alarm raised when the 24 hour ES threshold has been crossed."
			::= { sheIsdnPMAlarms 6 }

		
		sheIsdnPMThreshold24HrSESCrossAlarm NOTIFICATION-TYPE
			OBJECTS { sheAlarmTimeAndDate, sheAlarmReportingSource, sheAlarmReportingSourceType, sheAlarmSeverity }
			STATUS current
			DESCRIPTION 
				"Alarm raised when the 24 hour SES threshold has been crossed."
			::= { sheIsdnPMAlarms 7 }

		
		sheIsdnPMThreshold24HrBBECrossAlarm NOTIFICATION-TYPE
			OBJECTS { sheAlarmTimeAndDate, sheAlarmReportingSource, sheAlarmReportingSourceType, sheAlarmSeverity }
			STATUS current
			DESCRIPTION 
				"Alarm raised when the 24 hour BBE threshold has been crossed."
			::= { sheIsdnPMAlarms 8 }

		
		sheIsdnAlarms OBJECT IDENTIFIER ::= { sheIsdnNotifications 9 }

		
		sheIsdnLayer1Alarm NOTIFICATION-TYPE
			OBJECTS { sheAlarmTimeAndDate, sheAlarmReportingSource, sheAlarmReportingSourceType, sheAlarmSeverity }
			STATUS current
			DESCRIPTION 
				"Alarm raised when permanent layer 1 is switched on and the port has lost synchronization. 
				Reason for loosing synchronization can be LOF (see above) or link release from the NT side."
			::= { sheIsdnAlarms 1 }

		
		sheIsdnLayer2Alarm NOTIFICATION-TYPE
			OBJECTS { sheAlarmTimeAndDate, sheAlarmReportingSource, sheAlarmReportingSourceType, sheAlarmSeverity }
			STATUS current
			DESCRIPTION 
				"Alarm raised when permanent layer 2 is switched on and the port has lost layer 2 synchron state (because of any reason)."
			::= { sheIsdnAlarms 2 }

		
		sheIsdnBoardLineFeedCentDefAlarm NOTIFICATION-TYPE
			OBJECTS { sheAlarmTimeAndDate, sheAlarmReportingSource, sheAlarmReportingSourceType, sheAlarmSeverity }
			STATUS current
			DESCRIPTION 
				"Alarm raised when global line feeding defect, the sheAlarmReportingSource indicates the slot number."
			::= { sheIsdnAlarms 3 }

		
		sheIsdnBERCrossAlarm NOTIFICATION-TYPE
			OBJECTS { sheAlarmTimeAndDate, sheAlarmReportingSource, sheAlarmReportingSourceType, sheAlarmSeverity }
			STATUS current
			DESCRIPTION 
				"Alarm raised when the BER = 10E-3 crossing in case of permanent layer 1 configuration."
			::= { sheIsdnAlarms 4 }

		
		sheIsdnTestNotifications OBJECT IDENTIFIER ::= { sheIsdnNotifications 10 }

		
		sheIsdnLineTestCompletedTrap NOTIFICATION-TYPE
			OBJECTS { ifIndex, sheIsdnLineTestResult, sheIsdnLineTestControlMode, sheIsdnLineTestControlTimeStamp }
			STATUS current
			DESCRIPTION 
				"Send trap to indicate the line test completed if the sheIsdnLineTestControlTrapEnable 
				is enabled."
			::= { sheIsdnTestNotifications 1 }

		
		sheIsdnPortQuickCheckCompletedTrap NOTIFICATION-TYPE
			OBJECTS { ifIndex, sheIsdnQuickTestNtLoopbackResult, sheIsdnQuickTestLayer1ActivationResult, sheIsdnQuickCheckControlTimeStamp }
			STATUS current
			DESCRIPTION 
				"Send trap to indicate the port quick check completed if the 
				sheIsdnQuickCheckControlTrapEnable is enabled."
			::= { sheIsdnTestNotifications 2 }

		
		sheIsdnPortPowerFeedChangeTrap NOTIFICATION-TYPE
			OBJECTS { ifIndex, sheIsdnPortConfigPowerFeedingStatus, sheIsdnPowerFeedingStatusTimeStamp }
			STATUS current
			DESCRIPTION 
				"Send trap to indicate the port power feeding state changed."
			::= { sheIsdnTestNotifications 3 }

		
		sheIsdnPortLayer2Events NOTIFICATION-TYPE
			OBJECTS { ifIndex, sheIsdnLayer2EventsType, sheIsdnLayer2EventsTimeStamp }
			STATUS current
			DESCRIPTION 
				"Send trap to indicate the port layer 2 events occur."
			::= { sheIsdnTestNotifications 4 }

		
		sheIsdnConformance OBJECT IDENTIFIER ::= { sheIsdnMib 100 }

		
		sheIsdnCompliances OBJECT IDENTIFIER ::= { sheIsdnConformance 1 }

		
		sheIsdnCompliance MODULE-COMPLIANCE
			STATUS current
			DESCRIPTION 
				"Description."
			MODULE -- this module
				MANDATORY-GROUPS { sheIsdnPortConfigObjectsGroup, sheIsdnChannelObjectsGroup, sheIsdnTestObjectsGroup, sheIsdnPdataObjectsGroup, sheIsdnPMObjectsGroup, 
					sheIsdnErrorInfoObjectsGroup, sheIsdnNotificationsGroup }
			::= { sheIsdnCompliances 1 }

		
		sheIsdnGroups OBJECT IDENTIFIER ::= { sheIsdnConformance 2 }

		
		sheIsdnPortConfigObjectsGroup OBJECT-GROUP
			OBJECTS { sheIsdnPortConfigBasicRateIfType, sheIsdnPortConfigBasicRateLineTopology, sheIsdnPortConfigBasicRateIfMode, sheIsdnPortConfigBasicRateSignalMode, sheIsdnPortConfigL1PermanentActive, 
				sheIsdnPortConfigPowerFeedingStatus, sheIsdnPortConfigL2PermanentActive, sheIsdnPortConfigL2Out, sheIsdnPortConfigResetResult, sheIsdnPortConfigControlRequest, 
				sheIsdnPortConfigControlIndex, sheIsdnPortConfigControlReqResult, sheIsdnPortConfigControlBasicRateLineTopology, sheIsdnPortConfigControlL1PermanentActive, sheIsdnPortConfigControlPowerFeeding, 
				sheIsdnPortConfigControlL2PermanentActive, sheIsdnPortConfigControlL2Out, sheIsdnPortConfigControlTimeStamp, sheIsdnPortConfigControStatus, sheIsdnPortConfigControlTimer
				 }
			STATUS current
			DESCRIPTION 
				"Description."
			::= { sheIsdnGroups 1 }

		
		sheIsdnChannelObjectsGroup OBJECT-GROUP
			OBJECTS { sheIsdnChannelSigStatsInCalls, sheIsdnChannelSigStatsInConnected, sheIsdnChannelSigStatsOutCalls, sheIsdnChannelSigStatsOutConnected, sheIsdnChannelSigStatsChargedUnits, 
				sheIsdnChannelLapdPrimary, sheIsdnChannelLapdOperStatus, sheIsdnChannelLapdPeerSabme, sheIsdnChannelLapdRecvdFrmr, sheIsdnChannelLapdInOctets, 
				sheIsdnChannelLapdInUcastPkts, sheIsdnChannelLapdInBroadcastPkts, sheIsdnChannelLapdInDiscards, sheIsdnChannelLapdInErrors, sheIsdnChannelLapdInUnknownProtos, 
				sheIsdnChannelLapdOutOctets, sheIsdnChannelLapdOutUcastPkts, sheIsdnChannelLapdOutBroadcastPkts, sheIsdnChannelLapdOutDiscards, sheIsdnChannelLapdOutErrors, 
				sheIsdnChannelBearerChannelID, sheIsdnChannelBearerOperStatus }
			STATUS current
			DESCRIPTION 
				"Description."
			::= { sheIsdnGroups 2 }

		
		sheIsdnTestObjectsGroup OBJECT-GROUP
			OBJECTS { sheIsdnLineTestResult, sheIsdnLineTestOutwardTest, sheIsdnLineTestMode, sheIsdnLineTestControRequest, sheIsdnLineTestControReqResult, 
				sheIsdnLineTestControIndex, sheIsdnLineTestControlOutwardTest, sheIsdnLineTestControlMode, sheIsdnLineTestControlTimeStamp, sheIsdnLineTestControlTimer, 
				sheIsdnLineTestControlStatus }
			STATUS current
			DESCRIPTION 
				"Description."
			::= { sheIsdnGroups 3 }

		
		sheIsdnPdataObjectsGroup OBJECT-GROUP
			OBJECTS { sheIsdnPMBSSourceIP, sheIsdnPMBSSourcePort, sheIsdnPMBSIUAInterfaceIID, sheIsdnPMBSAdminStatus, sheISDNPMBSControlRequest, 
				sheISDNPMBSControlReqResult, sheISDNPMBSControlIndex, sheISDNPMBSControlInterfaceIID, sheISDNPMBSControlAdminStatus, sheIsdnPMBSControlSourceIP, 
				sheIsdnPMBSControlSourcePort, sheIsdnPMBSControlStatus, sheIsdnPMBSControlTimeStamp, sheIsdnPMBSControlTimer, sheIsdnQuickTestNtLoopbackResult, 
				sheIsdnQuickTestLayer1ActivationResult, sheIsdnQuickTestControlRequest, sheIsdnQuickTestControlReqResult, sheIsdnQuickTestControlIndex, sheIsdnQuickCheckControlTimeStamp, 
				sheIsdnQuickCheckControlStatus, sheIsdnQuickCheckControlTimer, sheIsdnPMBSPLLIndex, sheIsdnPMBSPLLTEINum, sheIsdnPMBSConnectionTime, 
				sheIsdnPMBSPLLSentFrame, sheISDNPMBSPLLReceiveFrames, sheIsdnPdataPHNumIndex, sheIsdnPdataPHIPAdd, sheIsdnPdataPHPortNum, 
				sheIsdnPdataPHStatus, sheIsdnPdataWhiteListIndex, sheIsdnPdataWhiteListIPAdd, sheIsdnPdataWhiteListIPMask, sheIsdnPdataWhiteListPortNum, 
				sheIsdnPdataWhiteListControlRequest, sheIsdnPdataWhiteListControlReqResult, sheIsdnPdataWhiteListControlIndex, sheIsdnPdataWhiteListControlIP, sheIsdnPdataWhiteListControlMask, 
				sheIsdnPdataWhiteListControlPort, sheIsdnPdataWhiteListControlTimeStamp, sheIsdnPdataWhiteListControlStatus, sheIsdnPdataWhiteListControlTimer }
			STATUS current
			DESCRIPTION 
				"Description."
			::= { sheIsdnGroups 4 }

		
		sheIsdnPMObjectsGroup OBJECT-GROUP
			OBJECTS { sheIsdnPmThresholdProfileIndex, sheIsdnPmThresholdProfilenName, sheIsdnPmThresholdProfilePer15MinUS, sheIsdnPmThresholdProfilePer15MinES, sheIsdnPmThresholdProfilePer15MinSES, 
				sheIsdnPmThresholdProfilePer15MinBBE, sheIsdnPmThresholdProfilePer24HourUS, sheIsdnPmThresholdProfilePer24HourES, sheIsdnPmThresholdProfilePer24HourSES, sheIsdnPmThresholdProfilePer24HourBBE, 
				sheIsdnPmThresholdProfileControlRequest, sheIsdnPmThresholdProfileControlReqResult, sheIsdnPmThresholdProfileControlName, sheIsdnPmThresholdProfileControlIndex, sheIsdnPmThresholdProfileControlPer15MinUS, 
				sheIsdnPmThresholdProfileControlPer15MinES, sheIsdnPmThresholdProfileControlPer15MinSES, sheIsdnPmThresholdProfileControlPer15MinBBE, sheIsdnPmThresholdProfileControlPer24HourUS, sheIsdnPmThresholdProfileControlPer24HourES, 
				sheIsdnPmThresholdProfileControlPer24HourSES, sheIsdnPmThresholdProfileControlPer24HourBBE, sheIsdnPmThresholdProfileControlTimeStamp, sheIsdnPmThresholdProfileControlStatus, sheIsdnPmThresholdProfileControlTimer, 
				sheIsdnPmConfigActive, sheIsdnPmConfigThresholdCheckActivated, sheIsdnPmConfigThresholdProfileIndex, sheIsdnPmConfigControlRequest, sheIsdnPmConfigControlIndex, 
				sheIsdnPmConfigControlReqResult, sheIsdnPmConfigControlActive, sheIsdnPmConfigControlThresProfileIndex, sheIsdnPmConfigControlThresCheckActivated, sheIsdnPmConfigControlTimeStamp, 
				sheIsdnPmConfigControlStatus, sheIsdnPmConfigControlTimer, sheIsdnPmActual15MinUS, sheIsdnPmActual15MinES, sheIsdnPmActual15MinSES, 
				sheIsdnPmActual15MinBBE, sheIsdnPmActual24HourUS, sheIsdnPmActual24HourES, sheIsdnPmActual24HourSES, sheIsdnPmActual24HourBBE, 
				sheIsdnPmPer15MinHistroyIndex, sheIsdnPmPre15MinHistroyUSCounters, sheIsdnPmPre15MinHistroyESCounters, sheIsdnPmPre15MinHistroySESCounters, sheIsdnPmPre15MinHistroyBBECounters, 
				sheIsdnPmPer24HourHistroyIndex, sheIsdnPmPre24HourHistroyUSCounters, sheIsdnPmPre24HourHistroyESCounters, sheIsdnPmPre24HourHistroySESCounters, sheIsdnPmPre24HourHistroyBBECounters
				 }
			STATUS current
			DESCRIPTION 
				"Description."
			::= { sheIsdnGroups 5 }

		
		sheIsdnErrorInfoObjectsGroup OBJECT-GROUP
			OBJECTS { sheIsdnber10e3Threshold, sheIsdnber10e6Threshold, sheIsdnPowerFeedingStatusTimeStamp, sheIsdnErrControlRequest, sheIsdnErrControlReqResult, 
				sheIsdnber10e3ControlThreshold, sheIsdnber10e6ControlThreshold, sheIsdnErrControlTimeStamp, sheIsdnErrControlStatus, sheIsdnErrControlTimer, 
				sheIsdnTimeStampLastL1BreakDown, sheIsdnTimeStampLastL2Deactivation, sheIsdnTimeStampLastBerCrossing, sheISDNTimeStampLastPortDeactivation, sheIsdnLayer2EventsType, 
				sheIsdnLayer2EventsTimeStamp, sheIsdnTrapEnableStatusLineTest, sheIsdnTrapEnableStatusQuickCheck, sheIsdnTrapEnableControlRequest, sheIsdnTrapEnableControlReqResult, 
				sheIsdnTrapEnableControlLineTest, sheIsdnTrapEnableControlQuickCheck, sheIsdnTrapEnableControlTimeStamp, sheIsdnTrapEnableControlStatus, sheIsdnTrapEnableControlTimer
				 }
			STATUS current
			DESCRIPTION 
				"Description."
			::= { sheIsdnGroups 6 }

		
		sheIsdnNotificationsGroup NOTIFICATION-GROUP
			NOTIFICATIONS { sheIsdnPmThresholdProfileCreatedTrap, sheIsdnPmThresholdProfileDeletedTrap, sheIsdnPmThresholdProfileModifiedTrap, sheIsdnPmConfigModifiedTrap, sheIsdnPmGlobalConfigModifiedTrap, 
				sheIsdnTrapEnableModifiedTrap, sheIsdnPMBSGlobalModifiedTrap, sheIsdnPMBSInterfaceModifiedTrap, sheIsdnPdataWhiteListCreatedTrap, sheIsdnPdataWhiteListDeletedTrap, 
				sheIsdnPortConfigModifiedTrap, sheIsdnPortOutwardTestModifiedTrap, sheIsdnPMThreshold15MinESCrossAlarm, sheIsdnPMThreshold15MinUSCrossAlarm, sheIsdnPMThreshold15MinSESCrossAlarm, 
				sheIsdnPMThreshold15MinBBECrossAlarm, sheIsdnPMThreshold24HrUSCrossAlarm, sheIsdnPMThreshold24HrESCrossAlarm, sheIsdnPMThreshold24HrSESCrossAlarm, sheIsdnPMThreshold24HrBBECrossAlarm, 
				sheIsdnLayer1Alarm, sheIsdnLayer2Alarm, sheIsdnBoardLineFeedCentDefAlarm, sheIsdnBERCrossAlarm, sheIsdnLineTestCompletedTrap, 
				sheIsdnPortQuickCheckCompletedTrap, sheIsdnPortPowerFeedChangeTrap, sheIsdnPortLayer2Events, sheIsdnErrGlobalModifiedTrap }
			STATUS current
			DESCRIPTION 
				"Description."
			::= { sheIsdnGroups 7 }

		
	
	END

--
-- she-isdn-mib.mib
--
