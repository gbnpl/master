--
-- she-tc-mib.mib
-- MIB generated by MG-SOFT Visual MIB Builder Version 5.0  Build 250
-- Friday, August 18, 2006 at 14:51:36
--

	DS-SHE-TC-MIB DEFINITIONS ::= BEGIN
 
		IMPORTS
			she			
				FROM AN-MIB
			dsShe
				FROM DASAN-SMI							
			MODULE-IDENTITY			
				FROM SNMPv2-SMI			
			TEXTUAL-CONVENTION			
				FROM SNMPv2-TC;
	
	
--  1.3.6.1.4.1.231.7.1.2.2.1.7
		sheTcMib MODULE-IDENTITY 
			LAST-UPDATED "200608181000Z"		-- August 18, 2006 at 10:00 GMT
			ORGANIZATION 
				"Siemens AG"
			CONTACT-INFO 
				"Gerd Barchmann
				Siemens AG, Com FN A PG D HW
				gerd.barchmann@siemens.com
				+493834 555654"
			DESCRIPTION 
				"Description."
			REVISION "200501101228Z"		-- January 10, 2005 at 12:28 GMT
			DESCRIPTION 
				"Change contens of SheAdminStateType to the corresponding standart values from if-Mib."
			REVISION "200608181450Z"		-- August 18, 2006 at 14:50 GMT
			DESCRIPTION 
				"Add enable type."
			::= { dsShe 7 }

		
	
--
-- Textual conventions
--
	
--  Textual conventions
-- 
-- Textual conventions
-- 
		SheControlStatusType ::= TEXTUAL-CONVENTION
			STATUS current
			DESCRIPTION 
				"The control status of an entity."
			SYNTAX INTEGER
				{
				requestIdle(1),
				requestBusy(2),
				requestPassed(3),
				requestFailed(4)
				}

		ShePermissionType ::= TEXTUAL-CONVENTION
			STATUS current
			DESCRIPTION 
				"Description."
			SYNTAX INTEGER
				{
				deny(0),
				permit(1)
				}

		SheOperStateType ::= TEXTUAL-CONVENTION
			STATUS current
			DESCRIPTION 
				"Description."
			SYNTAX INTEGER
				{
				enabled(1),
				disabled(2)
				}

		SheAdminStateType ::= TEXTUAL-CONVENTION
			STATUS current
			DESCRIPTION 
				"Description."
			SYNTAX INTEGER
				{
				up(1),
				down(2),
				testing(3)
				}

		SheCardType ::= TEXTUAL-CONVENTION
			STATUS current
			DESCRIPTION 
				"Type for card type."
			SYNTAX OCTET STRING (SIZE (0..20))

		SheSystemFileIndexType ::= TEXTUAL-CONVENTION
			STATUS current
			DESCRIPTION 
				" Sytem file index type."
			SYNTAX INTEGER (1..8)

		SheEnableType ::= TEXTUAL-CONVENTION
			STATUS current
			DESCRIPTION 
				"SHE enable type."
			SYNTAX INTEGER
				{
				disable(0),
				enable(1)
				}

	
--
-- Node definitions
--
	
	
	END

--
-- she-tc-mib.mib
--
