--
-- she-selt-mib.mib
-- MIB generated by MG-SOFT Visual MIB Builder Version 5.0  Build 250
-- Friday, September 15, 2006 at 14:35:11
--

	DS-SHE-SELT-MIB DEFINITIONS ::= BEGIN
 
		IMPORTS
			she			
				FROM AN-MIB
			dsShe
				FROM DASAN-SMI							
			ifIndex, InterfaceIndex			
				FROM IF-MIB			
			SheControlStatusType			
				FROM DS-SHE-TC-MIB			
			OBJECT-GROUP, MODULE-COMPLIANCE, NOTIFICATION-GROUP			
				FROM SNMPv2-CONF			
			IpAddress, Unsigned32, Gauge32, OBJECT-TYPE, MODULE-IDENTITY, 
			NOTIFICATION-TYPE			
				FROM SNMPv2-SMI			
			TEXTUAL-CONVENTION			
				FROM SNMPv2-TC;
	
	
		sheSelt MODULE-IDENTITY 
			LAST-UPDATED "200609151040Z"		-- September 15, 2006 at 10:40 GMT
			ORGANIZATION 
				"Siemens AG"
			CONTACT-INFO 
				"hongjing.sun@siemens.com
				
				Gerd Barchmann
				Com FN A PG HW
				gerd.barchmann@siemens.com"
			DESCRIPTION 
				" Definition of selt feature control command"
			REVISION "200608111044Z"		-- August 11, 2006 at 10:44 GMT
			DESCRIPTION 
				"Take over by Gerd Barchmann for R2.5."
			REVISION "200609151354Z"		-- September 15, 2006 at 13:54 GMT
			DESCRIPTION 
				"Replace TimeTicks by Unsigned32 in controlgroup TimeStamp values.
				Add compliance statement."
			::= { dsShe 23 }

		
	
--
-- Textual conventions
--
	
		SheSeltServerInfoConnectStateType ::= TEXTUAL-CONVENTION
			STATUS current
			DESCRIPTION 
				"The connection type between CXU and SELT server."
			SYNTAX INTEGER
				{
				sheSeltServerConnected(1),
				sheSeltServerDisconnected(2)
				}

		SheSeltServerControlReqType ::= TEXTUAL-CONVENTION
			STATUS current
			DESCRIPTION 
				"The type for SELT connection control commands."
			SYNTAX INTEGER
				{
				seltConfigSeltServer(1),
				seltConnectSeltServer(2),
				seltDisconnectSeltServer(3)
				}

		SheSeltServerControlReqResultType ::= TEXTUAL-CONVENTION
			STATUS current
			DESCRIPTION 
				"The result type for SELT connection control commands."
			SYNTAX INTEGER
				{
				seltControlServerReqNotSupported(4),
				commExecStarted(30),
				paramFaulty(31),
				requestBusy(32),
				setDataFailed(34),
				aswTimeout(35),
				commandFailed(36),
				commandSucceeded(37)
				}

--  GENERAL VALUES FOR USER COMMAND HANDLING
-- RETURN VALUES
		SheSeltTestRequestIfStateType ::= TEXTUAL-CONVENTION
			STATUS current
			DESCRIPTION 
				"The state type of port (IfIndex)."
			SYNTAX INTEGER
				{
				sheSeltStatusIfBeingTested(1),
				sheSeltStatusIfBeingIdle(2)
				}

		SheSeltTestRequestIuStateType ::= TEXTUAL-CONVENTION
			STATUS current
			DESCRIPTION 
				"The state type of IU (IuIndex)."
			SYNTAX INTEGER
				{
				sheSeltStatusIuBeingTested(1),
				sheSeltStatusIuBeingIdle(2)
				}

--  Start: Add some data type.
		SheSeltTestRequestControlReqFDRCollectionEnableType ::= TEXTUAL-CONVENTION
			STATUS current
			DESCRIPTION 
				"ControlRequest types."
			SYNTAX INTEGER
				{
				seltFDRCollectionDisable(0),
				seltFDRCollectionEnable(1)
				}

--  GENERAL VALUES FOR USER COMMAND HANDLING
-- RETURN VALUES
		SheSeltTestRequestControlReqType ::= TEXTUAL-CONVENTION
			STATUS current
			DESCRIPTION 
				"The type for SELT test command."
			SYNTAX INTEGER
				{
				seltStartSeltRequest(1),
				seltStopSeltRequest(2)
				}

		SheSeltTestRequestControlReqResultType ::= TEXTUAL-CONVENTION
			STATUS current
			DESCRIPTION 
				"The result type for SELT test command."
			SYNTAX INTEGER
				{
				seltRequestControlReqNotSupported(2),
				commExecStarted(30),
				paramFaulty(31),
				requestBusy(32),
				setDataFailed(34),
				aswTimeout(35),
				commandFailed(36),
				commandSucceeded(37),
				seltStopNotSupported(38)
				}

	
--
-- Node definitions
--
	
--  End: Add some data type.
-- -----------------------------------------------------------------
--       sheSeltServerObjects
-- -----------------------------------------------------------------
-- 
		sheSeltServerObjects OBJECT IDENTIFIER ::= { sheSelt 1 }

		
		sheSeltServerObjectsConnectState OBJECT-TYPE
			SYNTAX SheSeltServerInfoConnectStateType
			MAX-ACCESS read-only
			STATUS current
			DESCRIPTION
				"Indicates the connection state between CXU and SELT server."
			::= { sheSeltServerObjects 1 }

		
		sheSeltServerObjectsServerIP OBJECT-TYPE
			SYNTAX IpAddress
			MAX-ACCESS read-only
			STATUS current
			DESCRIPTION
				"Indicates IP address of SELT server."
			::= { sheSeltServerObjects 2 }

		
		sheSeltServerObjectsServicePort OBJECT-TYPE
			SYNTAX Unsigned32
			MAX-ACCESS read-only
			STATUS current
			DESCRIPTION
				"Indicates SELT service port of SELT server."
			::= { sheSeltServerObjects 3 }

		
-- -----------------------------------------------------------------
-- Single End Loop Test selt server control group  
-- -----------------------------------------------------------------
-- 
		sheSeltServerControl OBJECT IDENTIFIER ::= { sheSelt 2 }

		
		sheSeltServerControlReq OBJECT-TYPE
			SYNTAX SheSeltServerControlReqType
			MAX-ACCESS read-write
			STATUS current
			DESCRIPTION
				"Control connection between CXU and SELT server(config SELT server IP address and service port,
				connect CXU to SELT server and disconnect CXU with SELT server.SELT server is used to receive
				and collect selt raw data from plugin unit IU throuth CXU, to calculate and then to send selt result to CXU, 
				so before doing selt test,SELT server must be configed and connected.A config command is permanent 
				unless we need to change SELT sever's IP address or service port.A connect command supports all IU's
				selt test unless the connection is close for some reasons."
			::= { sheSeltServerControl 1 }

		
		sheSeltServerControlServerIP OBJECT-TYPE
			SYNTAX IpAddress
			MAX-ACCESS read-write
			STATUS current
			DESCRIPTION
				"SELT server's IP address."
			::= { sheSeltServerControl 2 }

		
		sheSeltServerControlServicePort OBJECT-TYPE
			SYNTAX Unsigned32
			MAX-ACCESS read-write
			STATUS current
			DESCRIPTION
				"SELT service port number."
			::= { sheSeltServerControl 3 }

		
		sheSeltServerControlStatus OBJECT-TYPE
			SYNTAX SheControlStatusType
			MAX-ACCESS read-only
			STATUS current
			DESCRIPTION
				"The status of a control request."
			::= { sheSeltServerControl 4 }

		
		sheSeltServerControlTimer OBJECT-TYPE
			SYNTAX Gauge32
			MAX-ACCESS read-only
			STATUS current
			DESCRIPTION
				"The maximum wait time for the manager for a long running user command."
			::= { sheSeltServerControl 5 }

		
		sheSeltServerControlReqResult OBJECT-TYPE
			SYNTAX SheSeltServerControlReqResultType
			MAX-ACCESS read-only
			STATUS current
			DESCRIPTION
				"The result of the last user command."
			::= { sheSeltServerControl 6 }

		
		sheSeltServerControlTimeStamp OBJECT-TYPE
			SYNTAX Unsigned32
			UNITS "sec"
			MAX-ACCESS read-only
			STATUS current
			DESCRIPTION
				"The time stamp of the last command (end of command). "
			::= { sheSeltServerControl 7 }

		
--  -----------------------------------------------------------------
-- sheSeltTestRequestObjects        
-- -----------------------------------------------------------------
-- 
		sheSeltTestRequestObjects OBJECT IDENTIFIER ::= { sheSelt 3 }

		
		sheSeltTestRequestIfStateTable OBJECT-TYPE
			SYNTAX SEQUENCE OF SheSeltTestRequestIfStateEntry
			MAX-ACCESS not-accessible
			STATUS current
			DESCRIPTION
				"Each entry in this table contains the testing status of each IfIndex and its related IuIndex."
			::= { sheSeltTestRequestObjects 1 }

		
		sheSeltTestRequestIfStateEntry OBJECT-TYPE
			SYNTAX SheSeltTestRequestIfStateEntry
			MAX-ACCESS not-accessible
			STATUS current
			DESCRIPTION
				"An entry in sheSeltStatusIfTable."
			INDEX { sheSeltTestRequestIfIndex }
			::= { sheSeltTestRequestIfStateTable 1 }

		
		SheSeltTestRequestIfStateEntry ::=
			SEQUENCE { 
				sheSeltTestRequestIfIndex
					InterfaceIndex,
				sheSeltTestRequestIfState
					SheSeltTestRequestIfStateType,
				sheSeltTestRequestIuState
					SheSeltTestRequestIuStateType,
				sheSeltTestRequestIfFDRCollectionEnableState
					SheSeltTestRequestControlReqFDRCollectionEnableType,
				sheSeltTestRequestIfFDRCollectionNumAverageState
					INTEGER
			 }

		sheSeltTestRequestIfIndex OBJECT-TYPE
			SYNTAX InterfaceIndex (100..2000)
			MAX-ACCESS read-only
			STATUS current
			DESCRIPTION
				"IfIndex: the Index of port(such as: 101, 102...172; 201, 202...272; ...)
				"
			::= { sheSeltTestRequestIfStateEntry 1 }

		
		sheSeltTestRequestIfState OBJECT-TYPE
			SYNTAX SheSeltTestRequestIfStateType
			MAX-ACCESS read-only
			STATUS current
			DESCRIPTION
				"The selt test status of port (IfIndex).
				If current port is under selt test, its sheSeltTestRequestIfState = sheSeltStatusIfBeingTested,
				otherwise its sheSeltTestRequestIfState = sheSeltStatusIfBeingIdle.
				"
			::= { sheSeltTestRequestIfStateEntry 2 }

		
		sheSeltTestRequestIuState OBJECT-TYPE
			SYNTAX SheSeltTestRequestIuStateType
			MAX-ACCESS read-only
			STATUS current
			DESCRIPTION
				"The selt test status of IU of this port.
				Every port must know whether this IU is under selt test or not,
				in order to decide if the selt test request on this port can be accepted.
				If any port of its IU is under selt test,
				sheSeltTestRequestIuState = sheSeltStatusIuBeingTested;
				If all ports are not under selt test,
				sheSeltTestRequestIuState = sheSeltStatusIuBeingIdle
				For example:
				If port 101 is under selt test, 
				sheSeltTestRequestIuState of 101 and 102 are both sheSeltStatusIuBeingTested.
				"
			::= { sheSeltTestRequestIfStateEntry 3 }

		
		sheSeltTestRequestIfFDRCollectionEnableState OBJECT-TYPE
			SYNTAX SheSeltTestRequestControlReqFDRCollectionEnableType
			MAX-ACCESS read-only
			STATUS current
			DESCRIPTION
				"The value of FDRCollectionEnable for this port, if it is under selt test.
				If this port is not under selt test, return FDRCollectionDisable(0).
				"
			::= { sheSeltTestRequestIfStateEntry 4 }

		
		sheSeltTestRequestIfFDRCollectionNumAverageState OBJECT-TYPE
			SYNTAX INTEGER (1..65535)
			MAX-ACCESS read-only
			STATUS current
			DESCRIPTION
				"The value of FDRCollectionNumAverage for this port, if it is under selt test.
				If this port is not under selt test, return 0.
				"
			::= { sheSeltTestRequestIfStateEntry 5 }

		
--  -----------------------------------------------------------------
-- Single End Loop Test request control group  
-- -----------------------------------------------------------------
-- 
		sheSeltTestRequestControl OBJECT IDENTIFIER ::= { sheSelt 4 }

		
		sheSeltTestRequestControlReq OBJECT-TYPE
			SYNTAX SheSeltTestRequestControlReqType
			MAX-ACCESS read-write
			STATUS current
			DESCRIPTION
				"Controls CXU to send doing selt test to IU for a specified subscriber's loop.Note that
				simultaneous tests of subscriber's loop on different IUs are allowed, but simultaneous tests
				of different subscribers' loops on the same IU are not allowed. When IU received the command
				it'll begin to process and send raw data to CXU,then to SELT server."
			::= { sheSeltTestRequestControl 1 }

		
		sheSeltTestRequestControlReqIfIndex OBJECT-TYPE
			SYNTAX InterfaceIndex (100..2000)
			MAX-ACCESS read-write
			STATUS current
			DESCRIPTION
				"The interface index of the ADSL central PPTP
				for which selt shall be activated. "
			::= { sheSeltTestRequestControl 2 }

		
		sheSeltTestRequestControlReqComdId OBJECT-TYPE
			SYNTAX Unsigned32
			MAX-ACCESS read-write
			STATUS current
			DESCRIPTION
				"Command ID of one single end loop test. "
			::= { sheSeltTestRequestControl 3 }

		
		sheSeltTestRequestControlStatus OBJECT-TYPE
			SYNTAX SheControlStatusType
			MAX-ACCESS read-only
			STATUS current
			DESCRIPTION
				"The status of a control request."
			::= { sheSeltTestRequestControl 4 }

		
		sheSeltTestRequestControlTimer OBJECT-TYPE
			SYNTAX Gauge32
			MAX-ACCESS read-only
			STATUS current
			DESCRIPTION
				"The maximum wait time for the manager for a long running user command."
			::= { sheSeltTestRequestControl 5 }

		
		sheSeltTestRequestControlReqResult OBJECT-TYPE
			SYNTAX SheSeltTestRequestControlReqResultType
			MAX-ACCESS read-only
			STATUS current
			DESCRIPTION
				"The result of the last user command."
			::= { sheSeltTestRequestControl 6 }

		
		sheSeltTestRequestControlReqTimeStamp OBJECT-TYPE
			SYNTAX Unsigned32
			UNITS "sec"
			MAX-ACCESS read-only
			STATUS current
			DESCRIPTION
				"The time stamp of the last command (end of command)."
			::= { sheSeltTestRequestControl 7 }

		
--  Start: Add some parameters.
-- (1) Enable FDR Data Collection
-- 
		sheSeltTestRequestControlReqFDRCollectionEnable OBJECT-TYPE
			SYNTAX SheSeltTestRequestControlReqFDRCollectionEnableType
			MAX-ACCESS read-write
			STATUS current
			DESCRIPTION
				"This parameter is specific for Infineon line card, but
				not for Conexant line card. 
				This parameter is to enable/disable FDR Data Collection. 
				Two kinds of value can be selected as following:
				I.  Disable (0)
				II. Enable  (1)
				"
			::= { sheSeltTestRequestControl 8 }

		
--  (2) Number of Averages for FDR Data Collection
-- 
		sheSeltTestRequestControlReqFDRCollectionNumAverage OBJECT-TYPE
			SYNTAX Unsigned32 (1..65535)
			MAX-ACCESS read-write
			STATUS current
			DESCRIPTION
				"This parameter is specific for Infineon line card, but
				not for Conexant line card. 
				This parameter is to set the number of average for FDR Data 
				Collection when sheSeltTestRequestControlReqFDRCollectionEnable
				is Enable(1). When sheSeltTestRequestControlReqFDRCollectionEnable
				is Disable(0), this one will be igored.
				The range of this one is [1, 65535], and the default value is 1024.
				With this default number of averages, a single data collection
				will take approximately 90 seconds."
			::= { sheSeltTestRequestControl 9 }

		
--  End: Add some parameters.
-- -----------------------------------------------------------------
--       Single End Loop Test Notifications for ADSL
-- -----------------------------------------------------------------
-- 
		sheSeltNotifications OBJECT IDENTIFIER ::= { sheSelt 5 }

		
		sheSeltServerControlResultEvent NOTIFICATION-TYPE
			OBJECTS { sheSeltServerControlReq, sheSeltServerControlReqResult, sheSeltServerControlTimeStamp }
			STATUS current
			DESCRIPTION 
				" Succeeded or failed to connect with SELT server. "
			::= { sheSeltNotifications 1 }

		
		sheSeltTestRequestControlResultEvent NOTIFICATION-TYPE
			OBJECTS { sheSeltTestRequestControlReq, sheSeltTestRequestControlReqIfIndex, sheSeltTestRequestControlReqComdId, sheSeltTestRequestControlReqResult, sheSeltTestRequestControlReqTimeStamp
				 }
			STATUS current
			DESCRIPTION 
				" Succeeded or failed to execute the command of selt request. "
			::= { sheSeltNotifications 2 }

		
		sheSeltReceivedRawDataEvent NOTIFICATION-TYPE
			OBJECTS { sheSeltTestRequestControlReqIfIndex, sheSeltTestRequestControlReqComdId }
			STATUS current
			DESCRIPTION 
				" Having received raw data from IU. "
			::= { sheSeltNotifications 3 }

		
		sheSeltNoReceivedRawDataEvent NOTIFICATION-TYPE
			OBJECTS { sheSeltTestRequestControlReqIfIndex, sheSeltTestRequestControlReqComdId }
			STATUS current
			DESCRIPTION 
				" Having not received raw data from IU. "
			::= { sheSeltNotifications 4 }

		
		sheSeltConformance OBJECT IDENTIFIER ::= { sheSelt 100 }

		
		sheSeltGroups OBJECT IDENTIFIER ::= { sheSeltConformance 1 }

		
--    units of conformance
-- 
		sheSeltGroup OBJECT-GROUP
			OBJECTS { sheSeltServerObjectsConnectState, sheSeltServerObjectsServerIP, sheSeltServerObjectsServicePort, sheSeltTestRequestIfIndex, sheSeltTestRequestIfState, 
				sheSeltTestRequestIuState, sheSeltTestRequestIfFDRCollectionEnableState, sheSeltTestRequestIfFDRCollectionNumAverageState }
			STATUS current
			DESCRIPTION 
				"A collection of objects providing information about
				a VDSL Line."
			::= { sheSeltGroups 1 }

		
		sheSeltControlGroup OBJECT-GROUP
			OBJECTS { sheSeltServerControlReq, sheSeltServerControlServerIP, sheSeltServerControlServicePort, sheSeltServerControlStatus, sheSeltServerControlTimer, 
				sheSeltServerControlReqResult, sheSeltServerControlTimeStamp, sheSeltTestRequestControlReq, sheSeltTestRequestControlReqIfIndex, sheSeltTestRequestControlReqComdId, 
				sheSeltTestRequestControlStatus, sheSeltTestRequestControlTimer, sheSeltTestRequestControlReqResult, sheSeltTestRequestControlReqTimeStamp, sheSeltTestRequestControlReqFDRCollectionEnable, 
				sheSeltTestRequestControlReqFDRCollectionNumAverage }
			STATUS current
			DESCRIPTION 
				"Description."
			::= { sheSeltGroups 2 }

		
		sheSeltNotificationGroup NOTIFICATION-GROUP
			NOTIFICATIONS { sheSeltServerControlResultEvent, sheSeltTestRequestControlResultEvent, sheSeltReceivedRawDataEvent, sheSeltNoReceivedRawDataEvent }
			STATUS current
			DESCRIPTION 
				"This group supports notifications of significant 
				conditions associated with physical objects."
			::= { sheSeltGroups 3 }

		
		sheSeltCompliances OBJECT IDENTIFIER ::= { sheSeltConformance 2 }

		
		sheSeltMibCompliance MODULE-COMPLIANCE
			STATUS current
			DESCRIPTION 
				"Description."
			MODULE -- this module
				MANDATORY-GROUPS { sheSeltGroup, sheSeltControlGroup, sheSeltNotificationGroup }
			::= { sheSeltCompliances 1 }

		
	
	END

--
-- she-selt-mib.mib
--
