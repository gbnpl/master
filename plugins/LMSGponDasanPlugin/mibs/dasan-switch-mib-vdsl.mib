-- *****************************************************************
-- dasanSwitch MIB -  The MIB for Switch Product
--
-- April 2001, Wonhee Lee
-- December 2002, Seungdong Lee
-- May 2003, Donghoon Lee                                    
-- Feb 2004, Donghoon Lee  
-- May 2004, Dongha Lee
-- May 2004, Youkyoung Lee
--
-- Copyright (c) 2001, 2002, 2003 by Dasan Co., Ltd.
-- Copyright (c) 2004  Dasan Networks Inc, 
-- All rights reserved.
-- *****************************************************************
   
-- ********************************************************************************
--  Log for dasanSwitch MIB.
--
--  July 23 2003
--    1. add 15mElapsedTimeSeconds & 1dayElapsedTimeSeconds in dsVdslPortTable.
--    2. add service profile(dsVdslPortUpServiceProfile, dsVdslPortDownServiceProfile) 
--       in dsVdslPortTable.
--    3. add service profile(dsVdslSlotUpServiceProfile, dsVdslSlotDownServicePrile)
--       in dsVdslSlotTable.           
--                     
--  Dec 19 2003
--    1. Add Vdsl profile         
--                           
--  Feb 13 2004
--    1. Set the value of MAX-ACCESS to obsolete between portProfile and portWanOperStatus.                                         
--      (Include both)
--    2. Add dsVdslPortModemReset to the dsVdslPortTable              
--	  3. Add dsVdslSlotLIUReboot to the dsVdslSlotTable
--
--  Mar 8 2004
--    1. add User Mac table                                         
--  
--  Mar 12 2004    
--    1. Add hardwareVersion to dsSwitchSystem.
--    2. add dsVdslPortLineActiveTimePrev1Day / dsVdslPortLineActiveTimeCurr1Day to dsVdslPortTable.
--                            
--  April 7 2004
--    1. add dsSwitchAtTable that support ARP information with physical port.
--
--  April 16 2004
--    1. change description of portIngress: including QAM 20 case.
--
--  May 10 2004
--    1. add some PSDMaskLevel entries in dsVdslPortTable & dsVdslSlotTable.  
--
--  May 20 2004
--    1. Add dsTcTable 
--     
--  July 26 2005
--    1. Add dsUserMacAddress5 ~ 8 
--
--  July 30 2005
--    1. Add dsSerialNumber
--  
--  Dec 13 2005
--    1. Add dsFirmwareVersion
--
--  Dec 17 2005
--    1. change dsSerialNumber as DisplayString
-- ********************************************************************************  
 
DASAN-SWITCH-MIB DEFINITIONS ::= BEGIN
IMPORTS
    MODULE-IDENTITY,
    OBJECT-TYPE,
    Counter32, Gauge32, Counter64,
    Integer32, TimeTicks, mib-2,
    NOTIFICATION-TYPE
    			FROM SNMPv2-SMI
    TEXTUAL-CONVENTION, DisplayString,
    PhysAddress, TruthValue, RowStatus,
    TimeStamp, AutonomousType, TestAndIncr
                        FROM SNMPv2-TC

    MODULE-COMPLIANCE,
    OBJECT-GROUP        FROM SNMPv2-CONF
    ifIndex             FROM IF-MIB
    dasanEvents,dasanMgmt           
                        FROM DASAN-SMI
    dsSubnetConfName
                        FROM DASAN-DHCP-MIB;
 
dasanSwitchMIB MODULE-IDENTITY
    LAST-UPDATED   "200107270000Z"
    ORGANIZATION   "Dasan Co., Ltd."
    CONTACT-INFO
                   "Dasan Co., Ltd."
    DESCRIPTION
        "The MIB module to describe Switch product."
    ::= { dasanMgmt 1 }
 
dasanSwitchMIBObjects  OBJECT IDENTIFIER ::= { dasanSwitchMIB 1 }

dsSwitchSystem           OBJECT IDENTIFIER ::= { dasanSwitchMIBObjects 1 }
dsSwitchModules          OBJECT IDENTIFIER ::= { dasanSwitchMIBObjects 2 }

   -- the Ports table

   -- The Ports table contains All Ports Information on each Node.
                         
   dsPortTable OBJECT-TYPE
       SYNTAX      SEQUENCE OF DsPortEntry
       MAX-ACCESS  not-accessible
       STATUS      current
       DESCRIPTION
               "A list of dsPortEntry entries."
       ::= { dsSwitchModules 4 }

   dsPortEntry OBJECT-TYPE
       SYNTAX      DsPortEntry
       MAX-ACCESS  not-accessible
       STATUS      current
       DESCRIPTION
               "An entry containing management information applicable
               to a particular port."

       INDEX   { dsPortModuleIndex , dsPortPortIndex }
       ::= { dsPortTable 1 }

   DsPortEntry ::=
       SEQUENCE {
           dsPortModuleIndex       INTEGER,
           dsPortPortIndex         INTEGER,
           dsPortType              DisplayString,
           dsPortIfIndex           OBJECT IDENTIFIER,
           dsPortPVID              INTEGER,
           dsPortShared            INTEGER,
           dsPortNego              INTEGER,
           dsPortDuplex            INTEGER,
           dsPortUpSpeed           INTEGER,
           dsPortDownSpeed         INTEGER,
           dsPortFlowControl       INTEGER,
           dsPortIngressrate       Counter,
           dsPortEgressrate        Counter,
           dsPortInstallStatus     INTEGER,
           dsPortCurrentHost       INTEGER,
           dsPortMaxHost           INTEGER,
           dsPortProfile           INTEGER,
           dsPortUpSNR             INTEGER,
           dsPortDownSNR           INTEGER,
           dsPortWanInPkt          INTEGER,
           dsPortWanInErr          INTEGER,
           dsPortWanOutPkt         INTEGER,
           dsPortWanReset          INTEGER,
           dsPortWanLoopbackAction INTEGER,
           dsPortWanLoopbackStatus INTEGER,
           dsPortUpUtil5s          INTEGER,
           dsPortUpUtil1m          INTEGER,
           dsPortUpUtil10m         INTEGER,
           dsPortDownUtil5s        INTEGER,
           dsPortDownUtil1m        INTEGER,
           dsPortDownUtil10m       INTEGER,
           dsPortDescription       DisplayString,
           dsPortWanAdminStatus    INTEGER,
           dsPortWanOperStatus     INTEGER,
           dsPortReset			   INTEGER,
           dsPortSpeed			   INTEGER,
           dsPortCurrUpTime        TimeTicks,
           dsPortPrevUpTime        TimeTicks      
       }

   dsPortModuleIndex OBJECT-TYPE
       SYNTAX      INTEGER
       MAX-ACCESS  read-only
       STATUS      current
       DESCRIPTION
               "A unique value, greater than zero, for each
               module.  It is recommended that values are assigned
               contiguously starting from 1.  The value for each
               interface sub-layer must remain constant at least from
               one re-initialization of the entity's network
               management system to the next re-initialization."
       ::= { dsPortEntry 1 }

   dsPortPortIndex OBJECT-TYPE
       SYNTAX      INTEGER
       MAX-ACCESS  read-only
       STATUS      current
       DESCRIPTION
               "A unique value, greater than zero, for each
               port.  It is recommended that values are assigned
               contiguously starting from 1.  The value for each
               interface sub-layer must remain constant at least from
               one re-initialization of the entity's network
               management system to the next re-initialization."
       ::= { dsPortEntry 2 }

   dsPortType OBJECT-TYPE
       SYNTAX      DisplayString (SIZE (0..64))
       MAX-ACCESS  read-only
       STATUS      current
       DESCRIPTION
               "The type of communication port. This string defines the type
                of port."
       ::= { dsPortEntry 3 }

   dsPortIfIndex OBJECT-TYPE
       SYNTAX      OBJECT IDENTIFIER
       MAX-ACCESS  read-only
       STATUS      current
       DESCRIPTION
               "matching ifIndex oid which is defined in interface mib."
       ::= { dsPortEntry 4 }

   dsPortPVID    OBJECT-TYPE
       -- SYNTAX      INTEGER (SIZE (1..4094)) 
       SYNTAX      INTEGER (1..4094)
       MAX-ACCESS  read-write
       STATUS      current
       DESCRIPTION
               "The PVID of port."
       ::= { dsPortEntry 5 }

   dsPortShared  OBJECT-TYPE
       SYNTAX      INTEGER {
                     enabled(1),
                     disabled(2)
                   }
       MAX-ACCESS  read-only
       STATUS      current
       DESCRIPTION
               "The Shared status of port."
       ::= { dsPortEntry 6 }

   dsPortNego    OBJECT-TYPE
       SYNTAX      INTEGER {
                     auto(1),
                     forced(2),
                     other(3)
                   }
       MAX-ACCESS  read-write
       STATUS      current
       DESCRIPTION
               "The Nego mode of port."
       ::= { dsPortEntry 7 }

   dsPortDuplex  OBJECT-TYPE
       SYNTAX      INTEGER {
                     full(1),
                     half(2),
                     other(3)
                   }
       MAX-ACCESS  read-write
       STATUS      current
       DESCRIPTION
               "The duplex status of port."
       ::= { dsPortEntry 8 }

   dsPortUpSpeed OBJECT-TYPE
       SYNTAX      INTEGER
       MAX-ACCESS  read-only
       STATUS      current
       DESCRIPTION
               "Upstream speed of port. bits/second "
       ::= { dsPortEntry 9 }

   dsPortDownSpeed OBJECT-TYPE
       SYNTAX      INTEGER
       MAX-ACCESS  read-only
       STATUS      current
       DESCRIPTION
               "Downstream speed of port. bits/second "
       ::= { dsPortEntry 10 }

   dsPortFlowControl  OBJECT-TYPE
       SYNTAX      INTEGER {
                     enabled(1),
                     disabled(2),
                     notavailable(3)
                   }
       MAX-ACCESS  read-write
       STATUS      current
       DESCRIPTION
               "The flow control mode of port."
       ::= { dsPortEntry 11 }

   dsPortIngressrate OBJECT-TYPE
       SYNTAX      Counter
       MAX-ACCESS  read-write
       STATUS      current
       DESCRIPTION
               "A incomming rate limit control value.
               In case of Vdsl QAM20, it means constellation value of each port."
       ::= { dsPortEntry 12 }

   dsPortEgressrate OBJECT-TYPE
       SYNTAX      Counter
       MAX-ACCESS  read-write
       STATUS      current
       DESCRIPTION
               "A outgoing rate limit control value."
       ::= { dsPortEntry 13 }


   dsPortInstallStatus  OBJECT-TYPE
       SYNTAX      INTEGER {
	   	     removed(0),
                     installed(1),
                     removed(2),
                     gbicinstalled(3)
                   }
       MAX-ACCESS  read-only
       STATUS      current
       DESCRIPTION
               "The install status of optional module."
       ::= { dsPortEntry 14 }

   dsPortCurrentHost OBJECT-TYPE
       SYNTAX      INTEGER 
       MAX-ACCESS  read-only
       STATUS      current
       DESCRIPTION
               "The number hosts which is allowed to be used."
       ::= { dsPortEntry 15 }

   dsPortMaxHost OBJECT-TYPE
       SYNTAX      INTEGER 
       MAX-ACCESS  read-write
       STATUS      current
       DESCRIPTION
               "The maximum number hosts which can be allowed to be used.
                '-1' means the unlimited max-host value. "
       ::= { dsPortEntry 16 }


--------------------------------------------------------------------------------------
-- 
--   dsPortProfile OBJECT-TYPE
--       SYNTAX      INTEGER {
--                        notavailable(-1),
--                       a-sym11(0),
--                        asym11(1),
--                        sym11(2),
--                        a-asym11(3),
--                        a-sym13(4),
--                        sym16(5),
--                        a-asym13(6),
--                        tl13(7),
--                        tl16(8),
--                        tl16a(9),
--                        asym24(11),
--                        asym18(12),
--                        asym25(13),
--                        asym26(14),
--                        asym50-998n(15),
--                        asym50-998e(16),
--                        sym25-997(17),
--                        asym50-998a(18),
--                        asym50-998i(19),
--                        asym50-998t(20),
--                        asym50-998s(21)                        
--					}
--       MAX-ACCESS  read-write
--       STATUS      obsolete
--       DESCRIPTION
--               "Vdsl profile ID
--                sym11 (2)     Symmetric 11/11
--                asym11 (1)    Asymmetric 3/11
--                a-sym11 (0)   ADSL friendly symmetric 11/11
--                a-asym11 (3)  ADSL friendly asymmetric 3/11
--                a-sym13 (4)   ADSL friendly symmetric 13/13
--                a-asym13 (6)  ADSL friendly asymmetric 3/13
--                sym16 (5)     Symmetric 16/16
--                tl13 (7)      T-LAN friendly 13/13
--                tl16 (8)      T-LAN friendly 16/16
--                tl16a (9)     T-LAN friendly 13/16A (QAM20 ONLY)
--                asym24 (11)   PLAN998 Asymmetric 8/24 (QAM20 ONLY)
--                asym18 (12)   PLAN998 Asymmetric 8/18 (QAM20 ONLY)
--                asym25 (13)   PLAN998 Asymmetric Enhanced 8/25(QAM20 ONLY)
--                asym26 (14)   PLAN998 Asymmetric Enhanced 8/26(QAM20 ONLY)
--                asym50-998n (15)  PLAN998 Asymmetric
--                asym50-998e (16)  PLAN998E Asymmetric
--                sym25-997 (17)    PLAN997 Asymmetric
--                asym50-998a (18)  ADSL friendly PLAN 998 Asymetric
--                asym50-998i (19)  ISDN friendly PLAN 998 Asymetric
--                asym50-998t (20)  TLAN friendly PLAN 998 Asymetric
--                asym50-998s (21)  ADSL soft mode Asymetric"
--       ::= { dsPortEntry 17 }
--
--   dsPortUpSNR OBJECT-TYPE
--       SYNTAX      INTEGER 
--       MAX-ACCESS  read-only
--       STATUS      obsolete
--       DESCRIPTION
--               "Vdsl upstream SNR * 1000."
--       ::= { dsPortEntry 18 }
--
--   dsPortDownSNR OBJECT-TYPE
--       SYNTAX      INTEGER 
--       MAX-ACCESS  read-only
--       STATUS      obsolete
--       DESCRIPTION
--               "Vdsl downstream SNR * 1000."
--       ::= { dsPortEntry 19 }
--
--   dsPortWanInPkt OBJECT-TYPE
--       SYNTAX      INTEGER 
--       MAX-ACCESS  read-only
--       STATUS      obsolete
--       DESCRIPTION
--               "Vdsl WAN in-packet count."
--       ::= { dsPortEntry 20 }
--
--   dsPortWanInErr OBJECT-TYPE
--       SYNTAX      INTEGER 
--       MAX-ACCESS  read-only
--       STATUS      obsolete
--       DESCRIPTION
--              "Vdsl WAN error packet count."
--       ::= { dsPortEntry 21 }
--
--   dsPortWanOutPkt OBJECT-TYPE
--       SYNTAX      INTEGER 
--       MAX-ACCESS  read-only
--       STATUS      obsolete
--       DESCRIPTION
--               "Vdsl WAN out-packet count."
--       ::= { dsPortEntry 22 }
--
--   dsPortWanReset OBJECT-TYPE
--       SYNTAX      INTEGER  { reset(1) }
--       MAX-ACCESS  read-write
--       STATUS      obsolete
--       DESCRIPTION
--               "Reaquire Vdsl line SYNC."
--       ::= { dsPortEntry 23 }
--
--   dsPortWanLoopbackAction OBJECT-TYPE
--       SYNTAX      INTEGER  { loopbacktest(1) }
--       MAX-ACCESS  read-write
--       STATUS      obsolete
--       DESCRIPTION
--               "Perform remote loopback ping test."
--       ::= { dsPortEntry 24 }
--
--   dsPortWanLoopbackStatus OBJECT-TYPE
--       SYNTAX      INTEGER  { never(0), failed(1), succeeded(2) }
--       MAX-ACCESS  read-only
--       STATUS      obsolete
--       DESCRIPTION
--               "Latest remote loopback test result."
--       ::= { dsPortEntry 25 }
--------------------------------------------------------------------------------------


   dsPortUpUtil5s OBJECT-TYPE
       SYNTAX      INTEGER 
       MAX-ACCESS  read-only
       STATUS      current
       DESCRIPTION
               "Upstream traffic utilization during last 5 seconfs. Unit: bps"
       ::= { dsPortEntry 26 }

   dsPortUpUtil1m OBJECT-TYPE
       SYNTAX      INTEGER 
       MAX-ACCESS  read-only
       STATUS      current
       DESCRIPTION
               "Upstream traffic utilization during last 1 minute. Unit: bps"
       ::= { dsPortEntry 27 }

   dsPortUpUtil10m OBJECT-TYPE
       SYNTAX      INTEGER 
       MAX-ACCESS  read-only
       STATUS      current
       DESCRIPTION
               "Upstream traffic utilization during last 10 minute. Unit: bps"
       ::= { dsPortEntry 28 }

   dsPortDownUtil5s OBJECT-TYPE
       SYNTAX      INTEGER 
       MAX-ACCESS  read-only
       STATUS      current
       DESCRIPTION
               "Downstream traffic utilization during last 5 seconfs. Unit: bps"
       ::= { dsPortEntry 29 }

   dsPortDownUtil1m OBJECT-TYPE
       SYNTAX      INTEGER 
       MAX-ACCESS  read-only
       STATUS      current
       DESCRIPTION
               "Downstream traffic utilization during last 1 minute. Unit: bps"
       ::= { dsPortEntry 30 }

   dsPortDownUtil10m OBJECT-TYPE
       SYNTAX      INTEGER 
       MAX-ACCESS  read-only
       STATUS      current
       DESCRIPTION
               "Downstream traffic utilization during last 10 minute. Unit: bps"
       ::= { dsPortEntry 31 }

   dsPortDescription OBJECT-TYPE
       SYNTAX      DisplayString 
       MAX-ACCESS  read-write
       STATUS      current
       DESCRIPTION
               "Port description string"
       ::= { dsPortEntry 32 }

   dsPortWanAdminStatus OBJECT-TYPE
       SYNTAX      INTEGER { down(0), up(1) }
       MAX-ACCESS  read-write
       STATUS      current
       DESCRIPTION
               "Administrative status of WAN port"
       ::= { dsPortEntry 33 }

   dsPortWanOperStatus OBJECT-TYPE
       SYNTAX      INTEGER { down(0), up(1) }
       MAX-ACCESS  read-only
       STATUS      current
       DESCRIPTION
               "Operational status of WAN port"
       ::= { dsPortEntry 34 }
                                          
   dsPortReset OBJECT-TYPE
       SYNTAX      INTEGER { reset(1) }
       MAX-ACCESS  read-write
       STATUS      current
       DESCRIPTION
               "Operational Reset of port"
       ::= { dsPortEntry 35 }

   dsPortSpeed OBJECT-TYPE
   	   SYNTAX		INTEGER  
       UNITS        "bps"
       MAX-ACCESS	read-write 
       STATUS		current
       DESCRIPTION
					"switch port speed. bits/second.
					 these value is vaild, 10000000,100000000,1000000000. "
       ::= { dsPortEntry 40 }

   dsPortCurrUpTime OBJECT-TYPE
       SYNTAX  TimeTicks 
       MAX-ACCESS  read-write
       STATUS  current    
       DESCRIPTION 
               "Port's link-up time within the current one day interval."
       ::= { dsPortEntry 41 }


   dsPortPrevUpTime OBJECT-TYPE
       SYNTAX  TimeTicks  
       MAX-ACCESS  read-write
       STATUS  current    
       DESCRIPTION 
               "Port's link-up time for the previous one day ."
       ::= { dsPortEntry 42 }

--
--  dsSwitchSystem 
--  
    dsResetSystem OBJECT-TYPE
       SYNTAX      INTEGER { reset(1)}
       MAX-ACCESS  read-write
       STATUS      current
       DESCRIPTION
               "Send system-reset to this system."
       ::= { dsSwitchSystem 1 }

    dsWriteConfig OBJECT-TYPE
       SYNTAX      INTEGER { write(1)}
       MAX-ACCESS  read-write
       STATUS      current
       DESCRIPTION
               "Write current running configuration to flash memory."
       ::= { dsSwitchSystem 2 }

    dsOsVersion OBJECT-TYPE
       SYNTAX      DisplayString
       MAX-ACCESS  read-only
       STATUS      current
       DESCRIPTION
               "The version of running OS."
       ::= { dsSwitchSystem 3 }

    dsTftpServer OBJECT-TYPE
       SYNTAX      DisplayString
       MAX-ACCESS  read-write
       STATUS      current
       DESCRIPTION
               "The IP address or hostname of TFTP server."
       ::= { dsSwitchSystem 4 }

    dsTftpFile OBJECT-TYPE
       SYNTAX      DisplayString
       MAX-ACCESS  read-write
       STATUS      current
       DESCRIPTION
               "The Remote file name"
       ::= { dsSwitchSystem 5 }

    dsTftpStatus OBJECT-TYPE
       SYNTAX      INTEGER {
			idle(0),
                        get(1),
                        unknown(2),
                        busy(3),
                        failed(4),
                        succeeded(5),
                        abort(6),
                        put(7)
		}
       MAX-ACCESS  read-write
       STATUS      current
       DESCRIPTION
               "TFTP transaction status. To receive a file from remote server,
                get is used. To send OS or Configuration to remote server,
                put is used. Abort can be used to terminate running tftp client."
       ::= { dsSwitchSystem 6 }

    dsTftpFileType OBJECT-TYPE
       SYNTAX      INTEGER {
			operating-system(0),
            configuration(1),
            cpe-nos(2)
		}
       MAX-ACCESS  read-write
       STATUS      current
       DESCRIPTION
               "TFTP file type.
               The value of cpe-nos(2) is only available, in case of dsVdsl."
       ::= { dsSwitchSystem 7 }                                                
       
--
--  appended :-) dhkim@da-san.com ,  Last updated  2003/02/03
--                       

    dsCpuLoad5s OBJECT-TYPE
       SYNTAX      INTEGER 
       MAX-ACCESS  read-only
       STATUS      current
       DESCRIPTION
               "The Avg. Value of CPU Load for 5 seconds"
       ::= { dsSwitchSystem 8 } 

    dsCpuLoad1m OBJECT-TYPE
       SYNTAX      INTEGER 
       MAX-ACCESS  read-only
       STATUS      current
       DESCRIPTION
               "The Avg. Value of CPU Load for 1 minute"
       ::= { dsSwitchSystem 9 } 

    dsCpuLoad10m OBJECT-TYPE
       SYNTAX      INTEGER 
       MAX-ACCESS  read-only
       STATUS      current
       DESCRIPTION
               "The Avg. Value of CPU Load for 10 minutes"
       ::= { dsSwitchSystem 10 } 

    dsCpuLoad5sisr OBJECT-TYPE
       SYNTAX      INTEGER 
       MAX-ACCESS  read-only
       STATUS      current
       DESCRIPTION
               "The Avg. Value of CPU Load for 5 seconds(interupt service routine)"
       ::= { dsSwitchSystem 11 } 

    dsCpuLoad1misr OBJECT-TYPE
       SYNTAX      INTEGER 
       MAX-ACCESS  read-only
       STATUS      current
       DESCRIPTION
               "The Avg. Value of CPU Load for 1 minute(interupt service routine)"
       ::= { dsSwitchSystem 12 } 

    dsCpuLoad10misr OBJECT-TYPE
       SYNTAX      INTEGER 
       MAX-ACCESS  read-only
       STATUS      current
       DESCRIPTION
               "The Avg. Value of CPU Load for 10 minutes(interupt service routine)"
       ::= { dsSwitchSystem 13 } 

    dsTotalMem OBJECT-TYPE
       SYNTAX      INTEGER 
       MAX-ACCESS  read-only
       STATUS      current
       DESCRIPTION
               "The Total memory of system"
       ::= { dsSwitchSystem 14 }   
       
    dsUsedMem OBJECT-TYPE
       SYNTAX      INTEGER 
       MAX-ACCESS  read-only
       STATUS      current
       DESCRIPTION
               "The Used memory of system"
       ::= { dsSwitchSystem 15 }        

    dsFreeMem OBJECT-TYPE
       SYNTAX      INTEGER 
       MAX-ACCESS  read-only
       STATUS      current
       DESCRIPTION
               "The Free memory of sytem"
       ::= { dsSwitchSystem 16 }  
    
    dsHardwareVersion OBJECT-TYPE       
       SYNTAX      DisplayString
       MAX-ACCESS  read-only
       STATUS      current
       DESCRIPTION
               "The Hardware version of system."
       ::= { dsSwitchSystem 17 }
       
    dsSoftwareCompatibility OBJECT-TYPE
       SYNTAX      INTEGER 
       MAX-ACCESS  read-only
       STATUS      current
       DESCRIPTION
               "The Software Compatibility"
       ::= { dsSwitchSystem 18 }       
       
   dsSerialNumber OBJECT-TYPE
       SYNTAX      DisplayString 
       MAX-ACCESS  read-only
       STATUS      current
       DESCRIPTION
               "The Serial number of system"
       ::= { dsSwitchSystem 19 }     

   dsFirmwareVersion OBJECT-TYPE
       SYNTAX      DisplayString 
       MAX-ACCESS  read-only
       STATUS      current
       DESCRIPTION
               "The Firmware version of system"
       ::= { dsSwitchSystem 20 }

--
-- May 2003
-- dhlee@da-san.com  : dsVdsl ports informations
--

   dsVdslPortTable OBJECT-TYPE
       SYNTAX      SEQUENCE OF DsVdslPortEntry
       MAX-ACCESS  not-accessible
       STATUS      current
       DESCRIPTION
               "A list of dsVdslPortEntry entries."
       ::= { dsSwitchModules 8 }

   dsVdslPortEntry OBJECT-TYPE
       SYNTAX      DsVdslPortEntry
       MAX-ACCESS  not-accessible
       STATUS      current
       DESCRIPTION
               "An entry containing management information applicable
               to a particular dsVdsl port."

       INDEX   { dsVdslModuleIndex , dsVdslPortIndex }
       ::= { dsVdslPortTable 1 }
                              
   DsVdslPortEntry ::=
       SEQUENCE {
           dsVdslModuleIndex                     INTEGER,
           dsVdslPortIndex                       INTEGER,
           dsVdslPortType                        DisplayString,
           dsVdslPortIfIndex                     OBJECT IDENTIFIER,
           -- speed
           dsVdslPortUpProfile                   INTEGER,
           dsVdslPortDownProfile                 INTEGER,
           dsVdslPortUpPhysicalSpeed             INTEGER,           
           dsVdslPortDownPhysicalSpeed           INTEGER,           
           dsVdslPortUpSpeed                     INTEGER,
           dsVdslPortDownSpeed                   INTEGER,
           -- service error  : raw 
           dsVdslPortServiceError                INTEGER,
           dsVdslPortErrorCRC                    INTEGER,
           dsVdslPortErrorSecond				   INTEGER,
           dsVdslPortErrorLOF                    INTEGER,
           dsVdslPortErrorLOS                    INTEGER,
           dsVdslPortErrorLPR                    INTEGER,                    
           dsVdslPortErrorLOL                    INTEGER,           
           -- Elapsed Time 
           dsVdslPort15mElapsedTime			   INTEGER,
           dsVdslPort1dayElapsedTime             INTEGER,
           -- service error  : 15m
           dsVdslPortServiceErrorPrev15m         INTEGER,
           dsVdslPortServiceErrorCurr15m         INTEGER,
           dsVdslPortErrorCRCPrev15m             INTEGER,
           dsVdslPortErrorCRCCurr15m             INTEGER,
           dsVdslPortErrorSecondPrev15m          INTEGER,
           dsVdslPortErrorSecondCurr15m          INTEGER,
           dsVdslPortErrorLOFPrev15m             INTEGER,                    
           dsVdslPortErrorLOFCurr15m             INTEGER,
           dsVdslPortErrorLOSPrev15m             INTEGER,                    
           dsVdslPortErrorLOSCurr15m             INTEGER,
           dsVdslPortErrorLPRPrev15m             INTEGER,                    
           dsVdslPortErrorLPRCurr15m             INTEGER,
           dsVdslPortErrorLOLPrev15m             INTEGER,                    
           dsVdslPortErrorLOLCurr15m             INTEGER,           
           -- service error  : 1day
           dsVdslPortServiceErrorPrev1day        INTEGER,
           dsVdslPortServiceErrorCurr1day        INTEGER,  
           dsVdslPortErrorCRCPrev1day            INTEGER,
           dsVdslPortErrorCRCCurr1day            INTEGER,
           dsVdslPortErrorSecondPrev1day         INTEGER,
           dsVdslPortErrorSecondCurr1day         INTEGER,
           dsVdslPortErrorLOFPrev1day            INTEGER,                    
           dsVdslPortErrorLOFCurr1day            INTEGER,                    
           dsVdslPortErrorLOSPrev1day            INTEGER,                    
           dsVdslPortErrorLOSCurr1day            INTEGER,
           dsVdslPortErrorLPRPrev1day            INTEGER,                    
           dsVdslPortErrorLPRCurr1day            INTEGER,
           dsVdslPortErrorLOLPrev1day            INTEGER,                    
           dsVdslPortErrorLOLCurr1day            INTEGER,
           -- 
           dsVdslPortUpSNR                       INTEGER,
           dsVdslPortDownSNR                     INTEGER,
           dsVdslPortUpSNRMargin                 INTEGER,                                 
           dsVdslPortDownSNRMargin               INTEGER,   
           dsVdslPortUpAttenuation               INTEGER,
           dsVdslPortDownAttenuation             INTEGER,
           dsVdslPortOutPower                    INTEGER,
           dsVdslPortWanInPkt                    INTEGER,
           dsVdslPortWanInErr                    INTEGER,
           dsVdslPortWanOutPkt                   INTEGER,
           dsVdslPortWanReset                    INTEGER,
           dsVdslPortWanLoopbackAction           INTEGER,
           dsVdslPortWanLoopbackStatus           INTEGER,
           dsVdslPortWanAdminStatus              INTEGER,
           dsVdslPortWanOperStatus               INTEGER,
           dsVdslPortVOCLinkStatus			   INTEGER,
           dsVdslPortVOCLinkDuplex               INTEGER,
           dsVdslPortVOCLinkSpeed                INTEGER,
           dsVdslPortOptionband                  INTEGER,
           dsVdslPortHamband					   Counter64,
           dsVdslPortUpInterleave                INTEGER,
           dsVdslPortDownInterleave              INTEGER,
           -- June 2003, newly add --
           dsVdslPortTargetUpSNRMargin		   INTEGER,
           dsVdslPortTargetDownSNRMargin         INTEGER,
           dsVdslPortPSDMaskLevel				   INTEGER,
           dsVdslPortPBOLength				   INTEGER,
           -- July 2003, newly add --       
           dsVdslPort15mElapsedTimeSeconds	   INTEGER,
           dsVdslPort1dayElapsedTimeSeconds      INTEGER,
           dsVdslPortUpServiceProfile			   INTEGER,
           dsVdslPortDownServiceProfile          INTEGER,
           -- Feb 2004, newly add CPE-Modem Management--          
           dsVdslPortModemReset				   INTEGER,
           dsVdslPortCPEVersion				   DisplayString,
           dsVdslPortCPEDownload				   INTEGER,
           dsVdslPortLineActiveTimePrev1Day	   INTEGER,
           dsVdslPortLineActiveTimeCurr1Day	   INTEGER,
           dsVdslPortLineConfProfileClear      INTEGER,
           dsVdslPortAlarmConfProfileClear      INTEGER,
           dsVdslPortEwl						INTEGER,
           dsVdslPortGhsNearEndEwl				INTEGER,
           dsVdslPortGhsFarEndEwl				INTEGER,                         
           -- following mib are referenced upper style..
           dsVdslPortLineActiveTimeClear         INTEGER,   
 		     dsVdslPortServiceErrorClear	       INTEGER,
           dsVdslPortErrorCRCClear			   INTEGER,
           dsVdslPortErrorSecondClear			   INTEGER,
           dsVdslPortErrorLOFClear			   INTEGER,
           dsVdslPortErrorLOSClear			   INTEGER,
           dsVdslPortErrorLPRClear			   INTEGER,
           dsVdslPortErrorLOLClear			   INTEGER,
  		   
  		   -- following mib are not decided to include or not..
 -- 		   dsVdslPortErrorUncorrectCRCClear      INTEGER,
 -- 		   dsVdslPortErrorCorrectCRCClear        INTEGER,
  		   
 -- 		   dsVdslPortErrorServiceErrorSecondClear	INTEGER,
 -- 		   dsVdslPortErrorCRCSecondClear         INTEGER,
 -- 		   dsVdslPortErrorLOFSecondClear         INTEGER,
 -- 		   dsVdslPortErrorLOSSecondClear         INTEGER,
 -- 		   dsVdslPortErrorLOLSecondClear         INTEGER,
 -- 		   dsVdslPortErrorSESSecondClear         INTEGER,
 -- 		   dsVdslPortErrorUASSecondClear         INTEGER,
          
          dsVdslPortErrorCountClear			  	INTEGER,
          dsVdslPortCpeErrorCRC					INTEGER,
--        dsVdslPortCpeErrorSecond				INTEGER,
          dsVdslPortCpePerfLOF					INTEGER,
          dsVdslPortCpePerfLos					INTEGER,
--        dsVdslPortCpePerfLPR					INTEGER,
          dsVdslPortCpePerfLol					INTEGER,
          dsVdslPortPerfCountClear				INTEGER,
          dsVdslPortStandard                    INTEGER,
          dsVdslPortLineProfile                 INTEGER,
          dsVdslPortMode                        INTEGER,
          dsVdslPortProfileSet                  INTEGER,
          dsVdslPortUpboEnable                  INTEGER,
          dsVdslPortChannel                     INTEGER,
          dsVdslPortTCMAdmin                    INTEGER
       }

   dsVdslModuleIndex OBJECT-TYPE
       SYNTAX      INTEGER
       MAX-ACCESS  read-only
       STATUS      current
       DESCRIPTION
               "A unique value, greater than zero, for each
               module.  It is recommended that values are assigned
               contiguously starting from 1.  The value for each
               interface sub-layer must remain constant at least from
               one re-initialization of the entity's network
               management system to the next re-initialization."
       ::= { dsVdslPortEntry 1 }

   dsVdslPortIndex OBJECT-TYPE
       SYNTAX      INTEGER
       MAX-ACCESS  read-only
       STATUS      current
       DESCRIPTION
               "A unique value, greater than zero, for each
               port.  It is recommended that values are assigned
               contiguously starting from 1.  The value for each
               interface sub-layer must remain constant at least from
               one re-initialization of the entity's network
               management system to the next re-initialization."
       ::= { dsVdslPortEntry 2 }

   dsVdslPortType OBJECT-TYPE
       SYNTAX      DisplayString (SIZE (0..64))
       MAX-ACCESS  read-only
       STATUS      current
       DESCRIPTION
               "The type of dsVdsl port. This string defines the type
                of port."
       ::= { dsVdslPortEntry 3 }

   dsVdslPortIfIndex OBJECT-TYPE
       SYNTAX      OBJECT IDENTIFIER
       MAX-ACCESS  read-only
       STATUS      current
       DESCRIPTION
               "matching ifIndex oid which is defined in interface mib."
       ::= { dsVdslPortEntry 4 }
       
   dsVdslPortUpProfile OBJECT-TYPE
       SYNTAX      INTEGER {
                 		notavailable(-1),
                        a-sym11(0),
                        asym11(1),
                        sym11(2),
                        a-asym11(3),
                        a-sym13(4),
                        sym16(5),
                        a-asym13(6),
                        tl13(7),
                        tl16(8),
                        tl16a(9),
                        asym24(11),
                        asym18(12),
                        asym25(13),
                        asym26(14),
                        asym50-998n(51),
                        asym50-998e(52),
                        sym25-997(53),
                        asym50-998a(54),
                        asym50-998i(55),
                        asym50-998t(56),
                        asym50-998s(57), 
                        asym50-998n-4b(58),
                        asym50-998i-4b(59),  
                        asym50-998a-4b(60), 
                        sym25-997a(61),
                        sym25-997i(62),
                        asym70-998n(63),
                        asym70-998i(64),          
                        asym70-998a(65),
                        asym100-998n(66), 
                        asym100-998i(67),
                        asym100-998a(68),
                        sym100-100-998n(69),
                        sym100-100-998i(70),
                        sym100-100-998a(71)
                   }
       MAX-ACCESS  read-write
       STATUS      current
       DESCRIPTION
               "dsVdsl Upstream profile ID.
                sym11 (2)     Symmetric 11/11
                asym11 (1)    Asymmetric 3/11
                a-sym11 (0)   ADSL friendly symmetric 11/11
                a-asym11 (3)  ADSL friendly asymmetric 3/11
                a-sym13 (4)   ADSL friendly symmetric 13/13
                a-asym13 (6)  ADSL friendly asymmetric 3/13
                sym16 (5)     Symmetric 16/16
                tl13 (7)      T-LAN friendly 13/13
                tl16 (8)      T-LAN friendly 16/16
                tl16a (9)     T-LAN friendly 13/16A (QAM20 ONLY)
                asym24 (11)   PLAN998 Asymmetric 8/24 (QAM20 ONLY)
                asym18 (12)   PLAN998 Asymmetric 8/18 (QAM20 ONLY)
                asym25 (13)   PLAN998 Asymmetric Enhanced 8/25(QAM20 ONLY)
                asym26 (14)   PLAN998 Asymmetric Enhanced 8/26(QAM20 ONLY)
                asym50-998n (51)  PLAN998 Asymmetric
                asym50-998e (52)  PLAN998E Asymmetric
                sym25-997 (53)    PLAN997 Asymmetric
                asym50-998a (54)  ADSL friendly PLAN 998 Asymetric
                asym50-998i (55)  ISDN friendly PLAN 998 Asymetric
                asym50-998t (56)  TLAN friendly PLAN 998 Asymetric
                asym50-998s (57)  ADSL soft mode Asymetric
                asym50-998n-4b(58) PLAN998 Asymmetric 13/50 4 band
                asym50-998i-4b(59) ISDN friendly PLAN 998 13/50 4 band
                asym50-998a-4b(60) ADSL friendly PLAN 998 13/50 4 band
                sym25-997a(61)  ADSL friendly PLAN 997 Symmetric 25/25     
                sym25-997i(62)  ISDN friendly PLAN 997 symmetric 25/25
                asym70-998n(63) PLAN998 Asymmetric 30/70 5 band
                asym70-998i(64) ISDN friendly PLAN 998 asymmetric 30/70 5 band        
                asym70-998a(65) ADSL friendly PLAN 998 asymmetric 30/70 5 band
                asym100-998n(66) PLAN 998n Asymmetric for 6Band DMT 100M 
                asym100-998i(67) PLAN 998i Asymmetric for 6Band DMT 100M
                asym100-998a(68) PLAN 998a Asymmetric for 6Band DMT 100M
                sym100-100-998n(69) PLAN 998n Symmetric for 6Band DMT 100/100M 
                sym100-100-998i(70) PLAN 998i Symmetric for 6Band DMT 100/100M  
                sym100-100-998a(71) PLAN 998a Symmetric for 6Band DMT 100/100M 
                "                         
       ::= { dsVdslPortEntry 5 }
                            
   dsVdslPortDownProfile OBJECT-TYPE
       SYNTAX      INTEGER {
            			notavailable(-1),
                        a-sym11(0),
                        asym11(1),
                        sym11(2),
                        a-asym11(3),
                        a-sym13(4),
                        sym16(5),
                        a-asym13(6),
                        tl13(7),
                        tl16(8),
                        tl16a(9),
                        asym24(11),
                        asym18(12),
                        asym25(13),
                        asym26(14),
                        asym50-998n(51),
                        asym50-998e(52),
                        sym25-997(53),
                        asym50-998a(54),
                        asym50-998i(55),
                        asym50-998t(56),
                        asym50-998s(57),
                        asym50-998n-4b(58),
                        asym50-998i-4b(59),  
                        asym50-998a-4b(60), 
                        sym25-997a(61),
                        sym25-997i(62), 
                        asym70-998n(63),
                        asym70-998i(64),          
                        asym70-998a(65),
                        asym100-998n(66), 
                        asym100-998i(67),
                        asym100-998a(68),
                        sym100-100-998n(69),
                        sym100-100-998i(70),
                        sym100-100-998a(71)         
                   }
       MAX-ACCESS  read-write
       STATUS      current
       DESCRIPTION
               "dsVdsl Downstream profile ID.
                sym11 (2)     Symmetric 11/11
                asym11 (1)    Asymmetric 3/11
                a-sym11 (0)   ADSL friendly symmetric 11/11
                a-asym11 (3)  ADSL friendly asymmetric 3/11
                a-sym13 (4)   ADSL friendly symmetric 13/13
                a-asym13 (6)  ADSL friendly asymmetric 3/13
                sym16 (5)     Symmetric 16/16
                tl13 (7)      T-LAN friendly 13/13
                tl16 (8)      T-LAN friendly 16/16
                tl16a (9)     T-LAN friendly 13/16A (QAM20 ONLY)
                asym24 (11)   PLAN998 Asymmetric 8/24 (QAM20 ONLY)
                asym18 (12)   PLAN998 Asymmetric 8/18 (QAM20 ONLY)
                asym25 (13)   PLAN998 Asymmetric Enhanced 8/25(QAM20 ONLY)
                asym26 (14)   PLAN998 Asymmetric Enhanced 8/26(QAM20 ONLY)
                asym50-998n (51)  PLAN998 Asymmetric
                asym50-998e (52)  PLAN998E Asymmetric
                sym25-997 (53)    PLAN997 Asymmetric
                asym50-998a (54)  ADSL friendly PLAN 998 Asymetric
                asym50-998i (55)  ISDN friendly PLAN 998 Asymetric
                asym50-998t (56)  TLAN friendly PLAN 998 Asymetric
                asym50-998s (57)  ADSL soft mode Asymetric
                asym50-998n-4b(58) PLAN998 Asymmetric 13/50 4 band
                asym50-998i-4b(59) ISDN friendly PLAN 998 13/50 4 band
                asym50-998a-4b(60) ADSL friendly PLAN 998 13/50 4 band
                sym25-997a(61)  ADSL friendly PLAN 997 Symmetric 25/25     
                sym25-997i(62)  ISDN friendly PLAN 997 symmetric 25/25
                asym70-998n(63) PLAN998 Asymmetric 30/70 5 band
                asym70-998i(64) ISDN friendly PLAN 998 asymmetric 30/70 5 band         
                asym70-998a(65) ADSL friendly PLAN 998 asymmetric 30/70 5 band
                asym100-998n(66) PLAN 998n Asymmetric for 6Band DMT 100M 
                asym100-998i(67) PLAN 998i Asymmetric for 6Band DMT 100M
                asym100-998a(68) PLAN 998a Asymmetric for 6Band DMT 100M
                sym100-100-998n(69) PLAN 998n Symmetric for 6Band DMT 100/100M 
                sym100-100-998i(70) PLAN 998i Symmetric for 6Band DMT 100/100M  
                sym100-100-998a(71) PLAN 998a Symmetric for 6Band DMT 100/100M 
                "
       ::= { dsVdslPortEntry 6 }                         
   
   dsVdslPortUpPhysicalSpeed OBJECT-TYPE
       SYNTAX      INTEGER
       MAX-ACCESS  read-only
       STATUS      current
       DESCRIPTION
               "Upstream attainable speed of port. bits/second."
       ::= { dsVdslPortEntry 7 }

   dsVdslPortDownPhysicalSpeed OBJECT-TYPE
       SYNTAX      INTEGER
       MAX-ACCESS  read-only
       STATUS      current
       DESCRIPTION
               "Downstream attainable speed of port. bits/second."
       ::= { dsVdslPortEntry 8 }
      
   dsVdslPortUpSpeed OBJECT-TYPE
       SYNTAX      INTEGER
       MAX-ACCESS  read-only
       STATUS      current
       DESCRIPTION
               "Upstream speed of port. bits/second."
       ::= { dsVdslPortEntry 9 }

   dsVdslPortDownSpeed OBJECT-TYPE
       SYNTAX      INTEGER
       MAX-ACCESS  read-only
       STATUS      current
       DESCRIPTION
               "Downstream speed of port. bits/second."
       ::= { dsVdslPortEntry 10 }                 
       
   dsVdslPortServiceError OBJECT-TYPE
       SYNTAX      INTEGER
       MAX-ACCESS  read-only
       STATUS      current
       DESCRIPTION
               "The raw accumulating dsVdsl service Error count."
       ::= { dsVdslPortEntry 11 }
       
   dsVdslPortErrorCRC OBJECT-TYPE
       SYNTAX      INTEGER
       MAX-ACCESS  read-only
       STATUS      current
       DESCRIPTION
               "The raw accumulating dsVdsl CRC Error count."
       ::= { dsVdslPortEntry 12 }
   
   dsVdslPortErrorSecond OBJECT-TYPE
       SYNTAX      INTEGER
       MAX-ACCESS  read-only
       STATUS      current
       DESCRIPTION
               "The raw accumulating dsVdsl Error Second."
       ::= { dsVdslPortEntry 13 }
                  
   dsVdslPortErrorLOF OBJECT-TYPE
       SYNTAX      INTEGER
       MAX-ACCESS  read-only
       STATUS      current
       DESCRIPTION
               "The raw accumulating dsVdsl loss of frame."
       ::= { dsVdslPortEntry 14 }
           
   dsVdslPortErrorLOS OBJECT-TYPE
       SYNTAX      INTEGER
       MAX-ACCESS  read-only
       STATUS      current
       DESCRIPTION
               "The raw accumulating dsVdsl loss of signal."
       ::= { dsVdslPortEntry 15 }
                               
   dsVdslPortErrorLPR OBJECT-TYPE
       SYNTAX      INTEGER
       MAX-ACCESS  read-only
       STATUS      current
       DESCRIPTION
               "The raw accumulating dsVdsl loss of power."
       ::= { dsVdslPortEntry 16 }
       
   dsVdslPortErrorLOL OBJECT-TYPE
       SYNTAX      INTEGER
       MAX-ACCESS  read-only
       STATUS      current
       DESCRIPTION
               "The raw accumulating dsVdsl loss of link."
       ::= { dsVdslPortEntry 17 }                          
       
   dsVdslPort15mElapsedTime OBJECT-TYPE
       SYNTAX      INTEGER  -- TimeTicks
       UNITS	   "1 minute"
       MAX-ACCESS  read-only
       STATUS      current
       DESCRIPTION
               "The current elapsed time from reinitializing point per 15 minutes."
       ::= { dsVdslPortEntry 18 }

   dsVdslPort1dayElapsedTime OBJECT-TYPE
       SYNTAX      INTEGER -- TimeTicks
       UNITS	   "1 minute"
       MAX-ACCESS  read-only
       STATUS      current
       DESCRIPTION
               "The current elapsed time from reinitializing point per 1 day."
       ::= { dsVdslPortEntry 19 }
                                                       
   dsVdslPortServiceErrorPrev15m OBJECT-TYPE
       SYNTAX      INTEGER
       MAX-ACCESS  read-only
       STATUS      current
       DESCRIPTION
               "The accumulating Serivce-Error count of previous 15 minute."
       ::= { dsVdslPortEntry 20 }
       
   dsVdslPortServiceErrorCurr15m OBJECT-TYPE
       SYNTAX      INTEGER
       MAX-ACCESS  read-only
       STATUS      current
       DESCRIPTION
               "The accumulating Service-Error count of current 15 minute."
       ::= { dsVdslPortEntry 21 }
       
   dsVdslPortErrorCRCPrev15m OBJECT-TYPE
       SYNTAX      INTEGER
       MAX-ACCESS  read-only
       STATUS      current
       DESCRIPTION
               "The accumulating CRC-error count of previous 15 minute."
       ::= { dsVdslPortEntry 22 }
       
   dsVdslPortErrorCRCCurr15m OBJECT-TYPE
       SYNTAX      INTEGER
       MAX-ACCESS  read-only
       STATUS      current
       DESCRIPTION
               "The accumulating CRC-error count of current 15 minute."
       ::= { dsVdslPortEntry 23 }
       
   dsVdslPortErrorSecondPrev15m OBJECT-TYPE
       SYNTAX      INTEGER
       MAX-ACCESS  read-only
       STATUS      current
       DESCRIPTION
               "The accumulating errored-second count of previous 15 minute."
       ::= { dsVdslPortEntry 24 }
       
   dsVdslPortErrorSecondCurr15m OBJECT-TYPE
       SYNTAX      INTEGER
       MAX-ACCESS  read-only
       STATUS      current
       DESCRIPTION
               "The accumulating errored-second count of current 15 minute."
       ::= { dsVdslPortEntry 25 }
           
   dsVdslPortErrorLOFPrev15m OBJECT-TYPE
       SYNTAX      INTEGER                    
       MAX-ACCESS  read-only
       STATUS      current
       DESCRIPTION
               "The accumulating loss-of-frame count of previous 15 minute."
       ::= { dsVdslPortEntry 26 }
                                                                            
                               
   dsVdslPortErrorLOFCurr15m OBJECT-TYPE
       SYNTAX      INTEGER                    
       MAX-ACCESS  read-only
       STATUS      current
       DESCRIPTION
               "The accumulating loss-of-frame count of current 15 minute."
       ::= { dsVdslPortEntry 27 }
             
   dsVdslPortErrorLOSPrev15m OBJECT-TYPE
       SYNTAX      INTEGER                    
       MAX-ACCESS  read-only
       STATUS      current
       DESCRIPTION
               "The accumulating loss-of-signal count of previous 15 minute."
       ::= { dsVdslPortEntry 28 }
                                                                            
                               
   dsVdslPortErrorLOSCurr15m OBJECT-TYPE
       SYNTAX      INTEGER                    
       MAX-ACCESS  read-only
       STATUS      current
       DESCRIPTION
               "The accumulating loss-of-signal count of current 15 minute."
       ::= { dsVdslPortEntry 29 }               
                                              
   dsVdslPortErrorLPRPrev15m OBJECT-TYPE
       SYNTAX      INTEGER                    
       MAX-ACCESS  read-only
       STATUS      current
       DESCRIPTION
               "The accumulating loss-of-power count of previous 15 minute."
       ::= { dsVdslPortEntry 30 }
                                                                            
                               
   dsVdslPortErrorLPRCurr15m OBJECT-TYPE
       SYNTAX      INTEGER                    
       MAX-ACCESS  read-only
       STATUS      current
       DESCRIPTION
               "The accumulating loss-of-power count of current 15 minute."
       ::= { dsVdslPortEntry 31 }               
        
   dsVdslPortErrorLOLPrev15m OBJECT-TYPE
       SYNTAX      INTEGER                    
       MAX-ACCESS  read-only
       STATUS      current
       DESCRIPTION
               "The accumulating loss-of-link count of previous 15 minute."
       ::= { dsVdslPortEntry 32 }
                               
   dsVdslPortErrorLOLCurr15m OBJECT-TYPE
       SYNTAX      INTEGER                    
       MAX-ACCESS  read-only
       STATUS      current
       DESCRIPTION
               "The accumulating loss-of-link count of current 15 minute."
       ::= { dsVdslPortEntry 33 }                  
           
   dsVdslPortServiceErrorPrev1day OBJECT-TYPE
       SYNTAX      INTEGER
       MAX-ACCESS  read-only
       STATUS      current
       DESCRIPTION
               "The accumulating Serivce-Error count of previous 1 day."
       ::= { dsVdslPortEntry 34 }
       
   dsVdslPortServiceErrorCurr1day OBJECT-TYPE
       SYNTAX      INTEGER
       MAX-ACCESS  read-only
       STATUS      current
       DESCRIPTION
               "The accumulating Service-Error count of current 1 day."
       ::= { dsVdslPortEntry 35 }
       
   dsVdslPortErrorCRCPrev1day OBJECT-TYPE
       SYNTAX      INTEGER
       MAX-ACCESS  read-only
       STATUS      current
       DESCRIPTION
               "The accumulating CRC-error count of previous 1 day."
       ::= { dsVdslPortEntry 36 }
       
   dsVdslPortErrorCRCCurr1day OBJECT-TYPE
       SYNTAX      INTEGER
       MAX-ACCESS  read-only
       STATUS      current
       DESCRIPTION
               "The accumulating CRC-error count of current 1 day."
       ::= { dsVdslPortEntry 37 }
       
   dsVdslPortErrorSecondPrev1day OBJECT-TYPE
       SYNTAX      INTEGER
       MAX-ACCESS  read-only
       STATUS      current
       DESCRIPTION
               "The accumulating errored-second count of previous 1 day."
       ::= { dsVdslPortEntry 38 }
       
   dsVdslPortErrorSecondCurr1day OBJECT-TYPE
       SYNTAX      INTEGER
       MAX-ACCESS  read-only
       STATUS      current
       DESCRIPTION
               "The accumulating errored-second count of current 1 day."
       ::= { dsVdslPortEntry 39 }
           
   dsVdslPortErrorLOFPrev1day OBJECT-TYPE
       SYNTAX      INTEGER                    
       MAX-ACCESS  read-only
       STATUS      current
       DESCRIPTION
               "The accumulating loss-of-frame count of previous 1 day."
       ::= { dsVdslPortEntry 40 }
                                                                            
                               
   dsVdslPortErrorLOFCurr1day OBJECT-TYPE
       SYNTAX      INTEGER                    
       MAX-ACCESS  read-only
       STATUS      current
       DESCRIPTION
               "The accumulating loss-of-frame count of current 1 day."
       ::= { dsVdslPortEntry 41 }
             
   dsVdslPortErrorLOSPrev1day OBJECT-TYPE
       SYNTAX      INTEGER                    
       MAX-ACCESS  read-only
       STATUS      current
       DESCRIPTION
               "The accumulating loss-of-signal count of previous 1 day."
       ::= { dsVdslPortEntry 42 }
                               
   dsVdslPortErrorLOSCurr1day OBJECT-TYPE
       SYNTAX      INTEGER                    
       MAX-ACCESS  read-only
       STATUS      current
       DESCRIPTION
               "The accumulating loss-of-signal count of current 1 day."
       ::= { dsVdslPortEntry 43 }               
                                              
   dsVdslPortErrorLPRPrev1day OBJECT-TYPE
       SYNTAX      INTEGER                    
       MAX-ACCESS  read-only
       STATUS      current
       DESCRIPTION
               "The accumulating loss-of-power count of previous 1 day."
       ::= { dsVdslPortEntry 44 }
                                                                            
                               
   dsVdslPortErrorLPRCurr1day OBJECT-TYPE
       SYNTAX      INTEGER                    
       MAX-ACCESS  read-only
       STATUS      current
       DESCRIPTION
               "The accumulating loss-of-power count of current 1 day."
       ::= { dsVdslPortEntry 45 }               
        
   dsVdslPortErrorLOLPrev1day OBJECT-TYPE
       SYNTAX      INTEGER                    
       MAX-ACCESS  read-only
       STATUS      current
       DESCRIPTION
               "The accumulating loss-of-link count of previous 1 day."
       ::= { dsVdslPortEntry 46 }
                               
   dsVdslPortErrorLOLCurr1day OBJECT-TYPE
       SYNTAX      INTEGER                    
       MAX-ACCESS  read-only
       STATUS      current
       DESCRIPTION
               "The accumulating loss-of-link count of current 1 day"
       ::= { dsVdslPortEntry 47 }                  
   
   dsVdslPortUpSNR OBJECT-TYPE
       SYNTAX      INTEGER 
       MAX-ACCESS  read-only
       STATUS      current
       DESCRIPTION
               "dsVdsl upstream SNR * 1000."
       ::= { dsVdslPortEntry 48 }

   dsVdslPortDownSNR OBJECT-TYPE
       SYNTAX      INTEGER 
       MAX-ACCESS  read-only
       STATUS      current
       DESCRIPTION
               "dsVdsl downstream SNR * 1000."
       ::= { dsVdslPortEntry 49 }    
   dsVdslPortUpSNRMargin OBJECT-TYPE
       SYNTAX      INTEGER        
       UNITS       "0.1db"
       MAX-ACCESS  read-only
       STATUS      current
       DESCRIPTION
               "dsVdsl upstream SNR Margin(CO SNR Margin)."
       ::= { dsVdslPortEntry 50 }    
                                   
   dsVdslPortDownSNRMargin OBJECT-TYPE
       SYNTAX      INTEGER 
       UNITS       "0.1db"       
       MAX-ACCESS  read-only
       STATUS      current
       DESCRIPTION
               "dsVdsl downstream SNR Margin(CPE SNR Margin)."
       ::= { dsVdslPortEntry 51 }    
                              
   dsVdslPortUpAttenuation OBJECT-TYPE
       SYNTAX      INTEGER   
       UNITS	   "0.1db"
       MAX-ACCESS  read-only
       STATUS      current
       DESCRIPTION
               "dsVdsl upstream port attenuation(CO Attenuation)."
       ::= { dsVdslPortEntry 52 }
                               
   dsVdslPortDownAttenuation OBJECT-TYPE
       SYNTAX      INTEGER 
       UNITS       "0.1db"
       MAX-ACCESS  read-only
       STATUS      current
       DESCRIPTION
               "dsVdsl downstream port attenuation(CPE Attenuation)."
       ::= { dsVdslPortEntry 53 }
       
   dsVdslPortOutPower OBJECT-TYPE
       SYNTAX      INTEGER
       UNITS       "0.1db"
       MAX-ACCESS  read-only
       STATUS      current
       DESCRIPTION
               "dsVdsl port Output Power."
       ::= { dsVdslPortEntry 54 }                     
                         
   dsVdslPortWanInPkt OBJECT-TYPE
       SYNTAX      INTEGER 
       MAX-ACCESS  read-only
       STATUS      current
       DESCRIPTION
               "dsVdsl WAN in-packet count."
       ::= { dsVdslPortEntry 55 }

   dsVdslPortWanInErr OBJECT-TYPE
       SYNTAX      INTEGER 
       MAX-ACCESS  read-only
       STATUS      current
       DESCRIPTION
               "dsVdsl WAN error packet count."
       ::= { dsVdslPortEntry 56 }

   dsVdslPortWanOutPkt OBJECT-TYPE
       SYNTAX      INTEGER 
       MAX-ACCESS  read-only
       STATUS      current
       DESCRIPTION
               "dsVdsl WAN out-packet count."
       ::= { dsVdslPortEntry 57 }

   dsVdslPortWanReset OBJECT-TYPE
       SYNTAX      INTEGER  { reset(1) }
       MAX-ACCESS  read-write
       STATUS      current
       DESCRIPTION
               "Reaquire dsVdsl line SYNC."
       ::= { dsVdslPortEntry 58 }

   dsVdslPortWanLoopbackAction OBJECT-TYPE
       SYNTAX      INTEGER  { loopbacktest(1) }
       MAX-ACCESS  read-write
       STATUS      current
       DESCRIPTION
               "Perform remote loopback ping test."
       ::= { dsVdslPortEntry 59 }

   dsVdslPortWanLoopbackStatus OBJECT-TYPE
       SYNTAX      INTEGER  { other(0), failed(1), succeeded(2) }
       MAX-ACCESS  read-only
       STATUS      current
       DESCRIPTION
               "Latest remote loopback test result."
       ::= { dsVdslPortEntry 60 }


   dsVdslPortWanAdminStatus OBJECT-TYPE
       SYNTAX      INTEGER { other(-1), down(0), up(1) }
       MAX-ACCESS  read-write
       STATUS      current
       DESCRIPTION
               "Administrative status of WAN port"
       ::= { dsVdslPortEntry 61 }

   dsVdslPortWanOperStatus OBJECT-TYPE
       SYNTAX      INTEGER { other(-1), down(0), up(1) }
       MAX-ACCESS  read-only
       STATUS      current
       DESCRIPTION
               "Operational status of WAN port"
       ::= { dsVdslPortEntry 62 }
          
   -- VOC information
   dsVdslPortVOCLinkStatus OBJECT-TYPE
       SYNTAX	   INTEGER { up(1), down(2) }
       MAX-ACCESS  read-only
       STATUS      current
       DESCRIPTION 
       	       "PC Ethernet link status through VOC channel."
       ::= { dsVdslPortEntry 63 }
                            
   dsVdslPortVOCLinkDuplex OBJECT-TYPE
       SYNTAX	   INTEGER  { full(1), half(2), notavailable(3) }
       MAX-ACCESS  read-only
       STATUS      current
       DESCRIPTION 
       	       "PC link duplex through VOC channel."
       ::= { dsVdslPortEntry 64 }
   
   dsVdslPortVOCLinkSpeed OBJECT-TYPE
       SYNTAX	   INTEGER
       MAX-ACCESS  read-only
       STATUS      current
       DESCRIPTION 
       	       "PC link speed through VOC channel. bits/second(bps)."
       ::= { dsVdslPortEntry 65 }                 
       
  --
  -- June 2003 dhlee 
  --
  dsVdslPortOptionband OBJECT-TYPE
       SYNTAX      INTEGER {
            			notavailable(-1),
                        annex-B-6-64(1),
                        annex-A-6-32(2),
                        annex-B-32-64(3),
                        exclude(4)                        
                   }
       MAX-ACCESS  read-only
       STATUS      current
       DESCRIPTION
               "dsVdsl Optional band ID.
                Annex B 6-64 (1)
                Annex A 6-32 (2)
                Annex B 32-64 (3)
                Exclude Option Band (4)
               "
       ::= { dsVdslPortEntry 66 }                  
  
  dsVdslPortHamband OBJECT-TYPE
       SYNTAX      Counter64 
       MAX-ACCESS  read-only
       STATUS      current
       DESCRIPTION
               "dsVdsl Amature Radio(HAM) band ID.
               The value of Ham band is combination of the following value.
               If you want to set band1 and band10, you should set value 257(band1 + band10)
               to the Ham band.   
               band1   [  1.800  -  1.810  ] MHz : RFI Notch                (1)
               band2   [  1.800  -  1.825  ] MHz : KOREA HAM-BAND           (2)
               band3   [  1.810  -  1.825  ] MHz : ANNEX F                  (4)
               band4   [  1.810  -  2.000  ] MHz : ETSI, T1E1               (8)
               band5   [  1.9075 -  1.9125 ] MHz : ANNEX F                  (16)
               band6   [  2.173  -  2.191  ] MHz : DT GMDSS                 (2097152)					0x0000 0020 0000
               band7   [  3.500  -  3.550  ] MHz : KOREA HAM-BAND           (32)
               band8   [  3.500  -  3.575  ] MHz : ANNEX F                  (64) 
               band9   [  3.500  -  3.800  ] MHz : ETSI                     (128)
               band10  [  3.500  -  4.000  ] MHz : T1E1                     (256)
               band11  [  3.747  -  3.754  ] MHz : ANNEX F                  (512)
               band12  [  3.790  -  3.800  ] MHz : KOREA HAM-BAND           (1024)             
               band13  [  3.791  -  3.805  ] MHz : ANNEX F                  (2048)
               band14  [  4.200  -  4.215  ] MHz : DT GMDSS                 (4194304)					0x0000 0040 0000
               band15  [  5.900  -  6.200  ] MHz : DT DRM radio (Broadcasting)           (8388608)		0x0000 0080 0000
               band16  [  6.300  -  6.320  ] MHz : DT GMDSS                              (16777216)		0x0000 0100 0000
               band17  [  7.000  -  7.100  ] MHz : KOREA HAM-BAND, ANNEX F, ETSI         (4096)
               band18  [  7.000  -  7.300  ] MHz : T1E1                                  (8192)
               band19  [  7.100  -  7.350  ] MHz : DT DRM radio (Broadcasting)           (33554432)		0x0000 0200 0000
               band20  [  8.405  -  8.420  ] MHz : DT GMDSS                              (67108864)		0x0000 0400 0000
               band21  [  9.400  -  9.900  ] MHz : DT DRM radio (Broadcasting)           (134217728)	0x0000 0800 0000   
               band22  [ 10.100  - 10.150  ] MHz : KOREA HAM-BAND, ANNEX F, ETSI, T1E1   (16384)
               band23  [ 11.600  - 12.100  ] MHz : DT DRM radio (Broadcasting)           (268435456)	0x0000 1000 0000
               band24  [ 12.570  - 12.585  ] MHz : DT GMDSS                              (536870912)	0x0000 2000 0000
               band25  [ 13.570  - 13.870  ] MHz : DT DRM radio (Broadcasting)           (1073741824)	0x0000 4000 0000
               band26  [ 14.000  - 14.350  ] MHz : ANNEX F, ETSI, T1E1                   (32768)
               band27  [ 15.100  - 15.800  ] MHz : DT DRM radio (Broadcasting)           (2147483648)	0x0000 8000 0000
               band28  [ 16.795  - 16.810  ] MHz : DT GMDSS                              (4294967296)	0x0001 0000 0000
               band29  [ 17.480  - 17.900  ] MHz : DT DRM radio (Broadcasting)           (8589934592)	0x0002 0000 0000
               band30  [ 18.068  - 18.168  ] MHz : ANNEX F, ETSI, T1E1                   (65536)
               band31  [ 21.000  - 21.450  ] MHz : ANNEX F, ETSI, T1E1                   (131072)		0x0000 0002 0000
               band32  [ 24.890  - 24.990  ] MHz : ANNEX F, ETST, T1E1                   (262144)		0x0000 0004 0000
               band33  [ 28.000  - 29.100  ] MHz : ETSI                                  (524288)		0x0000 0008 0000
               band34  [ 28.000  - 29.700  ] MHz : ANNEX F, ETSI, T1E1                   (1048576)		0x0000 0010 0000
               "
    
       ::= { dsVdslPortEntry 67 }                  
       
   dsVdslPortUpInterleave OBJECT-TYPE
       SYNTAX      INTEGER (1..100)
       UNITS	"1 ms"
       MAX-ACCESS  read-write
       STATUS      current
       DESCRIPTION
               " dsVdslPort Upstream Interleave delay."
       ::= { dsVdslPortEntry 68 }                  
       
   dsVdslPortDownInterleave OBJECT-TYPE
       SYNTAX      INTEGER (1..100)
       UNITS	"1 ms"
       MAX-ACCESS  read-write
       STATUS      current
       DESCRIPTION
               " dsVdslPort Downstream Interleave delay."
       ::= { dsVdslPortEntry 69 }                  

   dsVdslPortTargetUpSNRMargin OBJECT-TYPE
       SYNTAX      INTEGER (0..31)       
       UNITS       "1db"
       MAX-ACCESS  read-write
       STATUS      current
       DESCRIPTION
               "dsVdsl Target upstream SNR Margin(CO SNR Margin)."
       ::= { dsVdslPortEntry 70 }    
                                   
   dsVdslPortTargetDownSNRMargin OBJECT-TYPE
       SYNTAX      INTEGER (0..31)
       UNITS       "1db"       
       MAX-ACCESS  read-write
       STATUS      current
       DESCRIPTION
               "dsVdsl Target downstream SNR Margin(CPE SNR Margin)."
       ::= { dsVdslPortEntry 71 }    
                         
   dsVdslPortPSDMaskLevel OBJECT-TYPE
       SYNTAX      INTEGER {        
                        notavailable(-1),
            			old-gains(0),
                        aNSI-M1(1),
                        aNSI-M2(2), 
                        eTSI-M1(3),
                        eTSI-M2(4),
                        aNNEX-F-8-5(5), 
                        aNSI-M1-EX(6),
                        aNSI-M2-EX(7),
                        eTSI-M1-EX(8),
                        eTSI-M2-EX(9),
                        aNNEX-F-11-5(10),
                        pSD-K(11)                      
                   }
       MAX-ACCESS  read-only
       STATUS      current
       DESCRIPTION
               "dsVdsl PSD Mask Level.
                notavailable(-1)
                old gains(0)
                ANSI M1(1)
                ANSI M2(2) 
                ETSI M1(3)
                ETSI M2(4)
                ANNEX F 8.5(5) 
                ANSI M1 EX(6)
                ANSI M2 EX(7)
                ETSI M1 EX(8)
                ETSI M2 EX(9)
                ANNEX F 11.5(10)                                      
                PSD-K(11)
               "
       ::= { dsVdslPortEntry 72 }                  
       
   dsVdslPortPBOLength OBJECT-TYPE
       SYNTAX      INTEGER {
            			pbo100m(1),
                        pbo200m(2),
                        pbo300m(3),
                        pbo400m(4),
                        pbo500m(5),
                        pbo600m(6),
                        pbo700m(7),
                        pbo800m(8),
                        pbo900m(9),
                        pbo1000m(10)                       
                   }
       MAX-ACCESS  read-only
       STATUS      current
       DESCRIPTION
               "dsVdsl Power Back-Off Length.
                100m(1)
                200m(2)
                300m(3)
                400m(4)
                500m(5)
                600m(6)
                700m(7)
                800m(8)
                900m(9)
                1000m(10)                       
               "
   ::= { dsVdslPortEntry 73 }    
   
   dsVdslPort15mElapsedTimeSeconds OBJECT-TYPE
       SYNTAX      INTEGER 
       UNITS	   "1 second"
       MAX-ACCESS  read-only
       STATUS      current
       DESCRIPTION
               "The current elapsed time from reinitializing point per 15 minutes in seconds."
       ::= { dsVdslPortEntry 74 }

   dsVdslPort1dayElapsedTimeSeconds OBJECT-TYPE
       SYNTAX      INTEGER
       UNITS	   "1 second"
       MAX-ACCESS  read-only
       STATUS      current
       DESCRIPTION
               "The current elapsed time from reinitializing point per 1 day in seconds."
       ::= { dsVdslPortEntry 75 }              
   
   dsVdslPortUpServiceProfile OBJECT-TYPE
       SYNTAX      INTEGER 
       MAX-ACCESS  read-only
       STATUS      current
       DESCRIPTION
               "dsVdslPort upstream service profile."
   ::= { dsVdslPortEntry 76 }                  
   
   dsVdslPortDownServiceProfile OBJECT-TYPE
       SYNTAX      INTEGER 
       MAX-ACCESS  read-only
       STATUS      current
       DESCRIPTION
               "dsVdslPort downstream service profile."
   ::= { dsVdslPortEntry 77 }                  
   
   dsVdslPortModemReset OBJECT-TYPE
       SYNTAX      INTEGER {    
                        reset(1)
                   }
       MAX-ACCESS  read-write
       STATUS      current
       DESCRIPTION
               "Reset the Modem."
   ::= { dsVdslPortEntry 78 }  
                             
   dsVdslPortCPEVersion OBJECT-TYPE
       SYNTAX      DisplayString
       MAX-ACCESS  read-only
       STATUS      current
       DESCRIPTION
               "dsVdslPort CPE NOS informations.
               The format of value is 'OS1/OS2/ActiveOS'."
   ::= { dsVdslPortEntry 79 }         
   
    dsVdslPortCPEDownload OBJECT-TYPE
       SYNTAX      INTEGER {    
                        no(0),
                        yes(1),
                        done(2),
                        fail(3)
                   }
       MAX-ACCESS  read-write
       STATUS      current
       DESCRIPTION
               "Download the CPE NOS.
                no(0)   : No CPE NOS download.
                yes(1)  : Now downloading.
                done(2) : Download completed.
                fail(3) : Download fail."
   ::= { dsVdslPortEntry 80 }     
                                               
   dsVdslPortLineActiveTimePrev1Day OBJECT-TYPE
       SYNTAX      INTEGER
       MAX-ACCESS  read-only
       STATUS      current
       DESCRIPTION
               "The accumulating Line Active time of previous 1 day."
       ::= { dsVdslPortEntry 81 }
                                
    dsVdslPortLineActiveTimeCurr1Day OBJECT-TYPE
       SYNTAX      INTEGER
       MAX-ACCESS  read-only
       STATUS      current
       DESCRIPTION
               "The accumulating Line Active time of current 1 day."
       ::= { dsVdslPortEntry 82 }

	dsVdslPortLineConfProfileClear OBJECT-TYPE
		SYNTAX		INTEGER  { clear(1) }
		MAX-ACCESS	read-write
		STATUS		current
		DESCRIPTION
				"To remove the line configure profile assigned to 
				a physical port for a particular feature. This value
                should have 1 that means clear "
		::= { dsVdslPortEntry 83 }

	dsVdslPortAlarmConfProfileClear OBJECT-TYPE
		SYNTAX		INTEGER  { clear(1) }
		MAX-ACCESS	read-write
		STATUS		current
		DESCRIPTION
				"To remove the alarm configure profile assigned to 
				a physical port for a particular feature. This value
                should have 1 that means clear "
		::= { dsVdslPortEntry 84 }

	dsVdslPortEwl	OBJECT-TYPE
		SYNTAX		INTEGER 
		MAX-ACCESS	read-only
		STATUS      current
		DESCRIPTION
				"Vdsl Port wire length."
		::= { dsVdslPortEntry 86 }
		
    dsVdslPortGhsNearEndEwl	OBJECT-TYPE
    	SYNTAX		INTEGER
    	MAX-ACCESS	read-only
    	STATUS		current
    	DESCRIPTION	
    			"Vdsl Port Near End wire length."
    	::= { dsVdslPortEntry 87 }
    	
    dsVdslPortGhsFarEndEwl	OBJECT-TYPE
    	SYNTAX		INTEGER
    	MAX-ACCESS	read-only
    	STATUS		current
    	DESCRIPTION
    			"Vdsl Port Far End wire length."
    	::= { dsVdslPortEntry 88 }		
		
	dsVdslPortLineActiveTimeClear OBJECT-TYPE
       SYNTAX      INTEGER  { clear(1)}
       MAX-ACCESS  read-write
       STATUS      current
       DESCRIPTION
               "To initialize Line Active time."
       ::= { dsVdslPortEntry 89 }
    
   
	dsVdslPortServiceErrorClear OBJECT-TYPE
       SYNTAX      INTEGER  { clear(1)}
       MAX-ACCESS  read-write
       STATUS      current
       DESCRIPTION
               "To initialize  ."
       ::= { dsVdslPortEntry 90 }
	
	dsVdslPortErrorCRCClear	OBJECT-TYPE
       SYNTAX      INTEGER  { clear(1)}
       MAX-ACCESS  read-write
       STATUS      current
       DESCRIPTION
               "To initialize  ."
       ::= { dsVdslPortEntry 91 }
		  
	dsVdslPortErrorSecondClear	OBJECT-TYPE
       SYNTAX      INTEGER  { clear(1)}
       MAX-ACCESS  read-write
       STATUS      current
       DESCRIPTION
               "To initialize Count of ErrorSecond ."
       ::= { dsVdslPortEntry 92 }
		  
	dsVdslPortErrorLOFClear	OBJECT-TYPE
       SYNTAX      INTEGER  { clear(1)}
       MAX-ACCESS  read-write
       STATUS      current
       DESCRIPTION
               "To initialize Count of the number of LOF ."
       ::= { dsVdslPortEntry 93 }
		   
	dsVdslPortErrorLOSClear	OBJECT-TYPE
       SYNTAX      INTEGER  { clear(1)}
       MAX-ACCESS  read-write
       STATUS      current
       DESCRIPTION
               "To initialize Count of the number of LOS ."
       ::= { dsVdslPortEntry 94 }
		  
	dsVdslPortErrorLPRClear	OBJECT-TYPE
       SYNTAX      INTEGER  { clear(1)}
       MAX-ACCESS  read-write
       STATUS      current
       DESCRIPTION
               "To initialize Count of the number of LPR ."
       ::= { dsVdslPortEntry 95 }
		 
	dsVdslPortErrorLOLClear	OBJECT-TYPE
       SYNTAX      INTEGER  { clear(1)}
       MAX-ACCESS  read-write
       STATUS      current
       DESCRIPTION
               "To initialize Count of the number of LOL ."
       ::= { dsVdslPortEntry 96 }
		 

--	dsVdslPortErrorUncorrectCRCClear   OBJECT-TYPE
--       SYNTAX      INTEGER  { clear(1)}
--     	 MAX-ACCESS  read-write
--       STATUS      current
--       DESCRIPTION
--               "To initialize Count of the number of  ."
--       ::= { dsVdslPortEntry 97 }

--	dsVdslPortErrorCorrectCRCClear    OBJECT-TYPE
--       SYNTAX      INTEGER  { clear(1)}
--       MAX-ACCESS  read-write
--       STATUS      current
--       DESCRIPTION
--               "To initialize Count of the number of  ."
--       ::= { dsVdslPortEntry 98 }
  
  		   
--	dsVdslPortErrorServiceErrorSecondClear	OBJECT-TYPE
--       SYNTAX      INTEGER  { clear(1)}
--       MAX-ACCESS  read-write
--       STATUS      current
--       DESCRIPTION
--               "To initialize  ."
--       ::= { dsVdslPortEntry 99 }

--	dsVdslPortErrorCRCSecondClear     OBJECT-TYPE
--       SYNTAX      INTEGER  { clear(1)}
--       MAX-ACCESS  read-write
--       STATUS      current
--       DESCRIPTION
--               "To initialize  ."
--       ::= { dsVdslPortEntry 100 }
  
--	dsVdslPortErrorLOFSecondClear    OBJECT-TYPE
--       SYNTAX      INTEGER  { clear(1)}
--       MAX-ACCESS  read-write
--       STATUS      current
--       DESCRIPTION
--               "To initialize  ."
--       ::= { dsVdslPortEntry 101 }
   
--	dsVdslPortErrorLOSSecondClear    OBJECT-TYPE
--       SYNTAX      INTEGER  { clear(1)}
--       MAX-ACCESS  read-write
--       STATUS      current
--       DESCRIPTION
--               "To initialize ."
--       ::= { dsVdslPortEntry 102 }

--	dsVdslPortErrorLOLSecondClear    OBJECT-TYPE
--       SYNTAX      INTEGER  { clear(1)}
--       MAX-ACCESS  read-write
--       STATUS      current
--       DESCRIPTION
--               "To initialize  ."
--       ::= { dsVdslPortEntry 103 }

--	dsVdslPortErrorSESSecondClear    OBJECT-TYPE
--       SYNTAX      INTEGER  { clear(1)}
--       MAX-ACCESS  read-write
--       STATUS      current
--       DESCRIPTION
--              "To initialize  ."
--       ::= { dsVdslPortEntry 104 }

--	dsVdslPortErrorUASSecondClear   OBJECT-TYPE
--       SYNTAX      INTEGER  { clear(1)}
--       MAX-ACCESS  read-write
--       STATUS      current
--       DESCRIPTION
--               "To initialize  ."
--       ::= { dsVdslPortEntry 105 }
		
    dsVdslPortErrorCountClear	OBJECT-TYPE
       SYNTAX      INTEGER  { clear(1)}
       MAX-ACCESS  read-write
       STATUS      current
       DESCRIPTION
               "To initialize all error-count-value."
       ::= { dsVdslPortEntry 106 }        

    dsVdslPortCpeErrorCRC		OBJECT-TYPE
    	SYNTAX		INTEGER 
    	MAX-ACCESS	read-only
    	STATUS		current
    	DESCRIPTION
    			"."
    	::= { dsVdslPortEntry 108 }
    		 
--  dsVdslPortCpeErrorSecond	OBJECT-TYPE
--		SYNTAX		INTEGER
--		MAX-ACCESS	read-only
--		STATUS		current
--    	DESCRIPTION
--    			"."
--    	::= { dsVdslPortEntry 109 }

    dsVdslPortCpePerfLOF		OBJECT-TYPE	
	    SYNTAX		INTEGER
		MAX-ACCESS	read-only
		STATUS		current
    	DESCRIPTION
    			"."
    	::= { dsVdslPortEntry 110 }
 			           
    dsVdslPortCpePerfLos		OBJECT-TYPE
	    SYNTAX		INTEGER
		MAX-ACCESS	read-only
		STATUS		current
    	DESCRIPTION
    			"."
    	::= { dsVdslPortEntry 111 }

--  dsVdslPortCpePerfLPR		OBJECT-TYPE
--	    SYNTAX		INTEGER,
--		MAX-ACCESS	read-only
--		STATUS		current
--    	DESCRIPTION
--    			"."
--    	::= { dsVdslPortEntry 112 }

    dsVdslPortCpePerfLol		OBJECT-TYPE
	    SYNTAX		INTEGER
		MAX-ACCESS	read-only
		STATUS		current
    	DESCRIPTION
    			"."
    	::= { dsVdslPortEntry 113 }

    dsVdslPortPerfCountClear	OBJECT-TYPE
	    SYNTAX		INTEGER { clear(1) }
		MAX-ACCESS	read-write
		STATUS		current
    	DESCRIPTION
    			"."
    	::= { dsVdslPortEntry 114 }
    
    dsVdslPortStandard	OBJECT-TYPE
	    SYNTAX		INTEGER { VDSL(1), VDSL2(2) }
		MAX-ACCESS	read-write
		STATUS		current
    	DESCRIPTION
    			"VDSL Standard."
    	::= { dsVdslPortEntry 121 }

    dsVdslPortLineProfile OBJECT-TYPE
        SYNTAX      INTEGER {        
                        sym25(1),
                        asym50-3b(2), 
                        asym50-4b(3), 
                        asym70(4), 
                        asym100(5), 
                        sym100(6),
                        sym50(7),
                        v8a(8),
                        v8b(9),
                        v8c(10),
                        v8d(11),
                        v12a(12),
                        v12b(13),
                        v17a(14),
                        v30a(15),
                        v12a997(16),
                        v12b997(17)                                              
                   }
        MAX-ACCESS  read-write
        STATUS      current
        DESCRIPTION
               "        sym25(1),
                        asym50-3b(2), 
                        asym50-4b(3), 
                        asym70(4), 
                        asym100(5), 
                        sym100(6),
                        8a(8),
                        8b(9),
                        8c(10),
                        8d(11),
                        12a(12),
                        12b(13),
                        17a(14),
                        30a(15),
                        12a997(16),
                        12b997(17)  
                "
       ::= { dsVdslPortEntry 122 } 
       
    dsVdslPortMode OBJECT-TYPE
        SYNTAX      INTEGER {        
                        normal(1),
                        isdn(2), 
                        adsl(3), 
                        adsl2(4), 
                        t-lan(5),
                        adsl-s(6)                                              
                   }
        MAX-ACCESS  read-write
        STATUS      current
        DESCRIPTION
               "                
                        normal(1),
                        isdn(2), 
                        adsl(3), 
                        adsl2(4), 
                        t-lan(5),
                        adsl-safe(6)                          
                "
        ::= { dsVdslPortEntry 123 } 
 
    dsVdslPortProfileSet	OBJECT-TYPE
	    SYNTAX		INTEGER { write(1) }
		MAX-ACCESS	read-write
		STATUS		current
    	DESCRIPTION
    			"."
    	::= { dsVdslPortEntry 124 }

    dsVdslPortUpboEnable	OBJECT-TYPE
	    SYNTAX		INTEGER { enable(1), disable(2) }
		MAX-ACCESS	read-write
		STATUS		current
    	DESCRIPTION
    			"."
    	::= { dsVdslPortEntry 126 }

    dsVdslPortChannel	OBJECT-TYPE
	    SYNTAX		INTEGER { fast(0), slow(1) }
		MAX-ACCESS	read-write
		STATUS		current
    	DESCRIPTION
    			"."
    	::= { dsVdslPortEntry 127 }

    dsVdslPortTCMAdmin	OBJECT-TYPE
	    SYNTAX		INTEGER { enable(0), disable(1) }
		MAX-ACCESS	read-write
		STATUS		current
    	DESCRIPTION
    			"."
    	::= { dsVdslPortEntry 128 }    
          
--                                           
--  June 2003 dhlee add dsVdslSlotTable. 
--  For V5972 DMT 50 , V5916-DMT50, V5924-DMT50 etc.
--       
       
   dsVdslSlotTable OBJECT-TYPE
       SYNTAX      SEQUENCE OF DsVdslSlotEntry
       MAX-ACCESS  not-accessible
       STATUS      mandatory
       DESCRIPTION
               "A list of dsVdslSlotEntry entries."
       ::= { dsSwitchModules 9 }

   dsVdslSlotEntry OBJECT-TYPE
       SYNTAX      DsVdslSlotEntry
       MAX-ACCESS  not-accessible
       STATUS      current
       DESCRIPTION
               "An entry containing management information applicable
               to a particular dsVdsl Slot."

       INDEX   { dsVdslSlotModuleIndex , dsVdslSlotIndex }
       ::= { dsVdslSlotTable 1 }
                              
   DsVdslSlotEntry ::=
       SEQUENCE {
           dsVdslSlotModuleIndex                 INTEGER,
           dsVdslSlotIndex                       INTEGER,
           dsVdslSlotType						   DisplayString,
           dsVdslSlotInstallStatus               INTEGER,         
           dsVdslSlotProfile					   INTEGER,
           dsVdslSlotOptionband                  INTEGER,  -- 1 ~ 4 
           dsVdslSlotHamband					   Counter64,
           -- June 2003 newly add --
           dsVdslSlotPSDMaskLevel				   INTEGER,
           dsVdslSlotPBOLength		           INTEGER,
           dsVdslSlotUpServiceProfile			   INTEGER,
           dsVdslSlotDownServiceProfile          INTEGER,
           dsVdslSlotLIUReboot				   INTEGER,
           dsVdslSlotLIUCPENOSStore			   INTEGER
       }                                         

   dsVdslSlotModuleIndex OBJECT-TYPE
       SYNTAX      INTEGER
       MAX-ACCESS  read-only
       STATUS      current
       DESCRIPTION
               "A unique value, greater than zero, for each
               module(Node).  It is recommended that values are assigned
               contiguously starting from 1."
       ::= { dsVdslSlotEntry 1 }

   dsVdslSlotIndex OBJECT-TYPE
       SYNTAX      INTEGER
       MAX-ACCESS  read-only
       STATUS      current
       DESCRIPTION
               "A unique value, greater than zero, for each
               slot.  It is recommended that values are assigned
               contiguously starting from 1."
       ::= { dsVdslSlotEntry 2 }               
       
   dsVdslSlotType OBJECT-TYPE
--       SYNTAX      DisplayString (SIZE (0..64))    
       SYNTAX      DisplayString 
       MAX-ACCESS  read-only
       STATUS      current
       DESCRIPTION       
               "The type of each slot. This string defines the type of slot 
               ex) Vdsl, GBIC."
       ::= { dsVdslSlotEntry 3 }      
                               
   dsVdslSlotInstallStatus OBJECT-TYPE
       SYNTAX      INTEGER {
     			   	  installed(1),
       			      removed(2)
       			   }
       MAX-ACCESS  read-only
       STATUS      current
       DESCRIPTION       
               "The current install status of each slot."
       ::= { dsVdslSlotEntry 4 }                   

   dsVdslSlotProfile OBJECT-TYPE
       SYNTAX      INTEGER {
            			notavailable(-1),
                        asym50-998n(51),
                        asym50-998e(52),
                        sym25-997(53),
                        asym50-998a(54),
                        asym50-998i(55),
                        asym50-998t(56),
                        asym50-998s(57),
                        asym50-998n-4b(58),
                        asym50-998i-4b(59),  
                        asym50-998a-4b(60), 
                        sym25-997a(61),
                        sym25-997i(62),
                        asym70-998n(63),
                        asym70-998i(64),          
                        asym70-998a(65),
                        asym100-998n(66), 
                        asym100-998i(67),
                        asym100-998a(68),
                        sym100-100-998n(69),
                        sym100-100-998i(70),
                        sym100-100-998a(71)                                          
                   }
       MAX-ACCESS  read-write
       STATUS      current
       DESCRIPTION
               "dsVdsl profile ID.
                asym50-998n (51)  PLAN998 Asymmetric
                asym50-998e (52)  PLAN998E Asymmetric
                sym25-997 (53)    PLAN997 Asymmetric
                asym50-998a (54)  ADSL friendly PLAN 998 Asymetric
                asym50-998i (55)  ISDN friendly PLAN 998 Asymetric
                asym50-998t (56)  TLAN friendly PLAN 998 Asymetric
                asym50-998s (57)  ADSL soft mode Asymetric
                asym50-998n-4b(58) PLAN998 Asymmetric 13/50 4 band
                asym50-998i-4b(59) ISDN friendly PLAN 998 13/50 4 band
                asym50-998a-4b(60) ADSL friendly PLAN 998 13/50 4 band
                sym25-997a(61)  ADSL friendly PLAN 997 Symmetric 25/25     
                sym25-997i(62)  ISDN friendly PLAN 997 symmetric 25/25
                asym70-998n(63) PLAN998 Asymmetric 30/70 5 band
                asym70-998i(64) ISDN friendly PLAN 998 asymmetric 30/70 5 band        
                asym70-998a(65) ADSL friendly PLAN 998 asymmetric 30/70 5 band
                asym100-998n(66) PLAN 998n Asymmetric for 6Band DMT 100M 
                asym100-998i(67) PLAN 998i Asymmetric for 6Band DMT 100M
                asym100-998a(68) PLAN 998a Asymmetric for 6Band DMT 100M
                sym100-100-998n(69) PLAN 998n Symmetric for 6Band DMT 100/100M 
                sym100-100-998i(70) PLAN 998i Symmetric for 6Band DMT 100/100M  
                sym100-100-998a(71) PLAN 998a Symmetric for 6Band DMT 100/100M"                                      
       ::= { dsVdslSlotEntry 5 }                  
       
   dsVdslSlotOptionband OBJECT-TYPE
       SYNTAX      INTEGER {
            			notavailable(-1),
                        annex-B-6-64(1),
                        annex-A-6-32(2),
                        annex-B-32-64(3),
                        exclude(4)                        
                   }
       MAX-ACCESS  read-write
       STATUS      current
       DESCRIPTION
               "dsVdsl Optional band ID.
                Annex B 6-64 (1)
                Annex A 6-32 (2)
                Annex B 32-64 (3)
                Exclude Option Band (4)
               "
       ::= { dsVdslSlotEntry 6 }                  
       
   dsVdslSlotHamband OBJECT-TYPE
       SYNTAX      Counter64 
       MAX-ACCESS  read-write
       STATUS      current
       DESCRIPTION
               "dsVdsl Amature Radio(HAM) band ID.
               The value of Ham band is combination of the following value.
               If you want to set band1 and band10, you should set value 257(band1 + band10)
               to the Ham band.   
               band1   [  1.800  -  1.810  ] MHz : RFI Notch                (1)
               band2   [  1.800  -  1.825  ] MHz : KOREA HAM-BAND           (2)
               band3   [  1.810  -  1.825  ] MHz : ANNEX F                  (4)
               band4   [  1.810  -  2.000  ] MHz : ETSI, T1E1               (8)
               band5   [  1.9075 -  1.9125 ] MHz : ANNEX F                  (16)
               band6   [  2.173  -  2.191  ] MHz : DT GMDSS                 (2097152)   0x0000 0020 0000
               band7   [  3.500  -  3.550  ] MHz : KOREA HAM-BAND           (32)
               band8   [  3.500  -  3.575  ] MHz : ANNEX F                  (64) 
               band9   [  3.500  -  3.800  ] MHz : ETSI                     (128)
               band10  [  3.500  -  4.000  ] MHz : T1E1                     (256)
               band11  [  3.747  -  3.754  ] MHz : ANNEX F                  (512)
               band12  [  3.790  -  3.800  ] MHz : KOREA HAM-BAND           (1024)             
               band13  [  3.791  -  3.805  ] MHz : ANNEX F                  (2048)
               band14  [  4.200  -  4.215  ] MHz : DT GMDSS                 (4194304)                   0x0000 0040 0000
               band15  [  5.900  -  6.200  ] MHz : DT DRM radio (Broadcasting)           (8388608)      0x0000 0080 0000
               band16  [  6.300  -  6.320  ] MHz : DT GMDSS                              (16777216)     0x0000 0100 0000
               band17  [  7.000  -  7.100  ] MHz : KOREA HAM-BAND, ANNEX F, ETSI         (4096)
               band18  [  7.000  -  7.300  ] MHz : T1E1                                  (8192)
               band19  [  7.100  -  7.350  ] MHz : DT DRM radio (Broadcasting)           (33554432)     0x0000 0200 0000
               band20  [  8.405  -  8.420  ] MHz : DT GMDSS                              (67108864)     0x0000 0400 0000
               band21  [  9.400  -  9.900  ] MHz : DT DRM radio (Broadcasting)           (134217728)    0x0000 0800 0000   
               band22  [ 10.100  - 10.150  ] MHz : KOREA HAM-BAND, ANNEX F, ETSI, T1E1   (16384)
               band23  [ 11.600  - 12.100  ] MHz : DT DRM radio (Broadcasting)           (268435456)    0x0000 1000 0000
               band24  [ 12.570  - 12.585  ] MHz : DT GMDSS                              (536870912)    0x0000 2000 0000
               band25  [ 13.570  - 13.870  ] MHz : DT DRM radio (Broadcasting)           (1073741824)   0x0000 4000 0000
               band26  [ 14.000  - 14.350  ] MHz : ANNEX F, ETSI, T1E1                   (32768)
               band27  [ 15.100  - 15.800  ] MHz : DT DRM radio (Broadcasting)           (2147483648)   0x0000 8000 0000
               band28  [ 16.795  - 16.810  ] MHz : DT GMDSS                              (4294967296)   0x0001 0000 0000
               band29  [ 17.480  - 17.900  ] MHz : DT DRM radio (Broadcasting)           (8589934592)   0x0002 0000 0000
               band30  [ 18.068  - 18.168  ] MHz : ANNEX F, ETSI, T1E1                   (65536)
               band31  [ 21.000  - 21.450  ] MHz : ANNEX F, ETSI, T1E1                   (131072)       0x0000 0002 0000
               band32  [ 24.890  - 24.990  ] MHz : ANNEX F, ETST, T1E1                   (262144)       0x0000 0004 0000
               band33  [ 28.000  - 29.100  ] MHz : ETSI                                  (524288)       0x0000 0008 0000
               band34  [ 28.000  - 29.700  ] MHz : ANNEX F, ETSI, T1E1                   (1048576)      0x0000 0010 0000
               "
                                      
       ::= { dsVdslSlotEntry 7 }               
  
  dsVdslSlotPSDMaskLevel OBJECT-TYPE
       SYNTAX      INTEGER {  
       					notavailable(-1),
            			old-gains(0),
                        aNSI-M1(1),
                        aNSI-M2(2), 
                        eTSI-M1(3),
                        eTSI-M2(4),
                        aNNEX-F-8-5(5), 
                        aNSI-M1-EX(6),
                        aNSI-M2-EX(7),
                        eTSI-M1-EX(8),
                        eTSI-M2-EX(9),
                        aNNEX-F-11-5(10),
                        pSD-K(11)                      
                   }
       MAX-ACCESS  read-write
       STATUS      current
       DESCRIPTION
               "dsVdsl PSD Mask Level.
                notavailable(-1)
                old gains(0)
                ANSI M1(1)
                ANSI M2(2) 
                ETSI M1(3)
                ETSI M2(4)
                ANNEX F 8.5(5) 
                ANSI M1 EX(6)
                ANSI M2 EX(7)
                ETSI M1 EX(8)
                ETSI M2 EX(9)
                ANNEX F 11.5(10)
                PSD-K(11)                  
               "
       ::= { dsVdslSlotEntry 8 }                  
       
   dsVdslSlotPBOLength OBJECT-TYPE
       SYNTAX      INTEGER {
            			pbo100m(1),
                        pbo200m(2),
                        pbo300m(3),
                        pbo400m(4),
                        pbo500m(5),
                        pbo600m(6),
                        pbo700m(7),
                        pbo800m(8),
                        pbo900m(9)                       
                   }
       MAX-ACCESS  read-write
       STATUS      current
       DESCRIPTION
               "dsVdsl Power Back-Off Length.
                100m(1)
                200m(2)
                300m(3)
                400m(4)
                500m(5)
                600m(6)
                700m(7)
                800m(8)
                900m(9)                       
               "
   ::= { dsVdslSlotEntry 9 }                   
   
   dsVdslSlotUpServiceProfile OBJECT-TYPE
       SYNTAX      INTEGER 
       MAX-ACCESS  read-only
       STATUS      current
       DESCRIPTION
               "dsVdsl slot upstream service profile."
   ::= { dsVdslSlotEntry 10 }                  
   
   dsVdslSlotDownServiceProfile OBJECT-TYPE
       SYNTAX      INTEGER 
       MAX-ACCESS  read-only
       STATUS      current
       DESCRIPTION
               "dsVdsl slot downstream service profile."
   ::= { dsVdslSlotEntry 11 }                      
                   
   dsVdslSlotLIUReboot OBJECT-TYPE
       SYNTAX      INTEGER {
       					reboot(1)
       			   }
       MAX-ACCESS  read-write
       STATUS      current
       DESCRIPTION
               "dsVdsl LIU slot reboot."
   ::= { dsVdslSlotEntry 12 }                      
   
   dsVdslSlotLIUCPENOSStore OBJECT-TYPE
       SYNTAX      INTEGER {
       				   no(0),
                       yes(1),
                       done(2),
                       fail(3)
       			   }
       MAX-ACCESS  read-write
       STATUS      current
       DESCRIPTION
               "Store CPE NOS into each dsVdsl slot.
                no(0)   : No CPE NOS store.
                yes(1)  : Now storing.
                done(2) : Storing completed.
                fail(3) : Storing fail"
   ::= { dsVdslSlotEntry 13 }                      
                                      
--
-- June 2003 dhlee dsSystemSlotTable
-- Just for V51xxF,                                           
-- 
                                               
   dsSystemSlotTable OBJECT-TYPE
       SYNTAX      SEQUENCE OF DsSystemSlotEntry
       MAX-ACCESS  not-accessible
       STATUS      mandatory
       DESCRIPTION
               "A list of slotEntry entries."
       ::= { dsSwitchModules 10 }

   dsSystemSlotEntry OBJECT-TYPE
       SYNTAX      DsSystemSlotEntry
       MAX-ACCESS  not-accessible
       STATUS      mandatory
       DESCRIPTION
               "An entry containing management information applicable
               to a particular switch Slot."
       INDEX   { dsSystemSlotModuleIndex , dsSystemSlotIndex }
       ::= { dsSystemSlotTable 1 }
                              
   DsSystemSlotEntry ::=
       SEQUENCE {
           dsSystemSlotModuleIndex                 INTEGER,
           dsSystemSlotIndex                       INTEGER,
           dsSystemSlotType			   		       DisplayString,           
           dsSystemSlotInstallStatus			   INTEGER,
           dsSystemSlotStatus				       INTEGER,
           dsSystemSlotPortNum					   INTEGER	
       }                      
              
   dsSystemSlotModuleIndex OBJECT-TYPE
       SYNTAX      INTEGER
       MAX-ACCESS  read-only
       STATUS      current
       DESCRIPTION
               "A unique value, greater than zero, for each
               module(Node).  It is recommended that values are assigned
               contiguously starting from 1."
       ::= { dsSystemSlotEntry 1 }

   dsSystemSlotIndex OBJECT-TYPE
       SYNTAX      INTEGER
       MAX-ACCESS  read-only
       STATUS      current
       DESCRIPTION
               "A unique value, greater than zero, for each
               slot.  It is recommended that values are assigned
               contiguously starting from 1."
       ::= { dsSystemSlotEntry 2 }                   
                                             
   dsSystemSlotType OBJECT-TYPE
       SYNTAX      DisplayString 
       MAX-ACCESS  read-only
       STATUS      current
       DESCRIPTION       
               "The type of each slot. This string defines the type of slot
               ex) TX-10/100, FX-100, GBIC, SWU, ADSL2+, ADSL, SHDSL, Vdsl, Ethernet"
       ::= { dsSystemSlotEntry 3 }      
                               
  dsSystemSlotInstallStatus OBJECT-TYPE
       SYNTAX      INTEGER {
     			   	  installed(1),
       			      removed(2)
       			   }
       MAX-ACCESS  read-only
       STATUS      current
       DESCRIPTION       
               "The current install status of each slot."
       ::= { dsSystemSlotEntry 4 }
  
  dsSystemSlotStatus		OBJECT-TYPE
  		SYNTAX		INTEGER {
  				idle (0),
  				equip (1),
  				init (2),
  				ready (3),
  				run (4),
  				reset (5),
  				max (6)
  				}
  		MAX-ACCESS	read-only
  		STATUS		current
  		DESCRIPTION
  				"The current slot status "
  		::= { dsSystemSlotEntry 5 }     
  		
   dsSystemSlotPortNum 		OBJECT-TYPE
   	SYNTAX 		INTEGER 
   	MAX-ACCESS 	read-only
	STATUS		current
   	DESCRIPTION
   		"The number of port on the slot."				
   		::= { dsSystemSlotEntry 6 }
  						
  		
  						                        

--
--  June 2003 dhlee 
--    
   dsTemperatureTable OBJECT-TYPE
       SYNTAX      SEQUENCE OF DsTemperatureEntry
       MAX-ACCESS  not-accessible
       STATUS      current
       DESCRIPTION
               "A list of dsTemperatureEntry entries."
       ::= { dsSwitchModules 5 }

   dsTemperatureEntry OBJECT-TYPE
       SYNTAX      DsTemperatureEntry
       MAX-ACCESS  not-accessible
       STATUS      current
       DESCRIPTION
               "An entry containing temperature information."
       INDEX   { dsTemperatureNodeIndex , dsTemperatureIndex }
       ::= { dsTemperatureTable 1 }

   DsTemperatureEntry ::=
       SEQUENCE {
           dsTemperatureNodeIndex       INTEGER,
           dsTemperatureIndex           INTEGER,
           dsTemperatureStatus          INTEGER
       }

   dsTemperatureNodeIndex OBJECT-TYPE
       SYNTAX      INTEGER
       MAX-ACCESS  read-only
       STATUS      current
       DESCRIPTION
               "A unique value, greater than zero, for each
               module.  It is recommended that values are assigned
               contiguously starting from 1.  The value for each
               interface sub-layer must remain constant at least from
               one re-initialization of the entity's network
               management system to the next re-initialization."
       ::= { dsTemperatureEntry 1 }

   dsTemperatureIndex OBJECT-TYPE
       SYNTAX      INTEGER
       MAX-ACCESS  read-only
       STATUS      current
       DESCRIPTION
               "A unique value, greater than zero, for each
               module.  It is recommended that values are assigned
               contiguously starting from 1.  The value for each
               interface sub-layer must remain constant at least from
               one re-initialization of the entity's network
               management system to the next re-initialization."
       ::= { dsTemperatureEntry 2 }

   dsTemperatureStatus OBJECT-TYPE
       SYNTAX      INTEGER
       MAX-ACCESS  read-only
       STATUS      current
       DESCRIPTION
               "dsTemperature status information"
       ::= { dsTemperatureEntry 3 }


   dsPowerTable OBJECT-TYPE
       SYNTAX      SEQUENCE OF DsPowerEntry
       MAX-ACCESS  not-accessible
       STATUS      current
       DESCRIPTION
               "A list of dsPowerEntry entries."
       ::= { dsSwitchModules 6 }

   dsPowerEntry OBJECT-TYPE
       SYNTAX      DsPowerEntry
       MAX-ACCESS  not-accessible
       STATUS      current
       DESCRIPTION
               "An entry containing dsPower information."
       INDEX   { dsPowerNodeIndex , dsPowerIndex }
       ::= { dsPowerTable 1 }

   DsPowerEntry ::=
       SEQUENCE {
           dsPowerNodeIndex       INTEGER,
           dsPowerIndex           INTEGER,
           dsPowerstatus          INTEGER,
           dsPowerinstalled       INTEGER
       }

   dsPowerNodeIndex OBJECT-TYPE
       SYNTAX      INTEGER
       MAX-ACCESS  read-only
       STATUS      current
       DESCRIPTION
               "A unique value, greater than zero, for each
               module.  It is recommended that values are assigned
               contiguously starting from 1.  The value for each
               interface sub-layer must remain constant at least from
               one re-initialization of the entity's network
               management system to the next re-initialization."
       ::= { dsPowerEntry 1 }

   dsPowerIndex OBJECT-TYPE
       SYNTAX      INTEGER
       MAX-ACCESS  read-only
       STATUS      current
       DESCRIPTION
               "A unique value, greater than zero, for each
               module.  It is recommended that values are assigned
               contiguously starting from 1.  The value for each
               interface sub-layer must remain constant at least from
               one re-initialization of the entity's network
               management system to the next re-initialization."
       ::= { dsPowerEntry 2 }

   dsPowerstatus OBJECT-TYPE
       SYNTAX      INTEGER {
                     ok(1),
                     fail(2),
                     other(3)
                   }
       MAX-ACCESS  read-only
       STATUS      current
       DESCRIPTION
               "dsPower status information"
       ::= { dsPowerEntry 3 }

   dsPowerinstalled OBJECT-TYPE
       SYNTAX      INTEGER {
                     installed(1),
                     uninstalled(2)
                   }
       MAX-ACCESS  read-only
       STATUS      current
       DESCRIPTION
               "dsPower install information"
       ::= { dsPowerEntry 4 }







   dsFanTable OBJECT-TYPE
       SYNTAX      SEQUENCE OF DsFanEntry
       MAX-ACCESS  not-accessible
       STATUS      current
       DESCRIPTION
               "A list of dsFanEntry entries."
       ::= { dsSwitchModules 7 }

   dsFanEntry OBJECT-TYPE
       SYNTAX      DsFanEntry
       MAX-ACCESS  not-accessible
       STATUS      current
       DESCRIPTION
               "An entry containing fan information."
       INDEX   { dsFanNodeIndex , dsFanIndex }
       ::= { dsFanTable 1 }

   DsFanEntry ::=
       SEQUENCE {
           dsFanNodeIndex       INTEGER,
           dsFanIndex           INTEGER,
           dsFanstatus          INTEGER,
           dsFaninstalled       INTEGER
       }

   dsFanNodeIndex OBJECT-TYPE
       SYNTAX      INTEGER
       MAX-ACCESS  read-only
       STATUS      current
       DESCRIPTION
               "A unique value, greater than zero, for each
               module.  It is recommended that values are assigned
               contiguously starting from 1.  The value for each
               interface sub-layer must remain constant at least from
               one re-initialization of the entity's network
               management system to the next re-initialization."
       ::= { dsFanEntry 1 }

   dsFanIndex OBJECT-TYPE
       SYNTAX      INTEGER
       MAX-ACCESS  read-only
       STATUS      current
       DESCRIPTION
               "A unique value, greater than zero, for each
               module.  It is recommended that values are assigned
               contiguously starting from 1.  The value for each
               interface sub-layer must remain constant at least from
               one re-initialization of the entity's network
               management system to the next re-initialization."
       ::= { dsFanEntry 2 }

   dsFanstatus OBJECT-TYPE
       SYNTAX      INTEGER {
                     ok(1),
                     fail(2),
                     other(3)
                   }
       MAX-ACCESS  read-only
       STATUS      current
       DESCRIPTION
               "dsFan status information"
       ::= { dsFanEntry 3 }

   dsFaninstalled OBJECT-TYPE
       SYNTAX      INTEGER {
                     installed(1),
                     uninstalled(2)
                   }
       MAX-ACCESS  read-only
       STATUS      current
       DESCRIPTION
               "dsFan install information"
       ::= { dsFanEntry 4 }
 
--
-- Lastest user MAC table
--                                                        
                                                         
   dsSwitchUserMacTable OBJECT-TYPE
       SYNTAX      SEQUENCE OF DsSwitchUserMacEntry
       MAX-ACCESS  not-accessible
       STATUS      mandatory
       DESCRIPTION
               "A list of dsSwitchUserMacEntry entries."
       ::= { dsSwitchModules 11 }

   dsSwitchUserMacEntry OBJECT-TYPE
       SYNTAX      DsSwitchUserMacEntry
       MAX-ACCESS  not-accessible
       STATUS      mandatory
       DESCRIPTION
               "An entry containing management information applicable
               to a particular switch User mac address."
       INDEX   { dsUserMacModuleIndex , dsUserMacPortIndex }
       ::= { dsSwitchUserMacTable 1 }
                              
   DsSwitchUserMacEntry ::=
       SEQUENCE {
           dsUserMacModuleIndex                 INTEGER,
           dsUserMacPortIndex                   INTEGER,
           dsUserMacAddress1    	   		      PhysAddress,           
           dsUserMacAddress2			   		  PhysAddress,           
           dsUserMacAddress3			   		  PhysAddress,
           dsUserMacAddress4			   		  PhysAddress,
           dsUserMacAddress5					  PhysAddress,
           dsUserMacAddress6					  PhysAddress,
           dsUserMacAddress7					  PhysAddress,
           dsUserMacAddress8					  PhysAddress
       }                      
              
   dsUserMacModuleIndex OBJECT-TYPE
       SYNTAX      INTEGER
       MAX-ACCESS  read-only
       STATUS      current
       DESCRIPTION
               "A unique value, greater than zero, for each
               module(Node).  It is recommended that values are assigned
               contiguously starting from 1."
       ::= { dsSwitchUserMacEntry 1 }

   dsUserMacPortIndex OBJECT-TYPE
       SYNTAX      INTEGER
       MAX-ACCESS  read-only
       STATUS      current
       DESCRIPTION
               "A unique value, greater than zero, for each
               port.  It is recommended that values are assigned
               contiguously starting from 1."
       ::= { dsSwitchUserMacEntry 2 }                   
                                             
   dsUserMacAddress1 OBJECT-TYPE
       SYNTAX      PhysAddress
       MAX-ACCESS  read-only
       STATUS      current
       DESCRIPTION       
               "The first entry of lastest user mac address."
       ::= { dsSwitchUserMacEntry 3 }      
                               
   dsUserMacAddress2 OBJECT-TYPE
       SYNTAX      PhysAddress
       MAX-ACCESS  read-only
       STATUS      current
       DESCRIPTION       
               "The second entry of lastest user mac address."
       ::= { dsSwitchUserMacEntry 4 }      
   
   dsUserMacAddress3 OBJECT-TYPE
       SYNTAX      PhysAddress
       MAX-ACCESS  read-only
       STATUS      current
       DESCRIPTION       
               "The third entry of lastest user mac address."
       ::= { dsSwitchUserMacEntry 5 }      
                                   
   dsUserMacAddress4 OBJECT-TYPE
       SYNTAX      PhysAddress
       MAX-ACCESS  read-only
       STATUS      current
       DESCRIPTION       
               "The fourth entry of lastest user mac address."
       ::= { dsSwitchUserMacEntry 6 }  
       
   dsUserMacAddress5 OBJECT-TYPE
       SYNTAX      PhysAddress
       MAX-ACCESS  read-only
       STATUS      current
       DESCRIPTION       
               "The fifth entry of lastest user mac address."
       ::= { dsSwitchUserMacEntry 7 }   
       
       
   dsUserMacAddress6 OBJECT-TYPE
       SYNTAX      PhysAddress
       MAX-ACCESS  read-only
       STATUS      current
       DESCRIPTION       
               "The sixth entry of lastest user mac address."
       ::= { dsSwitchUserMacEntry 8 }   
       
   dsUserMacAddress7 OBJECT-TYPE
       SYNTAX      PhysAddress
       MAX-ACCESS  read-only
       STATUS      current
       DESCRIPTION       
               "The seventh entry of lastest user mac address."
       ::= { dsSwitchUserMacEntry 9 }   
       
       
   dsUserMacAddress8 OBJECT-TYPE
       SYNTAX      PhysAddress
       MAX-ACCESS  read-only
       STATUS      current
       DESCRIPTION       
               "The eighth entry of lastest user mac address."
       ::= { dsSwitchUserMacEntry 10 }      

--
-- ARP informations.
--

   dsSwitchAtTable OBJECT-TYPE
       SYNTAX      SEQUENCE OF DsSwitchAtEntry
       MAX-ACCESS  not-accessible
       STATUS      mandatory
       DESCRIPTION
               "A list of dsSwitchUserMacEntry entries."
       ::= { dsSwitchModules 12 }

   dsSwitchAtEntry OBJECT-TYPE
       SYNTAX      DsSwitchAtEntry
       MAX-ACCESS  not-accessible
       STATUS      mandatory
       DESCRIPTION
               "An entry containing management information applicable
               to a particular switch ARP."
       INDEX   { dsSwitchAtifIndex, dsSwitchAtNetAddress }
       ::= { dsSwitchAtTable 1 }

   DsSwitchAtEntry ::=
       SEQUENCE {
           dsSwitchAtifIndex                 INTEGER,
           dsSwitchAtNetAddress              IpAddress,
           dsSwitchAtMacAddress              PhysAddress,
           dsSwitchAtVID					   INTEGER
       }
  
   dsSwitchAtifIndex OBJECT-TYPE
       SYNTAX      INTEGER
       MAX-ACCESS  read-only
       STATUS      current
       DESCRIPTION
               "It means that the ifIndex in MIB-II Interface of physical port.."
       ::= { dsSwitchAtEntry 1 }

   dsSwitchAtNetAddress OBJECT-TYPE
       SYNTAX      IpAddress
       MAX-ACCESS  read-only
       STATUS      current
       DESCRIPTION
               "The IP address in ARP informations."
       ::= { dsSwitchAtEntry 2 }

   dsSwitchAtMacAddress OBJECT-TYPE
       SYNTAX      PhysAddress
       MAX-ACCESS  read-only
       STATUS      current
       DESCRIPTION
               "The physical address in ARP informations."
       ::= { dsSwitchAtEntry 3 }
                             
   dsSwitchAtVID OBJECT-TYPE
       SYNTAX      INTEGER
       MAX-ACCESS  read-only
       STATUS      current
       DESCRIPTION
               "The VLAN ID in ARP informations."
       ::= { dsSwitchAtEntry 4 }

-- 
-- TC table
--

    dsTcTable OBJECT-TYPE
		SYNTAX	    SEQUENCE OF DsTcEntry
		MAX-ACCESS  not-accessible
		STATUS	    current
		DESCRIPTION
			"A list of dsTcEntrry entries."
		::= { dsSwitchModules 20}

    dsTcEntry OBJECT-TYPE
		SYNTAX	    DsTcEntry
		MAX-ACCESS  not-accessible
		STATUS	    current
		DESCRIPTION
			"An entry containing dsTc information."
		INDEX { dsTcNodeIndex, dsTcIndex }
		::= { dsTcTable 1 }

    DsTcEntry ::=
		SEQUENCE {
			dsTcNodeIndex 			INTEGER,
	    	dsTcIndex	        		INTEGER,
	    	dsTcGuaranteedBandwidth	INTEGER,
	    	dsTcMaxBandwidth	    	INTEGER,
	   		dsTcWeight	        	INTEGER,
	    	dsTcReset					INTEGER,
	    	dsTcStatsCount			Counter64,
	    	dsTcStatsCount5Sec		Counter,
	    	dsTcStatsCount1Min		Counter,
	    	dsTcStatsCount10Min		Counter,
	    	dsTcStatsCountReset		INTEGER
		}
	    
    dsTcNodeIndex OBJECT-TYPE
		SYNTAX	    INTEGER
		MAX-ACCESS  read-only
		STATUS	    current
		DESCRIPTION
	    	"A unique value, greater than zero, for each
	    	node. It is recommended that values are assinged 
	    	contiguously starting from 1."
		::= { dsTcEntry 1 }

    dsTcIndex	OBJECT-TYPE
		SYNTAX	    INTEGER
		MAX-ACCESS  read-only
		STATUS	    current
		DESCRIPTION
	    	"A unique value, greater than zero, for each
	    	dsTc. It is recommended that values are assinged 
	    	contiguously starting from 1."
		::= { dsTcEntry 2 }

    dsTcGuaranteedBandwidth	OBJECT-TYPE	     
		SYNTAX	    INTEGER
		MAX-ACCESS  read-write
		STATUS	    current
		DESCRIPTION
	    	"It means reserved bandwidth of route applied to
	    	processing protocol. Bandwidth can be from 1 to 16Gbps."
		::= { dsTcEntry 3 }
    
    dsTcMaxBandwidth	OBJECT-TYPE
		SYNTAX	    INTEGER
		MAX-ACCESS  read-write
		STATUS	    current
		DESCRIPTION
	   		"It means maximum bandwidth of route applied to 
	    	processing protocol. Bandwidth can be from 1 to 16Gbps."
		::= { dsTcEntry 4 }

    dsTcWeight	OBJECT-TYPE
		SYNTAX	    INTEGER
		MAX-ACCESS  read-write
		STATUS	    current
		DESCRIPTION
	    	"It means weight limit of route applied to processing 
	    	protocol. Weight limit can be from 1 to 1024."
		::= { dsTcEntry 5 }

	dsTcReset		OBJECT-TYPE
		SYNTAX		INTEGER  { reset(1) }
		MAX-ACCESS	read-write
		STATUS		current
		DESCRIPTION
			"Reset configuration about route applied to processing protocol"
		::= { dsTcEntry 6 }
			
    dsTcStatsCount    OBJECT-TYPE
    	SYNTAX	    Counter64
    	MAX-ACCESS  read-only
    	STATUS	    current
    	DESCRIPTION
    	    "The total bits number of packets matching with a tc configuration, 
	    	the counter value is a cumulative sum"
    		::= { dsTcEntry 7 }

    dsTcStatsCount5Sec     OBJECT-TYPE
    	SYNTAX	    Counter
    	MAX-ACCESS  read-only
    	STATUS	    current
    	DESCRIPTION
    	    "The average bps of packets matching with 
	     	dsTc configuration during 5 sec."
    		::= { dsTcEntry 8 }
    	
    dsTcStatsCount1Min     OBJECT-TYPE
    	SYNTAX	    Counter
    	MAX-ACCESS  read-only
    	STATUS	    current
    	DESCRIPTION
    	    "The average bps of packets matching with 
	     	dsTc configuration during 1 minutes."
    		::= { dsTcEntry 9 }
    	
    dsTcStatsCount10Min     OBJECT-TYPE
    	SYNTAX	    Counter
    	MAX-ACCESS  read-only
    	STATUS	    current
    	DESCRIPTION
    	    "The average bps of packets matching with 
	     	dsTc configuration during 10 minutes."
    		::= { dsTcEntry 10 }
    	
    	
    dsTcStatsCountReset OBJECT-TYPE
    	SYNTAX 	     INTEGER { reset(1) }
    	MAX-ACCESS   read-write
    	STATUS       current
    	DESCRIPTION 
    	    "Reset Tc Statistics Counter Registers including tcStatsCount, 
 	     	tcStatsCount5Sec, tcStatsCount1Min and tcStatsCount10Min"
    		::= { dsTcEntry 11 }
    	       
END
