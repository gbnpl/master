--
-- sle-bridge-mib.mib
-- MIB generated by MG-SOFT Visual MIB Builder Version 6.0  Build 88
-- Thursday, August 08, 2013 at 14:45:02
--

--  SLE-BRIDGE-MIB.my
-- MIB generated by MG-SOFT Visual MIB Builder Version 3.0 Build 285
-- Monday, December 13, 2004 at 13:09:15
-- 
--  SLE-BRIDGE-MIB.my
-- MIB generated by MG-SOFT Visual MIB Builder Version 4.0 Build 417
-- Wednesday, December 08, 2004 at 13:53:43
-- 

	SLE-BRIDGE-MIB DEFINITIONS ::= BEGIN
 
		IMPORTS
			sleMgmt			
				FROM DASAN-SMI			
			AddressFamilyNumbers			
				FROM IANA-ADDRESS-FAMILY-NUMBERS-MIB			
			InterfaceIndex			
				FROM IF-MIB			
			SleControlStatusType, SleControlRequestResultType			
				FROM SLE-TC-MIB			
			OBJECT-GROUP, NOTIFICATION-GROUP			
				FROM SNMPv2-CONF			
			TimeTicks, IpAddress, Integer32, Unsigned32, Gauge32, 
			Counter32, Counter64, BITS, OBJECT-TYPE, MODULE-IDENTITY, 
			NOTIFICATION-TYPE			
				FROM SNMPv2-SMI			
			TimeStamp, MacAddress, TruthValue			
				FROM SNMPv2-TC;
	
	
--  			sle			
-- FROM AN-MIB			
-- December 08, 2004 at 08:40 GMT
-- 
-- 1.3.6.1.4.1.6296.9.8
-- December 08, 2004 at 09:03 GMT
-- December 08, 2004 at 08:40 GMT
		sleBridge MODULE-IDENTITY 
			LAST-UPDATED "200412080903Z"		-- December 08, 2004 at 09:03 GMT
			ORGANIZATION 
				" "
			CONTACT-INFO 
				" "
			DESCRIPTION 
				"This MIB contains all needed informations about bridgePorts and
				all supported sle bridgeing features."
			REVISION "200412080840Z"		-- December 08, 2004 at 08:40 GMT
			DESCRIPTION 
				"AFI"
			::= { sleMgmt 3 }

		
	
--
-- Type definitions
--
	
		Boolean ::= INTEGER
			{
			disable(0),
			enable(1)
			}

		SleLldpSysCapType ::= BITS
			{
			other(0),
			repeater(1),
			bridge(2),
			wlanAccessPoint(3),
			router(4),
			telephone(5),
			docsisCableDevice(6),
			stationOnly(7)
			}

--  Type definitions
-- 
		SleIgmpMcastControlRequestType ::= INTEGER
			{
			createIgmpStaticMcast(1),
			destroyIgmpStaticMcast(2)
			}

		SleIgmpConfControlRequestType ::= INTEGER { setIgmpConfProfile(1) }

		SleLldpManAddrIfSubType ::= INTEGER
			{
			unknown(1),
			ifIndex(2),
			systemPortNumber(3)
			}

	
	
--
-- Node definitions
--
	
--  Node definitions
-- 
-- 1.3.6.1.4.1.6296.9.8.1
		sleBridgeBase OBJECT IDENTIFIER ::= { sleBridge 1 }

		
--  1.3.6.1.4.1.6296.9.8.1.1
		sleBridgeBaseInfo OBJECT IDENTIFIER ::= { sleBridgeBase 1 }

		
--  1.3.6.1.4.1.6296.9.8.1.1.1
		sleBridgeMacAddress OBJECT-TYPE
			SYNTAX OCTET STRING (SIZE (6))
			MAX-ACCESS read-only
			STATUS current
			DESCRIPTION
				"System MAC Address of bridge"
			::= { sleBridgeBaseInfo 1 }

		
--  1.3.6.1.4.1.6296.9.8.1.1.2
		sleBridgePortNum OBJECT-TYPE
			SYNTAX INTEGER (1..256)
			MAX-ACCESS read-only
			STATUS current
			DESCRIPTION
				"Number of bridge ports"
			::= { sleBridgeBaseInfo 2 }

		
--  1.3.6.1.4.1.6296.9.8.1.1.3
		sleBridgeLagMaxId OBJECT-TYPE
			SYNTAX INTEGER (1..14)
			MAX-ACCESS read-only
			STATUS current
			DESCRIPTION
				"This value assigned to the aggregation max id."
			::= { sleBridgeBaseInfo 3 }

		
--  1.3.6.1.4.1.6296.9.8.1.1.4
		sleBridgeLacpActivity OBJECT-TYPE
			SYNTAX INTEGER
				{
				disabled(0),
				enabled(1)
				}
			MAX-ACCESS read-only
			STATUS current
			DESCRIPTION
				"The LACP enabled/disabled status of the switch"
			::= { sleBridgeBaseInfo 4 }

		
--  1.3.6.1.4.1.6296.9.8.1.1.5
		sleBridgeLacpPriority OBJECT-TYPE
			SYNTAX INTEGER (1..65535)
			MAX-ACCESS read-only
			STATUS current
			DESCRIPTION
				"The priority assigned to the Actor System"
			::= { sleBridgeBaseInfo 5 }

		
--  1.3.6.1.4.1.6296.9.8.1.1.6
		sleBridgeVlanSupportMode OBJECT-TYPE
			SYNTAX BITS
				{
				portbased(0),
				protocolbased(1),
				subnetbased(2)
				}
			MAX-ACCESS read-only
			STATUS current
			DESCRIPTION
				"The supported VLAN mode for ingress untagged frame"
			::= { sleBridgeBaseInfo 6 }

		
--  1.3.6.1.4.1.6296.9.8.1.1.7
		sleBridgeVlanMaxNum OBJECT-TYPE
			SYNTAX INTEGER (0..4096)
			MAX-ACCESS read-only
			STATUS current
			DESCRIPTION
				"sleBridgeVlanMaxNum"
			::= { sleBridgeBaseInfo 7 }

		
--  1.3.6.1.4.1.6296.9.8.1.1.8
		sleBridgeDoubleTagProtoId OBJECT-TYPE
			SYNTAX INTEGER
				{
				dtag8100(33024),
				dtag9100(37120)
				}
			MAX-ACCESS read-only
			STATUS current
			DESCRIPTION
				"programmable Double Tag Protocol Identifier.
				It means outerTPID."
			::= { sleBridgeBaseInfo 8 }

		
--  1.3.6.1.4.1.6296.9.8.1.1.23
		sleBridgeMirrorMode OBJECT-TYPE
			SYNTAX INTEGER
				{
				disabled(0),
				enabled(1)
				}
			MAX-ACCESS read-only
			STATUS current
			DESCRIPTION
				"Mirror mode of bridge"
			::= { sleBridgeBaseInfo 9 }

		
--  1.3.6.1.4.1.6296.9.8.1.1.24
		sleBridgeMirrorMonitorPortId OBJECT-TYPE
			SYNTAX INTEGER (1..255)
			MAX-ACCESS read-only
			STATUS current
			DESCRIPTION
				"Mirroring port ID
				1-254: physical port ID
				255: mirror to cpu"
			::= { sleBridgeBaseInfo 10 }

		
		sleBridgeMirroredIngressPorts OBJECT-TYPE
			SYNTAX OCTET STRING (SIZE (0..32))
			MAX-ACCESS read-only
			STATUS current
			DESCRIPTION
				"Ingress mirrored port map"
			::= { sleBridgeBaseInfo 11 }

		
		sleBridgeMirroredEgressPorts OBJECT-TYPE
			SYNTAX OCTET STRING (SIZE (0..32))
			MAX-ACCESS read-only
			STATUS current
			DESCRIPTION
				"Egress mirrored port map"
			::= { sleBridgeBaseInfo 12 }

		
		sleBridgeMaxLearnPerUnit OBJECT-TYPE
			SYNTAX INTEGER (-1..2147483647)
			MAX-ACCESS read-only
			STATUS current
			DESCRIPTION
				"Limit maximum number of MAC addresses learning 
				newly per unit time(one second) on a bridge.
				(0: nothing learned, -l: unlimited.)"
			::= { sleBridgeBaseInfo 13 }

		
--  1.3.6.1.4.1.6296.9.8.1.1.25
		sleBridgeFdbAgeingTime OBJECT-TYPE
			SYNTAX Integer32 (10..21474830)
			MAX-ACCESS read-only
			STATUS current
			DESCRIPTION
				"The timeout period in seconds for aging out 
				dynamically learned forwarding information."
			DEFVAL { 300 }
			::= { sleBridgeBaseInfo 14 }

		
--  1.3.6.1.4.1.6296.9.8.1.1.26
		sleBridgeFdbMaxEntries OBJECT-TYPE
			SYNTAX Integer32
			MAX-ACCESS read-only
			STATUS current
			DESCRIPTION
				"The supported maximum fdb entries."
			::= { sleBridgeBaseInfo 15 }

		
		sleBridgeFdbCurrentEntries OBJECT-TYPE
			SYNTAX Integer32
			MAX-ACCESS read-only
			STATUS current
			DESCRIPTION
				"Number of Fdb entries learned currently."
			::= { sleBridgeBaseInfo 16 }

		
--  1.3.6.1.4.1.6296.9.8.1.1.27
		sleBridgeStackMode OBJECT-TYPE
			SYNTAX INTEGER
				{
				disable(0),
				master(1),
				slave(2)
				}
			MAX-ACCESS read-only
			STATUS current
			DESCRIPTION
				"Stack status of device."
			::= { sleBridgeBaseInfo 17 }

		
--  1.3.6.1.4.1.6296.9.8.1.1.28
		sleBridgeStackDeviceName OBJECT-TYPE
			SYNTAX OCTET STRING (SIZE (0..8))
			MAX-ACCESS read-only
			STATUS current
			DESCRIPTION
				"Device name of stack device."
			::= { sleBridgeBaseInfo 18 }

		
--  1.3.6.1.4.1.6296.9.8.1.1.29
		sleBridgeStackNodeId OBJECT-TYPE
			SYNTAX INTEGER (1..65534)
			MAX-ACCESS read-only
			STATUS current
			DESCRIPTION
				"Node ID of stack device"
			::= { sleBridgeBaseInfo 19 }

		
--  1.3.6.1.4.1.6296.9.8.1.1.30
		sleBridgeLldpMessageTxInterval OBJECT-TYPE
			SYNTAX Integer32 (5..32768)
			MAX-ACCESS read-write
			STATUS current
			DESCRIPTION
				"The interval at which LLDP frames are transmitted on behalf of this LLDP agent."
			::= { sleBridgeBaseInfo 20 }

		
--  1.3.6.1.4.1.6296.9.8.1.1.31
		sleBridgeLldpTxHoldMultiplier OBJECT-TYPE
			SYNTAX Integer32 (2..10)
			MAX-ACCESS read-write
			STATUS current
			DESCRIPTION
				"The time-to-live value expressed as a multiple of the sleBridgeLldpMessageTxInterval object."
			::= { sleBridgeBaseInfo 21 }

		
--  1.3.6.1.4.1.6296.9.8.1.1.32
		sleBridgeLldpReinitDelay OBJECT-TYPE
			SYNTAX Integer32 (1..10)
			MAX-ACCESS read-write
			STATUS current
			DESCRIPTION
				"Delay (in units of seconds) from when lldpPortConfigAdminStatus object of a particular port  becomes 'disabled' until re-initialization will be attempted."
			::= { sleBridgeBaseInfo 22 }

		
--  1.3.6.1.4.1.6296.9.8.1.1.33
		sleBridgeLldpTxDelay OBJECT-TYPE
			SYNTAX Integer32 (1..8192)
			MAX-ACCESS read-write
			STATUS current
			DESCRIPTION
				"Delay (in units of seconds) between successive LLDP frame transmissions initiated by value/status changes in the LLDP local systems MIB."
			::= { sleBridgeBaseInfo 23 }

		
--  1.3.6.1.4.1.6296.9.8.1.1.34
		sleBridgeLldpNotificationInterval OBJECT-TYPE
			SYNTAX Integer32 (5..3600)
			MAX-ACCESS read-write
			STATUS current
			DESCRIPTION
				"The agent must not generate more than one lldpRemTablesChangenotification-event in the indicated period."
			DEFVAL { 5 }
			::= { sleBridgeBaseInfo 24 }

		
--  1.3.6.1.4.1.6296.9.8.1.1.36
		sleBridgeLldpStatsRemTablesLastChangeTime OBJECT-TYPE
			SYNTAX TimeTicks
			MAX-ACCESS read-only
			STATUS current
			DESCRIPTION
				"The value of sysUpTime object (defined in IETF RFC 3418)at the time an entry is created, modified, or deleted in thein tables associated with the lldpRemoteSystemsData objects and all LLDP extension objects associated with remote systems."
			::= { sleBridgeBaseInfo 25 }

		
--  1.3.6.1.4.1.6296.9.8.1.1.37
		sleBridgeLldpStatsRemTablesInserts OBJECT-TYPE
			SYNTAX Integer32
			MAX-ACCESS read-only
			STATUS current
			DESCRIPTION
				"The number of times the complete set of informationadvertised by a particular MSAP has been inserted into tables contained in lldpRemoteSystemsData and lldpExtensions objects."
			::= { sleBridgeBaseInfo 26 }

		
--  1.3.6.1.4.1.6296.9.8.1.1.38
		sleBridgeLldpStatsRemTablesDeletes OBJECT-TYPE
			SYNTAX Integer32
			MAX-ACCESS read-only
			STATUS current
			DESCRIPTION
				"The number of times the complete set of informationadvertised by a particular MSAP has been deleted fromtables contained in lldpRemoteSystemsData and lldpExtensions objects."
			::= { sleBridgeBaseInfo 27 }

		
--  1.3.6.1.4.1.6296.9.8.1.1.39
		sleBridgeLldpStatsRemTablesDrops OBJECT-TYPE
			SYNTAX Integer32
			MAX-ACCESS read-only
			STATUS current
			DESCRIPTION
				"The number of times the complete set of information advertised by a particular MSAP could not be entered intotables contained in lldpRemoteSystemsData and lldpExtensions objects because of insufficient resources."
			::= { sleBridgeBaseInfo 28 }

		
--  1.3.6.1.4.1.6296.9.8.1.1.40
		sleBridgeLldpStatsRemTablesAgeouts OBJECT-TYPE
			SYNTAX Integer32
			MAX-ACCESS read-only
			STATUS current
			DESCRIPTION
				"The number of times the complete set of informationadvertised by a particular MSAP has been deleted from tables contained in lldpRemoteSystemsData and lldpExtensions objectsbecause the information timeliness interval has expired."
			::= { sleBridgeBaseInfo 29 }

		
--  1.3.6.1.4.1.6296.9.8.1.1.41
		sleBridgeLldpLocalChassisIdSubtype OBJECT-TYPE
			SYNTAX INTEGER
				{
				chassisComponent(1),
				interfaceAlias(2),
				portComponent(3),
				macAddress(4),
				networkAddress(5),
				interfaceName(6),
				local(7)
				}
			MAX-ACCESS read-only
			STATUS current
			DESCRIPTION
				"The type of encoding used to identify the chassis associated with the local system."
			::= { sleBridgeBaseInfo 30 }

		
--  1.3.6.1.4.1.6296.9.8.1.1.42
		sleBridgeLldpLocalChassisId OBJECT-TYPE
			SYNTAX OCTET STRING (SIZE (1..255))
			MAX-ACCESS read-only
			STATUS current
			DESCRIPTION
				"The string value used to identify the chassis component associated with the local system."
			::= { sleBridgeBaseInfo 31 }

		
--  1.3.6.1.4.1.6296.9.8.1.1.43
		sleBridgeLldpLocalSysName OBJECT-TYPE
			SYNTAX OCTET STRING (SIZE (0..255))
			MAX-ACCESS read-only
			STATUS current
			DESCRIPTION
				"The string value used to identify the system name of the local system."
			::= { sleBridgeBaseInfo 32 }

		
--  1.3.6.1.4.1.6296.9.8.1.1.44
		sleBridgeLldpLocalSysDes OBJECT-TYPE
			SYNTAX OCTET STRING (SIZE (0..255))
			MAX-ACCESS read-write
			STATUS current
			DESCRIPTION
				"The string value used to identify the system description of the local system."
			::= { sleBridgeBaseInfo 33 }

		
--  1.3.6.1.4.1.6296.9.8.1.1.45
		sleBridgeLldpLocalSysCapSupported OBJECT-TYPE
			SYNTAX BITS
				{
				other(0),
				repeater(1),
				bridge(2),
				wlanAccessPoint(3),
				router(4),
				telephone(5),
				docsisCableDevice(6),
				stationOnly(7)
				}
			MAX-ACCESS read-only
			STATUS current
			DESCRIPTION
				"The bitmap value used to identify which system capabilities are supported on the local system."
			::= { sleBridgeBaseInfo 34 }

		
--  1.3.6.1.4.1.6296.9.8.1.1.46
		sleBridgeLldpLocalSysCapEnabled OBJECT-TYPE
			SYNTAX BITS
				{
				other(0),
				repeater(1),
				bridge(2),
				wlanAccessPoint(3),
				router(4),
				telephone(5),
				docsisCableDevice(6),
				stationOnly(7)
				}
			MAX-ACCESS read-only
			STATUS current
			DESCRIPTION
				"The bitmap value used to identify which system capabilities are enabled on the local system."
			::= { sleBridgeBaseInfo 35 }

		
--  1.3.6.1.4.1.6296.9.8.1.1.47
		sleBridgeStpActivity OBJECT-TYPE
			SYNTAX INTEGER
				{
				disabled(0),
				enabled(1)
				}
			MAX-ACCESS read-only
			STATUS current
			DESCRIPTION
				"The STP enabled/disabled status of the switch."
			::= { sleBridgeBaseInfo 36 }

		
		sleBridgeStpSelfLoop OBJECT-TYPE
			SYNTAX INTEGER
				{
				disable(0),
				enable(1)
				}
			MAX-ACCESS read-write
			STATUS current
			DESCRIPTION
				"The STP self loop
				0: disabled
				1: enabled
				"
			::= { sleBridgeBaseInfo 37 }

		
		sleBridgePvlanOnePromPortEnable OBJECT-TYPE
			SYNTAX INTEGER
				{
				disable(0),
				enable(1)
				}
			MAX-ACCESS read-write
			STATUS current
			DESCRIPTION
				"The value used to identify that a isolated port can be associated with only one or entire promiscuous ports on the local system."
			DEFVAL { 0 }
			::= { sleBridgeBaseInfo 38 }

		
		sleBridgeTcpSyncookie OBJECT-TYPE
			SYNTAX INTEGER
				{
				disable(0),
				enable(1)
				}
			MAX-ACCESS read-only
			STATUS current
			DESCRIPTION
				"The value permits only when transmitted cookies are returned after sending cookies with SYN"
			::= { sleBridgeBaseInfo 39 }

		
		sleBridgeTcpIgnoreRstUnknown OBJECT-TYPE
			SYNTAX INTEGER
				{
				disable(0),
				enable(1)
				}
			MAX-ACCESS read-only
			STATUS current
			DESCRIPTION
				"The value configures not to send the message that informs TCP connection cannot be done."
			::= { sleBridgeBaseInfo 40 }

		
		sleBridgeAutoInterfaceActivation OBJECT-TYPE
			SYNTAX INTEGER
				{
				enable(1),
				disable(2)
				}
			MAX-ACCESS read-only
			STATUS current
			DESCRIPTION
				"The value configures auto Interface activation.
				(supported only model 5924N)"
			::= { sleBridgeBaseInfo 41 }

		
		sleBridgeLoopDetectStatus OBJECT-TYPE
			SYNTAX INTEGER
				{
				enable(1),
				disable(2)
				}
			MAX-ACCESS read-only
			STATUS current
			DESCRIPTION
				"The global adminStatus of Loop-Detect."
			::= { sleBridgeBaseInfo 42 }

		
		sleBridgeLoopDetectPacketType OBJECT-TYPE
			SYNTAX INTEGER
				{
				laa(1),
				system(2)
				}
			MAX-ACCESS read-only
			STATUS current
			DESCRIPTION
				"The type of srcmac to be detected.
				1.laa : Locally Administered Address
				2.system : System MAC (default)"
			::= { sleBridgeBaseInfo 43 }

		
		sleBridgePvlanPromSelectMode OBJECT-TYPE
			SYNTAX INTEGER
				{
				normal(0),
				manual(1),
				stp(2),
				erp(3)
				}
			MAX-ACCESS read-only
			STATUS current
			DESCRIPTION
				"The value is used to indicate promiscuous ports selection mode:
				normal ?default
				manual ? by user
				stp ? by STP (not supported)
				erp ? by ERP
				"
			::= { sleBridgeBaseInfo 44 }

		
		sleBridgePvlanPromiscuousPorts OBJECT-TYPE
			SYNTAX OCTET STRING
			MAX-ACCESS read-only
			STATUS current
			DESCRIPTION
				"Bitmap of promiscuous ports on bridge."
			::= { sleBridgeBaseInfo 45 }

		
		sleBridgeInnerTagProtoId OBJECT-TYPE
			SYNTAX INTEGER
				{
				dtag8100(33024),
				dtag9100(37120)
				}
			MAX-ACCESS read-only
			STATUS current
			DESCRIPTION
				"programmable Inner Double Tag Protocol Identifier.
				It means innerTPID"
			::= { sleBridgeBaseInfo 46 }

		
		sleBridgeUnknownMcastBlockAllPorts OBJECT-TYPE
			SYNTAX INTEGER
				{
				enable(1),
				disable(2)
				}
			MAX-ACCESS read-only
			STATUS current
			DESCRIPTION
				"Unknown multicast block setting for all ports."
			::= { sleBridgeBaseInfo 47 }

		
		sleBridgeEcmpHashType OBJECT-TYPE
			SYNTAX INTEGER
				{
				sip(1),
				sipDip(2)
				}
			MAX-ACCESS read-only
			STATUS current
			DESCRIPTION
				"ECMP Hash Type"
			::= { sleBridgeBaseInfo 48 }

		
		sleBridgeTcpSynguard OBJECT-TYPE
			SYNTAX Integer32 (0..2147483647)
			MAX-ACCESS read-only
			STATUS current
			DESCRIPTION
				"The tcp-synguard bandwidth."
			::= { sleBridgeBaseInfo 49 }

		
		sleBridgeOuterTagProtoId OBJECT-TYPE
			SYNTAX INTEGER
				{
				dtag8100(33024),
				dtag9100(37120)
				}
			MAX-ACCESS read-only
			STATUS current
			DESCRIPTION
				"programmable outer Double Tag Protocol Identifier.
				  It means OutTPID"
			::= { sleBridgeBaseInfo 50 }

		
		sleBridgeMacAntiSpoofing OBJECT-TYPE
			SYNTAX INTEGER
				{
				enable(1),
				disable(2)
				}
			MAX-ACCESS read-only
			STATUS current
			DESCRIPTION
				"The protect uplink mac address"
			::= { sleBridgeBaseInfo 51 }

		
		sleBridgeMacReplace OBJECT-TYPE
			SYNTAX INTEGER
				{
				enable(1),
				disable(2)
				}
			MAX-ACCESS read-only
			STATUS current
			DESCRIPTION
				"The mac address replace mode"
			::= { sleBridgeBaseInfo 52 }

		
		sleBridgeStormControlBcast OBJECT-TYPE
			SYNTAX INTEGER (0 | 1..65535)
			MAX-ACCESS read-only
			STATUS current
			DESCRIPTION
				"The Storm Control Broadcast Configuration
				0: disable bcast
				"
			::= { sleBridgeBaseInfo 53 }

		
		sleBridgeStormControlDLF OBJECT-TYPE
			SYNTAX INTEGER (0 | 1..65535)
			MAX-ACCESS read-only
			STATUS current
			DESCRIPTION
				"The Storm Control DLF Configuration
				0: disable DLF
				"
			::= { sleBridgeBaseInfo 54 }

		
		sleBridgeStormControlMulticast OBJECT-TYPE
			SYNTAX INTEGER (0 | 1..65535)
			MAX-ACCESS read-only
			STATUS current
			DESCRIPTION
				"The Storm Control MultiCast Configuration
				0: disable multicast
				"
			::= { sleBridgeBaseInfo 55 }

		
		sleBridgeMacLearningMode OBJECT-TYPE
			SYNTAX INTEGER
				{
				cml(1),
				sml(2),
				cmlsml(3)
				}
			MAX-ACCESS read-only
			STATUS current
			DESCRIPTION
				"The MAC Learning Mode.
				1: cml
				2: sml
				3: cmlsml"
			::= { sleBridgeBaseInfo 56 }

		
		sleBridgeLagGlobalDistMode OBJECT-TYPE
			SYNTAX INTEGER
				{
				none(0),
				srcmac(1),
				dstmac(2),
				srcdstmac(3),
				srcip(4),
				dstip(5),
				srcdstip(6),
				srcdstl4(7),
				label(8)
				}
			MAX-ACCESS read-only
			STATUS current
			DESCRIPTION
				"The LAG global distmode."
			::= { sleBridgeBaseInfo 57 }

		
		sleBridgeMultiPortLlcfPortA OBJECT-TYPE
			SYNTAX OCTET STRING
			MAX-ACCESS read-only
			STATUS current
			DESCRIPTION
				"The Multi port LLCF - RAPS East/West Port."
			::= { sleBridgeBaseInfo 58 }

		
		sleBridgeMultiPortLlcfPortB OBJECT-TYPE
			SYNTAX OCTET STRING
			MAX-ACCESS read-only
			STATUS current
			DESCRIPTION
				"The Multi port LLCF - RAPS East/West Port."
			::= { sleBridgeBaseInfo 59 }

		
		sleBridgeMultiPortLlcfUpPortC OBJECT-TYPE
			SYNTAX OCTET STRING
			MAX-ACCESS read-only
			STATUS current
			DESCRIPTION
				"The Multi port LLCF - force down ports"
			::= { sleBridgeBaseInfo 60 }

		
		sleBridgeMultiPortLlcfDownPortC OBJECT-TYPE
			SYNTAX OCTET STRING
			MAX-ACCESS read-only
			STATUS current
			DESCRIPTION
				"The Multi port LLCF - force down ports"
			::= { sleBridgeBaseInfo 61 }

		
		sleBridgeMultiPortLlcfPortAStatus OBJECT-TYPE
			SYNTAX INTEGER
				{
				none(0),
				loc(1),
				disable(2),
				forcedToDown(3)
				}
			MAX-ACCESS read-only
			STATUS current
			DESCRIPTION
				"The Multi port LLCF port's status."
			::= { sleBridgeBaseInfo 62 }

		
		sleBridgeMultiPortLlcfPortBStatus OBJECT-TYPE
			SYNTAX INTEGER
				{
				none(0),
				loc(1),
				disable(2),
				forcedToDown(3)
				}
			MAX-ACCESS read-only
			STATUS current
			DESCRIPTION
				"The Multi port LLCF port's status."
			::= { sleBridgeBaseInfo 63 }

		
		sleBridgeMultiPortLlcfUpPortCStatus OBJECT-TYPE
			SYNTAX INTEGER
				{
				none(0),
				loc(1),
				disable(2),
				forcedToDown(3)
				}
			MAX-ACCESS read-only
			STATUS current
			DESCRIPTION
				"The Multi port LLCF port's status."
			::= { sleBridgeBaseInfo 64 }

		
		sleBridgeMultiPortLlcfDownPortCStatus OBJECT-TYPE
			SYNTAX INTEGER
				{
				none(0),
				loc(1),
				disable(2),
				forcedToDown(3)
				}
			MAX-ACCESS read-only
			STATUS current
			DESCRIPTION
				"The Multi port LLCF port's status."
			::= { sleBridgeBaseInfo 65 }

		
		sleBridgeMultiPortLlcfTimer OBJECT-TYPE
			SYNTAX Integer32 (1000..10000)
			MAX-ACCESS read-only
			STATUS current
			DESCRIPTION
				"The LLCF's checking interval. 1000~10000ms
				
				(default: 2500ms)"
			::= { sleBridgeBaseInfo 66 }

		
--  1.3.6.1.4.1.6296.9.8.1.2
		sleBridgeBaseControl OBJECT IDENTIFIER ::= { sleBridgeBase 2 }

		
--   1.3.6.1.4.1.6296.9.8.1.2.1
-- 1.3.6.1.4.1.6296.101.3.1.2.1
		sleBridgeControlRequest OBJECT-TYPE
			SYNTAX INTEGER
				{
				setLacpProfile(1),
				setDoubleTagProtoId(2),
				setMirrorProfile(3),
				setMaxLearnPerUnit(4),
				setFdbAgeingTime(5),
				setStackProfile(6),
				setLldpProfile(7),
				setStpProfile(8),
				setTcpSyncookie(9),
				setTcpIgnoreRstUnknown(10),
				setAutoInterfaceActivation(11),
				setLoopDetectProfile(12),
				setPvlanPromSelectMode(13),
				setInnerTagProtoId(14),
				setUnknownMcastBlockAllPorts(15),
				setEcmpHashType(16),
				setTcpSynguard(17),
				setOuterTagProtoId(18),
				setMacAntiSpoofing(19),
				setMacReplace(20),
				setStormControl(21),
				setMacLearningMode(22),
				setLagGlobalDistMode(23),
				setMultiPortLlcf(24),
				delMultiPortLlcf(25),
				setMultiPortLlcfTimer(26)
				}
			MAX-ACCESS read-write
			STATUS current
			DESCRIPTION
				"The request of a user command"
			::= { sleBridgeBaseControl 1 }

		
--  1.3.6.1.4.1.6296.9.8.1.2.2
		sleBridgeControlStatus OBJECT-TYPE
			SYNTAX SleControlStatusType
			MAX-ACCESS read-only
			STATUS current
			DESCRIPTION
				" The status of user command"
			::= { sleBridgeBaseControl 2 }

		
--  1.3.6.1.4.1.6296.9.8.1.2.3
		sleBridgeControlTimer OBJECT-TYPE
			SYNTAX Gauge32
			MAX-ACCESS read-write
			STATUS current
			DESCRIPTION
				" The maximum time for the manager for a long running user command"
			::= { sleBridgeBaseControl 3 }

		
--  1.3.6.1.4.1.6296.9.8.1.2.5
		sleBridgeControlTimeStamp OBJECT-TYPE
			SYNTAX TimeTicks
			MAX-ACCESS read-only
			STATUS current
			DESCRIPTION
				" The time stamp of the last command(end of command)"
			::= { sleBridgeBaseControl 4 }

		
--  1.3.6.1.4.1.6296.9.8.1.2.4
		sleBridgeControlReqResult OBJECT-TYPE
			SYNTAX SleControlRequestResultType
			MAX-ACCESS read-only
			STATUS current
			DESCRIPTION
				"The result of the last user command"
			::= { sleBridgeBaseControl 5 }

		
--  1.3.6.1.4.1.6296.9.8.1.2.6
		sleBridgeControlLacpActivity OBJECT-TYPE
			SYNTAX INTEGER
				{
				disabled(0),
				enabled(1)
				}
			MAX-ACCESS read-write
			STATUS current
			DESCRIPTION
				" The LACP enabled/disabled status of the switch"
			::= { sleBridgeBaseControl 6 }

		
--  1.3.6.1.4.1.6296.9.8.1.2.7
		sleBridgeControlLacpPriority OBJECT-TYPE
			SYNTAX INTEGER (1..65535)
			MAX-ACCESS read-write
			STATUS current
			DESCRIPTION
				" The priority assigned to the Actor System"
			::= { sleBridgeBaseControl 7 }

		
--  1.3.6.1.4.1.6296.9.8.1.2.8
		sleBridgeControlDoubleTagProtoId OBJECT-TYPE
			SYNTAX Integer32
			MAX-ACCESS read-write
			STATUS current
			DESCRIPTION
				" programmable Double Tag Protocol Identifier.
				It means outerTPID.
				"
			::= { sleBridgeBaseControl 8 }

		
--  1.3.6.1.4.1.6296.9.8.1.2.18
		sleBridgeControlMirrorMode OBJECT-TYPE
			SYNTAX INTEGER
				{
				disabled(0),
				enabled(1)
				}
			MAX-ACCESS read-write
			STATUS current
			DESCRIPTION
				" Mirror mode of bridge"
			::= { sleBridgeBaseControl 9 }

		
--  1.3.6.1.4.1.6296.9.8.1.2.19
		sleBridgeControlMirrorMonitorPortId OBJECT-TYPE
			SYNTAX INTEGER (1..255)
			MAX-ACCESS read-write
			STATUS current
			DESCRIPTION
				"Mirroring port ID
				1-254: physical port ID
				255: mirror to cpu"
			::= { sleBridgeBaseControl 10 }

		
		sleBridgeControlMaxLearnPerUnit OBJECT-TYPE
			SYNTAX INTEGER (-1..2147483647)
			MAX-ACCESS read-write
			STATUS current
			DESCRIPTION
				"Limit maximum number of MAC addresses learning 
				newly per unit time(one second) on a bridge.
				(0: nothing learned, -l: unlimited.)"
			::= { sleBridgeBaseControl 11 }

		
--  1.3.6.1.4.1.6296.9.8.1.2.20
		sleBridgeControlFdbAgeingTime OBJECT-TYPE
			SYNTAX Unsigned32 (10..21474830)
			MAX-ACCESS read-write
			STATUS current
			DESCRIPTION
				"The timeout period in seconds for aging out
				dynamically learned forwarding information."
			DEFVAL { 300 }
			::= { sleBridgeBaseControl 12 }

		
--  1.3.6.1.4.1.6296.9.8.1.2.21
		sleBridgeControlStackMode OBJECT-TYPE
			SYNTAX INTEGER
				{
				disable(0),
				master(1),
				slave(2)
				}
			MAX-ACCESS read-write
			STATUS current
			DESCRIPTION
				"Stack status of device."
			::= { sleBridgeBaseControl 13 }

		
--  1.3.6.1.4.1.6296.9.8.1.2.22
		sleBridgeControlStackDeviceName OBJECT-TYPE
			SYNTAX OCTET STRING (SIZE (0..8))
			MAX-ACCESS read-write
			STATUS current
			DESCRIPTION
				"Device name of stack device."
			::= { sleBridgeBaseControl 14 }

		
--  1.3.6.1.4.1.6296.9.8.1.2.23
		sleBridgeControlLldpMessageTxInterval OBJECT-TYPE
			SYNTAX INTEGER (5..32767)
			MAX-ACCESS read-write
			STATUS current
			DESCRIPTION
				" The interval at which LLDP frames are transmitted on behalf of this LLDP agent."
			::= { sleBridgeBaseControl 15 }

		
--  1.3.6.1.4.1.6296.9.8.1.2.24
		sleBridgeControlLldpTxHoldMultiplier OBJECT-TYPE
			SYNTAX INTEGER (2..10)
			MAX-ACCESS read-write
			STATUS current
			DESCRIPTION
				"The time-to-live value expressed as a multiple of the sleBridgeLldpMessageTxInterval object."
			::= { sleBridgeBaseControl 16 }

		
--  1.3.6.1.4.1.6296.9.8.1.2.25
		sleBridgeControlLldpReinitDelay OBJECT-TYPE
			SYNTAX INTEGER (1..10)
			MAX-ACCESS read-write
			STATUS current
			DESCRIPTION
				" Delay (in units of seconds) from when lldpPortConfigAdminStatus object of a particular port  becomes 'disabled' until re-initialization will be attempted."
			::= { sleBridgeBaseControl 17 }

		
--  1.3.6.1.4.1.6296.9.8.1.2.26
		sleBridgeControlLldpTxDelay OBJECT-TYPE
			SYNTAX INTEGER (1..8192)
			MAX-ACCESS read-write
			STATUS current
			DESCRIPTION
				"Delay (in units of seconds) between successive LLDP frame transmissions initiated by value/status changes in the LLDP local systems MIB."
			::= { sleBridgeBaseControl 18 }

		
--  1.3.6.1.4.1.6296.9.8.1.2.27
		sleBridgeControlLldpNotificationInterval OBJECT-TYPE
			SYNTAX INTEGER (5..3600)
			MAX-ACCESS read-write
			STATUS current
			DESCRIPTION
				" The agent must not generate more than one lldpRemTablesChangenotification-event in the indicated period."
			::= { sleBridgeBaseControl 19 }

		
--  1.3.6.1.4.1.6296.9.8.1.2.29
		sleBridgeControlStpActivity OBJECT-TYPE
			SYNTAX INTEGER
				{
				disabled(0),
				enabled(1)
				}
			MAX-ACCESS read-write
			STATUS current
			DESCRIPTION
				" The STP enabled/disabled status of the switch."
			::= { sleBridgeBaseControl 20 }

		
		sleBridgeControlStpSelfLoop OBJECT-TYPE
			SYNTAX INTEGER
				{
				disable(0),
				enable(1)
				}
			MAX-ACCESS read-write
			STATUS current
			DESCRIPTION
				"The STP self loop
				0: disabled
				1: enabled"
			::= { sleBridgeBaseControl 21 }

		
		sleBridgeControlTcpSyncookie OBJECT-TYPE
			SYNTAX INTEGER
				{
				disable(0),
				enable(1)
				}
			MAX-ACCESS read-write
			STATUS current
			DESCRIPTION
				"The value permits only when transmitted cookies are returned after sending cookies with SYN"
			::= { sleBridgeBaseControl 22 }

		
		sleBridgeControlTcpIgnoreRstUnknown OBJECT-TYPE
			SYNTAX INTEGER
				{
				disable(0),
				enable(1)
				}
			MAX-ACCESS read-write
			STATUS current
			DESCRIPTION
				"The value configures not to send the message that informs TCP connection cannot be done."
			::= { sleBridgeBaseControl 23 }

		
		sleBridgeControlAutoInterfaceActivation OBJECT-TYPE
			SYNTAX INTEGER
				{
				enable(1),
				disable(2)
				}
			MAX-ACCESS read-write
			STATUS current
			DESCRIPTION
				"The value configures auto Interface activation.
				(supported only model 5924N)"
			::= { sleBridgeBaseControl 24 }

		
		sleBridgeControlLoopDetectStatus OBJECT-TYPE
			SYNTAX INTEGER
				{
				enable(1),
				disable(2)
				}
			MAX-ACCESS read-write
			STATUS current
			DESCRIPTION
				"The global adminStatus of Loop-Detect."
			::= { sleBridgeBaseControl 25 }

		
		sleBridgeControlLoopDetectPacketType OBJECT-TYPE
			SYNTAX INTEGER
				{
				laa(1),
				system(2)
				}
			MAX-ACCESS read-write
			STATUS current
			DESCRIPTION
				"The type of srcmac to be detected.
				1.laa : Locally Administered Address
				2.system : System MAC (default)"
			::= { sleBridgeBaseControl 26 }

		
		sleBridgeControlPvlanPromSelectMode OBJECT-TYPE
			SYNTAX INTEGER
				{
				normal(0),
				manual(1),
				stp(2),
				erp(3)
				}
			MAX-ACCESS read-write
			STATUS current
			DESCRIPTION
				"The value is used to indicate promiscuous ports selection mode:
				normal ?default
				manual ? by user
				stp ? by STP (not supported)
				erp ? by ERP"
			::= { sleBridgeBaseControl 27 }

		
		sleBridgeControlPvlanPromiscuousPorts OBJECT-TYPE
			SYNTAX OCTET STRING
			MAX-ACCESS read-write
			STATUS current
			DESCRIPTION
				"Valid if only if sleBridgeControlPvlanPromSelectMode is not manual.
				If sleBridgePvlanOnePromPortEnable is enabled, then it can only indicate one port or none."
			::= { sleBridgeBaseControl 28 }

		
		sleBridgeControlInnerTagProtoId OBJECT-TYPE
			SYNTAX INTEGER
				{
				dtag8100(33024),
				dtag9100(37120)
				}
			MAX-ACCESS read-write
			STATUS current
			DESCRIPTION
				"programmable Inner Double Tag Protocol Identifier. It means innerTPID."
			::= { sleBridgeBaseControl 29 }

		
		sleBridgeControlUnknownMcastBlockAllPorts OBJECT-TYPE
			SYNTAX INTEGER
				{
				enable(1),
				disable(2)
				}
			MAX-ACCESS read-write
			STATUS current
			DESCRIPTION
				"Unknown multicast block setting for all ports."
			::= { sleBridgeBaseControl 30 }

		
		sleBridgeControlEcmpHashType OBJECT-TYPE
			SYNTAX INTEGER
				{
				sip(1),
				sipDip(2)
				}
			MAX-ACCESS read-write
			STATUS current
			DESCRIPTION
				"ECMP Hash Type
				"
			::= { sleBridgeBaseControl 31 }

		
		sleBridgeControlTcpSynguard OBJECT-TYPE
			SYNTAX Integer32 (0..2147483647)
			MAX-ACCESS read-write
			STATUS current
			DESCRIPTION
				"The tcp-synguard bandwidth."
			::= { sleBridgeBaseControl 32 }

		
		sleBridgeControlOuterTagProtoId OBJECT-TYPE
			SYNTAX INTEGER
				{
				dtag8100(33024),
				dtag9100(37120)
				}
			MAX-ACCESS read-write
			STATUS current
			DESCRIPTION
				"programmable outer Double Tag Protocol Identifier.
				  It means OutTPID"
			::= { sleBridgeBaseControl 33 }

		
		sleBridgeControlMacAntiSpoofing OBJECT-TYPE
			SYNTAX INTEGER
				{
				enable(1),
				disable(2)
				}
			MAX-ACCESS read-write
			STATUS current
			DESCRIPTION
				"The protect uplink mac address
				2011/01/20 V5924CR supports."
			::= { sleBridgeBaseControl 34 }

		
		sleBridgeControlMacReplace OBJECT-TYPE
			SYNTAX INTEGER
				{
				enable(1),
				disable(2)
				}
			MAX-ACCESS read-write
			STATUS current
			DESCRIPTION
				"The mac address replace mode
				2011/01/20 V5924CR supports."
			::= { sleBridgeBaseControl 35 }

		
		sleBridgeControlStormControlBcast OBJECT-TYPE
			SYNTAX INTEGER (0 | 1..65535)
			MAX-ACCESS read-write
			STATUS current
			DESCRIPTION
				"The Storm Control Broadcast Configuration
				0: disable bcast
				"
			::= { sleBridgeBaseControl 36 }

		
		sleBridgeControlStormControlDLF OBJECT-TYPE
			SYNTAX INTEGER (0 | 1..65535)
			MAX-ACCESS read-write
			STATUS current
			DESCRIPTION
				"The Storm Control DLF Configuration
				0: disable DLF
				"
			::= { sleBridgeBaseControl 37 }

		
		sleBridgeControlStormControlMulticast OBJECT-TYPE
			SYNTAX INTEGER (0 | 1..65535)
			MAX-ACCESS read-only
			STATUS current
			DESCRIPTION
				"The Storm Control Multicast Configuration
				0: disable multicast
				"
			::= { sleBridgeBaseControl 38 }

		
		sleBridgeControlMacLearningMode OBJECT-TYPE
			SYNTAX INTEGER
				{
				cml(1),
				sml(2),
				cmlsml(3)
				}
			MAX-ACCESS read-write
			STATUS current
			DESCRIPTION
				"The MAC Learning Mode.
				1: cml
				2: sml
				3: cmlsml"
			::= { sleBridgeBaseControl 39 }

		
		sleBridgeControlLagGlobalDistMode OBJECT-TYPE
			SYNTAX INTEGER
				{
				none(0),
				srcmac(1),
				dstmac(2),
				srcdstmac(3),
				srcip(4),
				dstip(5),
				srcdstip(6),
				srcdstl4(7),
				label(8)
				}
			MAX-ACCESS read-write
			STATUS current
			DESCRIPTION
				"The LAG global distmode."
			::= { sleBridgeBaseControl 40 }

		
		sleBridgeControlMultiPortLlcfPortA OBJECT-TYPE
			SYNTAX OCTET STRING
			MAX-ACCESS read-write
			STATUS current
			DESCRIPTION
				"The Multi port LLCF - RAPS East/West Port."
			::= { sleBridgeBaseControl 41 }

		
		sleBridgeControlMultiPortLlcfPortB OBJECT-TYPE
			SYNTAX OCTET STRING
			MAX-ACCESS read-write
			STATUS current
			DESCRIPTION
				"The Multi port LLCF - RAPS East/West Port."
			::= { sleBridgeBaseControl 42 }

		
		sleBridgeControlMultiPortLlcfPortC OBJECT-TYPE
			SYNTAX OCTET STRING
			MAX-ACCESS read-write
			STATUS current
			DESCRIPTION
				"The Multi port LLCF - force down ports"
			::= { sleBridgeBaseControl 43 }

		
		sleBridgeControlMultiPortLlcfTimer OBJECT-TYPE
			SYNTAX Integer32 (-1 | 1000..10000)
			MAX-ACCESS read-write
			STATUS current
			DESCRIPTION
				"The LLCF's checking interval. 1000~10000ms (default:2500ms)
				clear set value is -1."
			::= { sleBridgeBaseControl 44 }

		
--  1.3.6.1.4.1.6296.9.8.1.4
		sleBridgeBaseNotification OBJECT IDENTIFIER ::= { sleBridgeBase 3 }

		
--  1.3.6.1.4.1.6296.9.8.1.4.1
		sleBridgeLacpProfileChanged NOTIFICATION-TYPE
			OBJECTS { sleBridgeLacpActivity, sleBridgeLacpPriority, sleBridgeControlRequest, sleBridgeControlTimeStamp, sleBridgeControlReqResult
				 }
			STATUS current
			DESCRIPTION 
				" "
			::= { sleBridgeBaseNotification 1 }

		
--  1.3.6.1.4.1.6296.9.8.1.4.2
		sleBridgeDoubleTagProtoIdChanged NOTIFICATION-TYPE
			OBJECTS { sleBridgeDoubleTagProtoId, sleBridgeControlRequest, sleBridgeControlTimeStamp, sleBridgeControlReqResult }
			STATUS current
			DESCRIPTION 
				" "
			::= { sleBridgeBaseNotification 2 }

		
--  1.3.6.1.4.1.6296.9.8.1.4.5
		sleBridgeMirrorProfileChanged NOTIFICATION-TYPE
			OBJECTS { sleBridgeMirrorMode, sleBridgeMirrorMonitorPortId, sleBridgeControlRequest, sleBridgeControlTimeStamp, sleBridgeControlReqResult
				 }
			STATUS current
			DESCRIPTION 
				" "
			::= { sleBridgeBaseNotification 3 }

		
		sleBridgeMaxLearnPerUnitChanged NOTIFICATION-TYPE
			OBJECTS { sleBridgeControlRequest, sleBridgeControlTimeStamp, sleBridgeControlReqResult, sleBridgeMaxLearnPerUnit }
			STATUS current
			DESCRIPTION 
				"Description."
			::= { sleBridgeBaseNotification 4 }

		
--  1.3.6.1.4.1.6296.9.8.1.4.6
		sleBridgeFdbAgeingTimeChanged NOTIFICATION-TYPE
			OBJECTS { sleBridgeFdbAgeingTime, sleBridgeControlRequest, sleBridgeControlTimeStamp, sleBridgeControlReqResult }
			STATUS current
			DESCRIPTION 
				"Changed Fdb ageding time."
			::= { sleBridgeBaseNotification 5 }

		
--  1.3.6.1.4.1.6296.9.8.1.4.7
		sleBridgeStackProfileChanged NOTIFICATION-TYPE
			OBJECTS { sleBridgeStackMode, sleBridgeStackDeviceName, sleBridgeControlRequest, sleBridgeControlTimeStamp, sleBridgeControlReqResult
				 }
			STATUS current
			DESCRIPTION 
				"Changed Stack device's profile."
			::= { sleBridgeBaseNotification 6 }

		
--  1.3.6.1.4.1.6296.9.8.1.4.8
		sleBridgeLldpProfileChanged NOTIFICATION-TYPE
			OBJECTS { sleBridgeLldpMessageTxInterval, sleBridgeLldpTxHoldMultiplier, sleBridgeLldpReinitDelay, sleBridgeLldpTxDelay, sleBridgeLldpNotificationInterval, 
				sleBridgeControlRequest, sleBridgeControlTimeStamp, sleBridgeControlReqResult }
			STATUS current
			DESCRIPTION 
				" "
			::= { sleBridgeBaseNotification 7 }

		
--  1.3.6.1.4.1.6296.9.8.1.4.9
		sleBridgeStpProfileChanged NOTIFICATION-TYPE
			OBJECTS { sleBridgeControlRequest, sleBridgeControlReqResult, sleBridgeControlTimeStamp, sleBridgeStpActivity, sleBridgeStpSelfLoop
				 }
			STATUS current
			DESCRIPTION 
				" "
			::= { sleBridgeBaseNotification 8 }

		
		sleBridgeTcpSyncookieChanged NOTIFICATION-TYPE
			OBJECTS { sleBridgeControlRequest, sleBridgeControlTimeStamp, sleBridgeControlReqResult, sleBridgeTcpSyncookie }
			STATUS current
			DESCRIPTION 
				"Description."
			::= { sleBridgeBaseNotification 9 }

		
		sleBridgeTcpIgnoreRstUnknownChanged NOTIFICATION-TYPE
			OBJECTS { sleBridgeControlRequest, sleBridgeControlTimeStamp, sleBridgeControlReqResult, sleBridgeTcpIgnoreRstUnknown }
			STATUS current
			DESCRIPTION 
				"Description."
			::= { sleBridgeBaseNotification 10 }

		
		sleBridgeAutoInterfaceActivationChanged NOTIFICATION-TYPE
			OBJECTS { sleBridgeControlRequest, sleBridgeControlTimeStamp, sleBridgeControlReqResult, sleBridgeAutoInterfaceActivation }
			STATUS current
			DESCRIPTION 
				"Description."
			::= { sleBridgeBaseNotification 11 }

		
		sleBridgeLoopDetectProfileChanged NOTIFICATION-TYPE
			OBJECTS { sleBridgeControlRequest, sleBridgeControlTimeStamp, sleBridgeControlReqResult, sleBridgeLoopDetectStatus, sleBridgeLoopDetectPacketType
				 }
			STATUS current
			DESCRIPTION 
				"Description."
			::= { sleBridgeBaseNotification 12 }

		
		sleBridgePvlanPormSelectModeChanged NOTIFICATION-TYPE
			OBJECTS { sleBridgeControlRequest, sleBridgeControlTimeStamp, sleBridgeControlReqResult, sleBridgeControlPvlanPromSelectMode, sleBridgeControlPvlanPromiscuousPorts
				 }
			STATUS current
			DESCRIPTION 
				"Description."
			::= { sleBridgeBaseNotification 13 }

		
		sleBridgeInnerTagProtoIdChanged NOTIFICATION-TYPE
			OBJECTS { sleBridgeControlRequest, sleBridgeControlTimeStamp, sleBridgeControlReqResult, sleBridgeControlInnerTagProtoId }
			STATUS current
			DESCRIPTION 
				"Description."
			::= { sleBridgeBaseNotification 14 }

		
		sleBridgeUnknownMcastBlockAllPortsChanged NOTIFICATION-TYPE
			OBJECTS { sleBridgeControlRequest, sleBridgeControlTimeStamp, sleBridgeControlReqResult, sleBridgeControlUnknownMcastBlockAllPorts }
			STATUS current
			DESCRIPTION 
				"Description."
			::= { sleBridgeBaseNotification 15 }

		
		sleBridgeEcmpHashTypeChanged NOTIFICATION-TYPE
			OBJECTS { sleBridgeControlRequest, sleBridgeControlTimeStamp, sleBridgeControlReqResult, sleBridgeControlEcmpHashType }
			STATUS current
			DESCRIPTION 
				"Description."
			::= { sleBridgeBaseNotification 16 }

		
		sleBridgeTcpSynguardChanged NOTIFICATION-TYPE
			OBJECTS { sleBridgeTcpSynguard, sleBridgeControlRequest, sleBridgeControlTimeStamp, sleBridgeControlReqResult }
			STATUS current
			DESCRIPTION 
				"Description."
			::= { sleBridgeBaseNotification 17 }

		
		sleBridgeOuterTagProtoIdChanged NOTIFICATION-TYPE
			OBJECTS { sleBridgeControlRequest, sleBridgeControlTimeStamp, sleBridgeControlReqResult, sleBridgeControlOuterTagProtoId }
			STATUS current
			DESCRIPTION 
				"sleBridgeControlOuterTagProtoId"
			::= { sleBridgeBaseNotification 18 }

		
		sleBridgeMacAntiSpoofingChanged NOTIFICATION-TYPE
			OBJECTS { sleBridgeControlRequest, sleBridgeControlTimeStamp, sleBridgeControlReqResult, sleBridgeControlMacAntiSpoofing }
			STATUS current
			DESCRIPTION 
				"Description."
			::= { sleBridgeBaseNotification 19 }

		
		sleBridgeMacReplaceChanged NOTIFICATION-TYPE
			OBJECTS { sleBridgeControlRequest, sleBridgeControlTimeStamp, sleBridgeControlReqResult, sleBridgeControlMacReplace }
			STATUS current
			DESCRIPTION 
				"Description."
			::= { sleBridgeBaseNotification 20 }

		
		sleBridgeStormControlChanged NOTIFICATION-TYPE
			OBJECTS { sleBridgeControlRequest, sleBridgeControlTimeStamp, sleBridgeControlReqResult, sleBridgePortNum, sleBridgeControlStormControlBcast, 
				sleBridgeControlStormControlDLF, sleBridgeControlStormControlMulticast }
			STATUS current
			DESCRIPTION 
				"Description."
			::= { sleBridgeBaseNotification 21 }

		
		sleBridgeMacLearningModeChanged NOTIFICATION-TYPE
			OBJECTS { sleBridgeControlRequest, sleBridgeControlTimeStamp, sleBridgeControlReqResult, sleBridgeControlMacLearningMode }
			STATUS current
			DESCRIPTION 
				"Description."
			::= { sleBridgeBaseNotification 22 }

		
		sleBridgeLagGlobalDistModeChanged NOTIFICATION-TYPE
			OBJECTS { sleBridgeControlRequest, sleBridgeControlTimeStamp, sleBridgeControlReqResult, sleBridgeControlLagGlobalDistMode }
			STATUS current
			DESCRIPTION 
				"setLagGlobalDistMode"
			::= { sleBridgeBaseNotification 23 }

		
		sleBridgeMultiPortLlcfChanged NOTIFICATION-TYPE
			OBJECTS { sleBridgeControlRequest, sleBridgeControlTimeStamp, sleBridgeControlReqResult, sleBridgeControlMultiPortLlcfPortA, sleBridgeControlMultiPortLlcfPortB, 
				sleBridgeControlMultiPortLlcfPortC }
			STATUS current
			DESCRIPTION 
				"setMultiPortLlcf "
			::= { sleBridgeBaseNotification 24 }

		
		sleBridgeMultiPortLlcfDeleted NOTIFICATION-TYPE
			OBJECTS { sleBridgeControlRequest, sleBridgeControlTimeStamp, sleBridgeControlReqResult }
			STATUS current
			DESCRIPTION 
				"delMultiPortLlcf "
			::= { sleBridgeBaseNotification 25 }

		
		sleBridgeMultiPortLlcfTimerChanged NOTIFICATION-TYPE
			OBJECTS { sleBridgeControlRequest, sleBridgeControlTimeStamp, sleBridgeControlReqResult, sleBridgeControlMultiPortLlcfTimer }
			STATUS current
			DESCRIPTION 
				"setMultiPortLlcfTimer "
			::= { sleBridgeBaseNotification 26 }

		
--  			::= { sle 4 }
-- 
-- Node definitions
-- 
-- 1.3.6.1.4.1.6296.9.8.2
		sleBridgePort OBJECT IDENTIFIER ::= { sleBridge 2 }

		
--  1.3.6.1.4.1.6296.9.8.2.1
		sleBridgePortTable OBJECT-TYPE
			SYNTAX SEQUENCE OF SleBridgePortEntry
			MAX-ACCESS not-accessible
			STATUS current
			DESCRIPTION
				"Bridge Port Table"
			::= { sleBridgePort 1 }

		
--  1.3.6.1.4.1.6296.9.8.2.1.1
		sleBridgePortEntry OBJECT-TYPE
			SYNTAX SleBridgePortEntry
			MAX-ACCESS not-accessible
			STATUS current
			DESCRIPTION
				"Bridge Port Entry
				key: sleBridgePortIndex"
			INDEX { sleBridgePortIndex }
			::= { sleBridgePortTable 1 }

		
		SleBridgePortEntry ::=
			SEQUENCE { 
				sleBridgePortIndex
					INTEGER,
				sleBridgePortIfIndex
					INTEGER,
				sleBridgePortPVid
					INTEGER,
				sleBridgePortMaxHosts
					INTEGER,
				sleBridgePortCurrentHosts
					INTEGER,
				sleBridgePortMaxLearnPerUnit
					INTEGER,
				sleBridgePortMACFilterPermission
					INTEGER,
				sleBridgePortIngMirrorStatus
					INTEGER,
				sleBridgePortEgMirrorStatus
					INTEGER,
				sleBridgePortBcastThreshold
					INTEGER,
				sleBridgePortMcastThreshold
					INTEGER,
				sleBridgePortDlfThreshold
					INTEGER,
				sleBridgePortQinQStatus
					INTEGER,
				sleBridgePortAdminLinktype
					INTEGER,
				sleBridgePortAdminEdgemode
					INTEGER,
				sleBridgePortOperLinktype
					INTEGER,
				sleBridgePortOperEdgemode
					INTEGER,
				sleBridgePortStpBpduFilter
					INTEGER,
				sleBridgePortPvlanIsolatedStatus
					INTEGER,
				sleBridgePortPvlanPromPorts
					OCTET STRING,
				sleBridgePortDhcpFilterServer
					INTEGER,
				sleBridgePortLoopDetectStatus
					INTEGER,
				sleBridgePortLoopDetectBlock
					INTEGER,
				sleBridgePortLoopDetectPeriod
					INTEGER,
				sleBridgePortLoopDetectTimer
					INTEGER,
				sleBridgePortLoopDetectBlockStatus
					INTEGER,
				sleBridgePortNetBIOSFilter
					INTEGER,
				sleBridgePortPushInnertag
					INTEGER,
				sleBridgePortPopInnertag
					INTEGER,
				sleBridgePortInnertag
					INTEGER,
				sleBridgePortPriority
					INTEGER,
				sleBridgePortInner2outerPri
					INTEGER,
				sleBridgePortInner2outerVid
					INTEGER,
				sleBridgePortLinkUpCnt
					INTEGER,
				sleBridgePortLinkDownCnt
					INTEGER,
				sleBridgePortLinkUpTime
					Counter64,
				sleBridgePortElapsedTimeAfterClearStats
					Counter64,
				sleBridgePortMACLearningStatus
					INTEGER,
				sleBridgePortPortBridgeStatus
					INTEGER,
				sleBridgePortUnknownMcastBlock
					INTEGER,
				sleBridgePortDescription
					OCTET STRING,
				sleBridgePortHoldTime
					Integer32,
				sleBridgePortMacAntiSpoofing
					TruthValue,
				sleBridgePortSwitchType
					INTEGER,
				sleBridgePortSwitchState
					INTEGER,
				sleBridgePortSwitchMode
					INTEGER,
				sleBridgePortSwitchSubMode
					INTEGER,
				sleBridgePortSwitchDefaultVlan
					Integer32,
				sleBridgePortSwitchIngressFilter
					INTEGER,
				sleBridgePortSwitchAccFrameType
					BITS,
				sleBridgePortSwitchNativeVid
					Integer32,
				sleBridgePortSwitchAllowedVlan
					OCTET STRING,
				sleBridgePortSwitchAllowedVlanEtag
					OCTET STRING,
				sleBridgePortSwitchChannelType
					INTEGER,
				sleBridgePortSwitchStaticChannelGroup
					OCTET STRING,
				sleBridgePortSwitchChannelLoadbalance
					INTEGER
			 }

--  1.3.6.1.4.1.6296.9.8.2.1.1.1
		sleBridgePortIndex OBJECT-TYPE
			SYNTAX INTEGER (1..65535)
			MAX-ACCESS read-only
			STATUS current
			DESCRIPTION
				"Same as ifIndex (for all ifTable entries),
				additionally aggregation group index values available."
			::= { sleBridgePortEntry 1 }

		
--  1.3.6.1.4.1.6296.9.8.2.1.1.1
		sleBridgePortIfIndex OBJECT-TYPE
			SYNTAX INTEGER (1..4094)
			MAX-ACCESS read-only
			STATUS current
			DESCRIPTION
				"Bridge Interface Index."
			::= { sleBridgePortEntry 2 }

		
--  1.3.6.1.4.1.6296.9.8.2.1.1.2
		sleBridgePortPVid OBJECT-TYPE
			SYNTAX INTEGER (1..4094)
			MAX-ACCESS read-only
			STATUS current
			DESCRIPTION
				"The PVID of port. 
				Taken if no other rule given for VLAN association. 
				If aggregated: only for group."
			::= { sleBridgePortEntry 3 }

		
--  1.3.6.1.4.1.6296.9.8.2.1.1.3
		sleBridgePortMaxHosts OBJECT-TYPE
			SYNTAX INTEGER (0..2147483647)
			MAX-ACCESS read-only
			STATUS current
			DESCRIPTION
				"The maximum number of hosts allowed. 
				Aggregation group available. Value 0 is allowed. 
				Default value is -1: it means unlimited. "
			::= { sleBridgePortEntry 4 }

		
--  1.3.6.1.4.1.6296.9.8.2.1.1.4
		sleBridgePortCurrentHosts OBJECT-TYPE
			SYNTAX INTEGER (0..65535)
			MAX-ACCESS read-only
			STATUS current
			DESCRIPTION
				"The number hosts which is allowed to be used. 
				Aggregation group available."
			::= { sleBridgePortEntry 5 }

		
		sleBridgePortMaxLearnPerUnit OBJECT-TYPE
			SYNTAX INTEGER (-1..2147483647)
			MAX-ACCESS read-only
			STATUS current
			DESCRIPTION
				"Limit maximum number of MAC addresses learning 
				newly per unit time(one second) on a port.
				(0: nothing learned, -l: unlimited.)"
			::= { sleBridgePortEntry 6 }

		
--  1.3.6.1.4.1.6296.9.8.2.1.1.5
		sleBridgePortMACFilterPermission OBJECT-TYPE
			SYNTAX INTEGER
				{
				deny(0),
				permit(1)
				}
			MAX-ACCESS read-only
			STATUS current
			DESCRIPTION
				"The default permission for mac filtering. 
				Valid only for physical ports,
				use values from MFDB Table. "
			DEFVAL { 1 }
			::= { sleBridgePortEntry 7 }

		
--  1.3.6.1.4.1.6296.9.8.2.1.1.6
		sleBridgePortIngMirrorStatus OBJECT-TYPE
			SYNTAX INTEGER
				{
				disable(0),
				enable(1)
				}
			MAX-ACCESS read-only
			STATUS current
			DESCRIPTION
				"Mirroring on ingress packets. 
				Valid only for physical ports. "
			DEFVAL { 0 }
			::= { sleBridgePortEntry 8 }

		
--  1.3.6.1.4.1.6296.9.8.2.1.1.7
		sleBridgePortEgMirrorStatus OBJECT-TYPE
			SYNTAX INTEGER
				{
				disable(0),
				enable(1)
				}
			MAX-ACCESS read-only
			STATUS current
			DESCRIPTION
				"Mirroring on egress packets. 
				Valid only for physical ports. "
			DEFVAL { 0 }
			::= { sleBridgePortEntry 9 }

		
--  1.3.6.1.4.1.6296.9.8.2.1.1.8
		sleBridgePortBcastThreshold OBJECT-TYPE
			SYNTAX INTEGER (0..2097150)
			MAX-ACCESS read-only
			STATUS current
			DESCRIPTION
				"Broadcast packet rate limit(unit: packets/s),
				Valid only for physical ports. 
				Default value is 0: it means BCSC clear-state.
				Value Range: 0-262142(TX/FX),0-2097150(GBIC)."
			DEFVAL { 0 }
			::= { sleBridgePortEntry 10 }

		
--  1.3.6.1.4.1.6296.9.8.2.1.1.9
		sleBridgePortMcastThreshold OBJECT-TYPE
			SYNTAX INTEGER (0..2097150)
			MAX-ACCESS read-only
			STATUS current
			DESCRIPTION
				"Multicast packet rate limit.(unit: packets/s), 
				Valid only for physical ports. 
				Default value is 0: it means BCSC clear-state.
				Value Range: 0-262142(TX/FX),0-2097150(GBIC)."
			DEFVAL { 0 }
			::= { sleBridgePortEntry 11 }

		
--  1.3.6.1.4.1.6296.9.8.2.1.1.10
		sleBridgePortDlfThreshold OBJECT-TYPE
			SYNTAX INTEGER (0..2097150)
			MAX-ACCESS read-only
			STATUS current
			DESCRIPTION
				"DLF packet rate limit(unit: packets/s), 
				Valid only for physical ports.
				Default value is 0: it means BCSC clear-state.
				Value Range: 0-262142(TX/FX),0-2097150(GBIC)."
			DEFVAL { 0 }
			::= { sleBridgePortEntry 12 }

		
--  1.3.6.1.4.1.6296.9.8.2.1.1.11
		sleBridgePortQinQStatus OBJECT-TYPE
			SYNTAX INTEGER
				{
				disable(0),
				enable(1)
				}
			MAX-ACCESS read-only
			STATUS current
			DESCRIPTION
				"QinQ Status of the port. 
				Valid only for physical ports. "
			DEFVAL { 0 }
			::= { sleBridgePortEntry 13 }

		
--  1.3.6.1.4.1.6296.9.8.2.1.1.12
		sleBridgePortAdminLinktype OBJECT-TYPE
			SYNTAX INTEGER
				{
				shared(0),
				pointTopoint(1),
				automatic(2)
				}
			MAX-ACCESS read-only
			STATUS current
			DESCRIPTION
				"The administrative link-type of port on the xSTP."
			DEFVAL { 2 }
			::= { sleBridgePortEntry 14 }

		
--  1.3.6.1.4.1.6296.9.8.2.1.1.13
		sleBridgePortAdminEdgemode OBJECT-TYPE
			SYNTAX INTEGER
				{
				disable(0),
				enable(1)
				}
			MAX-ACCESS read-only
			STATUS current
			DESCRIPTION
				"The administrative edgemode of port on the xSTP."
			DEFVAL { 0 }
			::= { sleBridgePortEntry 15 }

		
--  1.3.6.1.4.1.6296.9.8.2.1.1.14
		sleBridgePortOperLinktype OBJECT-TYPE
			SYNTAX INTEGER
				{
				shared(0),
				pointTopoint(1)
				}
			MAX-ACCESS read-only
			STATUS current
			DESCRIPTION
				"The link-type of the port on the xSTP."
			::= { sleBridgePortEntry 16 }

		
--  1.3.6.1.4.1.6296.9.8.2.1.1.15
		sleBridgePortOperEdgemode OBJECT-TYPE
			SYNTAX INTEGER
				{
				disabled(0),
				enabled(1)
				}
			MAX-ACCESS read-only
			STATUS current
			DESCRIPTION
				"The edge-mode of the port on the xSTP."
			::= { sleBridgePortEntry 17 }

		
		sleBridgePortStpBpduFilter OBJECT-TYPE
			SYNTAX INTEGER
				{
				disable(0),
				enable(1)
				}
			MAX-ACCESS read-only
			STATUS current
			DESCRIPTION
				"The stp bpdu-filter of the port on the xSTP. Default value is 0. "
			::= { sleBridgePortEntry 18 }

		
		sleBridgePortPvlanIsolatedStatus OBJECT-TYPE
			SYNTAX INTEGER
				{
				disable(0),
				enable(1)
				}
			MAX-ACCESS read-only
			STATUS current
			DESCRIPTION
				"Isolated status of this port. Default value is disable(0). "
			DEFVAL { 0 }
			::= { sleBridgePortEntry 19 }

		
		sleBridgePortPvlanPromPorts OBJECT-TYPE
			SYNTAX OCTET STRING
			MAX-ACCESS read-only
			STATUS current
			DESCRIPTION
				"Portlist for promiscuous ports of this port. The OctetString is a list of pairs of octets each identify an sheBridgePortIndex. The least significant byte is the second octet."
			::= { sleBridgePortEntry 20 }

		
		sleBridgePortDhcpFilterServer OBJECT-TYPE
			SYNTAX INTEGER
				{
				disable(0),
				enable(1)
				}
			MAX-ACCESS read-only
			STATUS current
			DESCRIPTION
				"DHCP filter server status
				0: disabled
				1: enabled"
			::= { sleBridgePortEntry 21 }

		
		sleBridgePortLoopDetectStatus OBJECT-TYPE
			SYNTAX INTEGER
				{
				enable(1),
				disable(2)
				}
			MAX-ACCESS read-only
			STATUS current
			DESCRIPTION
				"The adminStatus of loop-detect per ports."
			::= { sleBridgePortEntry 22 }

		
		sleBridgePortLoopDetectBlock OBJECT-TYPE
			SYNTAX INTEGER
				{
				enable(1),
				disable(2)
				}
			MAX-ACCESS read-only
			STATUS current
			DESCRIPTION
				"The adminBlock mode of loop-detect per ports.
				Indicate whether block port or not."
			::= { sleBridgePortEntry 23 }

		
		sleBridgePortLoopDetectPeriod OBJECT-TYPE
			SYNTAX INTEGER (1..60)
			MAX-ACCESS read-only
			STATUS current
			DESCRIPTION
				"The sending period of detection packet."
			::= { sleBridgePortEntry 24 }

		
		sleBridgePortLoopDetectTimer OBJECT-TYPE
			SYNTAX INTEGER (0 | 1..86400)
			MAX-ACCESS read-only
			STATUS current
			DESCRIPTION
				"The Blocked list expire timer."
			::= { sleBridgePortEntry 25 }

		
		sleBridgePortLoopDetectBlockStatus OBJECT-TYPE
			SYNTAX INTEGER
				{
				block(1),
				unblock(2)
				}
			MAX-ACCESS read-only
			STATUS current
			DESCRIPTION
				"The operStauts of loop-detect per ports."
			::= { sleBridgePortEntry 26 }

		
		sleBridgePortNetBIOSFilter OBJECT-TYPE
			SYNTAX INTEGER
				{
				disable(0),
				enable(1)
				}
			MAX-ACCESS read-only
			STATUS current
			DESCRIPTION
				"The netBios filter status per ports"
			::= { sleBridgePortEntry 27 }

		
		sleBridgePortPushInnertag OBJECT-TYPE
			SYNTAX INTEGER
				{
				disable(0),
				enable(1)
				}
			MAX-ACCESS read-only
			STATUS current
			DESCRIPTION
				"The ingress port that push inner-tag"
			::= { sleBridgePortEntry 28 }

		
		sleBridgePortPopInnertag OBJECT-TYPE
			SYNTAX INTEGER
				{
				disable(0),
				enable(1)
				}
			MAX-ACCESS read-only
			STATUS current
			DESCRIPTION
				"The egress port that pop inner-tag"
			::= { sleBridgePortEntry 29 }

		
		sleBridgePortInnertag OBJECT-TYPE
			SYNTAX INTEGER (0..4096)
			MAX-ACCESS read-only
			STATUS current
			DESCRIPTION
				"The inner-tag value to push for incoming untagged packet"
			::= { sleBridgePortEntry 30 }

		
		sleBridgePortPriority OBJECT-TYPE
			SYNTAX INTEGER (0..7)
			MAX-ACCESS read-only
			STATUS current
			DESCRIPTION
				"The port priority value for incoming untagged packet"
			::= { sleBridgePortEntry 31 }

		
		sleBridgePortInner2outerPri OBJECT-TYPE
			SYNTAX INTEGER
				{
				disable(0),
				enable(1)
				}
			MAX-ACCESS read-only
			STATUS current
			DESCRIPTION
				"Use inner-tag’s priority as outer-tag’s priority."
			::= { sleBridgePortEntry 32 }

		
		sleBridgePortInner2outerVid OBJECT-TYPE
			SYNTAX INTEGER
				{
				disable(0),
				enable(1)
				}
			MAX-ACCESS read-only
			STATUS current
			DESCRIPTION
				"Use inner-tag’s vlan-id as outer-tag’s vlan-id."
			::= { sleBridgePortEntry 33 }

		
		sleBridgePortLinkUpCnt OBJECT-TYPE
			SYNTAX INTEGER (1..65535)
			MAX-ACCESS read-only
			STATUS current
			DESCRIPTION
				"The times of link-up event"
			::= { sleBridgePortEntry 34 }

		
		sleBridgePortLinkDownCnt OBJECT-TYPE
			SYNTAX INTEGER (1..65535)
			MAX-ACCESS read-only
			STATUS current
			DESCRIPTION
				"The times of link-down event"
			::= { sleBridgePortEntry 35 }

		
		sleBridgePortLinkUpTime OBJECT-TYPE
			SYNTAX Counter64
			UNITS "1 sec"
			MAX-ACCESS read-only
			STATUS current
			DESCRIPTION
				"The elapsed time after link is up."
			::= { sleBridgePortEntry 36 }

		
		sleBridgePortElapsedTimeAfterClearStats OBJECT-TYPE
			SYNTAX Counter64
			UNITS "1 sec"
			MAX-ACCESS read-only
			STATUS current
			DESCRIPTION
				"The elapsed time after clearing statistics."
			::= { sleBridgePortEntry 37 }

		
		sleBridgePortMACLearningStatus OBJECT-TYPE
			SYNTAX INTEGER
				{
				enable(1),
				disable(2)
				}
			MAX-ACCESS read-only
			STATUS current
			DESCRIPTION
				"If enable, SLF packet is forwarded with mac-learning.
				Otherwise, SLF packet is forwarded without mac-learning."
			::= { sleBridgePortEntry 38 }

		
		sleBridgePortPortBridgeStatus OBJECT-TYPE
			SYNTAX INTEGER
				{
				enable(1),
				disable(2)
				}
			MAX-ACCESS read-only
			STATUS current
			DESCRIPTION
				"Port Bridge Feature for transmitting the packet out on the same port of which is received."
			::= { sleBridgePortEntry 39 }
-- Port Bridge Feature for transmitting the packet out on the same port of which is received.
		
		sleBridgePortUnknownMcastBlock OBJECT-TYPE
			SYNTAX INTEGER
				{
				enable(1),
				disable(2)
				}
			MAX-ACCESS read-only
			STATUS current
			DESCRIPTION
				"Unknown multicast block setting for a port."
			::= { sleBridgePortEntry 40 }

		
		sleBridgePortDescription OBJECT-TYPE
			SYNTAX OCTET STRING (SIZE (1..128))
			MAX-ACCESS read-write
			STATUS current
			DESCRIPTION
				"The port description."
			::= { sleBridgePortEntry 41 }

		
		sleBridgePortHoldTime OBJECT-TYPE
			SYNTAX Integer32 (1..65535)
			MAX-ACCESS read-only
			STATUS current
			DESCRIPTION
				"The hold-time"
			::= { sleBridgePortEntry 42 }

		
		sleBridgePortMacAntiSpoofing OBJECT-TYPE
			SYNTAX TruthValue
			MAX-ACCESS read-only
			STATUS current
			DESCRIPTION
				"The mac anti-spoofing per port."
			::= { sleBridgePortEntry 43 }

		
		sleBridgePortSwitchType OBJECT-TYPE
			SYNTAX INTEGER
				{
				special(1),
				inner(2),
				vlan(3),
				eth(4),
				portChannel(5),
				tunnel(6),
				unknown(255)
				}
			MAX-ACCESS read-only
			STATUS current
			DESCRIPTION
				"Interface type."
			::= { sleBridgePortEntry 44 }

		
		sleBridgePortSwitchState OBJECT-TYPE
			SYNTAX INTEGER
				{
				switchedPort(1),
				routedPort(2)
				}
			MAX-ACCESS read-only
			STATUS current
			DESCRIPTION
				"The interface mode to switched port or routed port."
			::= { sleBridgePortEntry 45 }

		
		sleBridgePortSwitchMode OBJECT-TYPE
			SYNTAX INTEGER
				{
				access(1),
				hybrid(2),
				trunk(3),
				ce(4),
				cn(5),
				pn(6),
				pe(7),
				cnp(8),
				vip(9),
				pip(10),
				cbp(11),
				invalid(255)
				}
			MAX-ACCESS read-only
			STATUS current
			DESCRIPTION
				"The switching mode of L2 interface."
			::= { sleBridgePortEntry 46 }

		
		sleBridgePortSwitchSubMode OBJECT-TYPE
			SYNTAX INTEGER
				{
				access(1),
				hybrid(2),
				trunk(3),
				ce(4),
				cn(5),
				pn(6),
				pe(7),
				cnp(8),
				vip(9),
				pip(10),
				cbp(11),
				invalid(255)
				}
			MAX-ACCESS read-only
			STATUS current
			DESCRIPTION
				"The switching sub mode of L2 interface."
			::= { sleBridgePortEntry 47 }

		
		sleBridgePortSwitchDefaultVlan OBJECT-TYPE
			SYNTAX Integer32 (1..4094)
			MAX-ACCESS read-only
			STATUS current
			DESCRIPTION
				"The default VLAN of L2 interface."
			::= { sleBridgePortEntry 48 }

		
		sleBridgePortSwitchIngressFilter OBJECT-TYPE
			SYNTAX INTEGER
				{
				enable(1),
				disable(2)
				}
			MAX-ACCESS read-only
			STATUS current
			DESCRIPTION
				"Set the ingress filtering for 
the received frames.
				"
			::= { sleBridgePortEntry 49 }

		
		sleBridgePortSwitchAccFrameType OBJECT-TYPE
			SYNTAX BITS
				{
				allType(0),
				tagged(1),
				untagged(2)
				}
			MAX-ACCESS read-only
			STATUS current
			DESCRIPTION
				"Set the Layer 2 interface acceptable frame types. 
				This processing occurs
after VLAN classification.
vlan-tagged Accept only classified frames 
				which belong to the port's member set.

Hybridge interface only.
				"
			::= { sleBridgePortEntry 50 }

		
		sleBridgePortSwitchNativeVid OBJECT-TYPE
			SYNTAX Integer32 (1..4094)
			MAX-ACCESS read-only
			STATUS current
			DESCRIPTION
				"The native VLAN is used for classifying the incoming untagged packets.
				"
			::= { sleBridgePortEntry 51 }

		
		sleBridgePortSwitchAllowedVlan OBJECT-TYPE
			SYNTAX OCTET STRING
			MAX-ACCESS read-only
			STATUS current
			DESCRIPTION
				"Both tagged and untagged
				frames will be classified over interfaces."
			::= { sleBridgePortEntry 52 }

		
		sleBridgePortSwitchAllowedVlanEtag OBJECT-TYPE
			SYNTAX OCTET STRING
			MAX-ACCESS read-only
			STATUS current
			DESCRIPTION
				"egress Port string"
			::= { sleBridgePortEntry 53 }

		
		sleBridgePortSwitchChannelType OBJECT-TYPE
			SYNTAX INTEGER
				{
				none(0),
				aggregator(1),
				aggregated(2)
				}
			MAX-ACCESS read-only
			STATUS current
			DESCRIPTION
				"Indicate whether port is aggregator or aggregated(member)."
			::= { sleBridgePortEntry 54 }

		
		sleBridgePortSwitchStaticChannelGroup OBJECT-TYPE
			SYNTAX OCTET STRING
			MAX-ACCESS read-only
			STATUS current
			DESCRIPTION
				"Static channel group name"
			::= { sleBridgePortEntry 55 }

		
		sleBridgePortSwitchChannelLoadbalance OBJECT-TYPE
			SYNTAX INTEGER
				{
				dstMac(1),
				srcMac(2),
				srcDstMac(3),
				srcIp(4),
				dstIp(5),
				srcDstIp(6),
				srcPort(7),
				dstPort(8),
				srcDstPort(9)
				}
			MAX-ACCESS read-only
			STATUS current
			DESCRIPTION
				"Channel group hash method."
			::= { sleBridgePortEntry 56 }

		
--   Node definitions
-- 
-- 1.3.6.1.4.1.6296.9.8.2.2
		sleBridgePortControl OBJECT IDENTIFIER ::= { sleBridgePort 2 }

		
--  1.3.6.1.4.1.6296.9.8.2.2.1
		sleBridgePortControlRequest OBJECT-TYPE
			SYNTAX INTEGER
				{
				setBridgePortPVid(1),
				setBridgePortMaxHosts(2),
				setBridgePortMaxLearnPerUnit(3),
				setBridgePortMACFilterPermission(4),
				setBridgePortMirrorProfile(5),
				setBridgePortBcscThresholdProfile(6),
				setBridgePortQinQStatus(7),
				setBridgePortLinktype(8),
				setBridgePortEdgemode(9),
				setBridgePortStpBpduFilter(10),
				setBridgePortIsolatedStatus(11),
				setBridgePortStpBpduGuardErrRcv(12),
				setBridgePortDhcpFilterServer(13),
				setBridgePortLoopDetectProfile(14),
				setBridgePortLoopDetectUnblock(15),
				setBridgePortNetBIOSFilter(16),
				setBridgePortPushInnertag(17),
				setBridgePortPopInnertag(18),
				setBridgePortInnertag(19),
				setBridgePortPriority(20),
				setBridgePortInner2outerPri(21),
				setBridgePortInner2outerVid(22),
				setBridgePortMacLearningStatus(23),
				setBridgePortPortBridgeStatus(24),
				setBridgePortUnknownMcastBlock(25),
				setBridgePortDescriptopn(26),
				setBridgePortHoldTime(27),
				setBridgePortMacAntiSpoofing(28),
				setBridgePortSwitchStatus(29),
				setBridgePortSwitchMode(30),
				setBridgePortSwitchDefaultVlan(31),
				setBridgePortSwitchNativeVlan(32),
				setBridgePortSwitchAccFramType(33),
				setBridgePortSwitchAddAllowdVlan(34),
				setBridgePortSwitchRemoveAllowdVlan(35),
				setBridgePortSwitchStaticChannel(36),
				setBridgePortSwitchChannelLoadbalance(37)
				}
			MAX-ACCESS read-write
			STATUS current
			DESCRIPTION
				"
				setBridgePortPVid:
				sleBridgePortControlIndex
				sleBridgePortControlPVid
				
				setBridgePortMaxHosts:
				sleBridgePortControlIndex
				sleBridgePortControlMaxHosts
				
				setBridgePortMACFilterPermission:
				sleBridgePortControlIndex
				sleBridgePortControlMACFilterPermission
				
				setBridgePortMirrorProfile:
				sleBridgePortControlIndex
				sleBridgePortControlIngMirrorStatus
				sleBridgePortControlEgMirrorStatus
				            
				setBridgePortBcscThresholdProfile:
				sleBridgePortControlIndex
				sleBridgePortControlBcastThreshold
				sleBridgePortControlMcastThreshold
				sleBridgePortControlDlfThreshold
				            
				setBridgePortQinQStatus:
				sleBridgePortControlIndex
				sleBridgePortControlQinQStatus
				            
				setBridgePortLinktype:
				sleBridgePortControlIndex
				sleBridgePortControlAdminLinktype
				            
				setBridgePortEdgemode:
				sleBridgePortControlIndex
				sleBridgePortControlAdminEdgemode
				
				setBridgePortNetBIOSFilter:
				sleBridgePortControlIndex
				sleBridgePortControlNetBIOSFilter
				"
			::= { sleBridgePortControl 1 }

		
--  1.3.6.1.4.1.6296.9.8.2.2.3
		sleBridgePortControlStatus OBJECT-TYPE
			SYNTAX SleControlStatusType
			MAX-ACCESS read-only
			STATUS current
			DESCRIPTION
				"The status of a user command."
			::= { sleBridgePortControl 2 }

		
--  1.3.6.1.4.1.6296.9.8.2.2.4
		sleBridgePortControlTimer OBJECT-TYPE
			SYNTAX Gauge32
			MAX-ACCESS read-write
			STATUS current
			DESCRIPTION
				"The maximum wait time for the manager for a long running user command."
			::= { sleBridgePortControl 3 }

		
--  1.3.6.1.4.1.6296.9.8.2.2.6
		sleBridgePortControlTimeStamp OBJECT-TYPE
			SYNTAX TimeTicks
			MAX-ACCESS read-only
			STATUS current
			DESCRIPTION
				"The time stamp of the last command (end of command)."
			::= { sleBridgePortControl 4 }

		
--  1.3.6.1.4.1.6296.9.8.2.2.5
		sleBridgePortControlReqResult OBJECT-TYPE
			SYNTAX SleControlRequestResultType
			MAX-ACCESS read-only
			STATUS current
			DESCRIPTION
				"The result of the last user command."
			::= { sleBridgePortControl 5 }

		
--  1.3.6.1.4.1.6296.9.8.2.2.2
		sleBridgePortControlIndex OBJECT-TYPE
			SYNTAX INTEGER (1..255)
			MAX-ACCESS read-write
			STATUS current
			DESCRIPTION
				"sleBridgePortIndex"
			::= { sleBridgePortControl 6 }

		
--  1.3.6.1.4.1.6296.9.8.2.2.7
		sleBridgePortControlPVid OBJECT-TYPE
			SYNTAX INTEGER (1..4094)
			MAX-ACCESS read-write
			STATUS current
			DESCRIPTION
				"The PVID of port. 
				Taken if no other rule given for VLAN association. 
				If aggregated: only for group."
			::= { sleBridgePortControl 7 }

		
--  1.3.6.1.4.1.6296.9.8.2.2.8
		sleBridgePortControlMaxHosts OBJECT-TYPE
			SYNTAX INTEGER (-1..2147483647)
			MAX-ACCESS read-write
			STATUS current
			DESCRIPTION
				"The maximum number of hosts allowed. 
				Aggregation group available. Value 0 is allowed,
				Value -1 is used to clear."
			DEFVAL { -1 }
			::= { sleBridgePortControl 8 }

		
		sleBridgePortControlMaxLearnPerUnit OBJECT-TYPE
			SYNTAX INTEGER (-1..2147483647)
			MAX-ACCESS read-write
			STATUS current
			DESCRIPTION
				"Limit maximum number of MAC addresses learning 
				newly per unit time(one second) on a port.
				(0: nothing learned, -l: unlimited.)"
			::= { sleBridgePortControl 9 }

		
--  1.3.6.1.4.1.6296.9.8.2.2.9
		sleBridgePortControlMACFilterPermission OBJECT-TYPE
			SYNTAX INTEGER
				{
				deny(0),
				permit(1)
				}
			MAX-ACCESS read-write
			STATUS current
			DESCRIPTION
				"The default permission for mac filtering. 
				Valid only for physical ports, 
				use values from MFDB  Table."
			DEFVAL { 1 }
			::= { sleBridgePortControl 10 }

		
--  1.3.6.1.4.1.6296.9.8.2.2.10
		sleBridgePortControlIngMirrorStatus OBJECT-TYPE
			SYNTAX INTEGER
				{
				disable(0),
				enable(1)
				}
			MAX-ACCESS read-write
			STATUS current
			DESCRIPTION
				"Mirroring on ingress packets. 
				Valid only for physical ports. "
			DEFVAL { 0 }
			::= { sleBridgePortControl 11 }

		
--  1.3.6.1.4.1.6296.9.8.2.2.11
		sleBridgePortControlEgMirrorStatus OBJECT-TYPE
			SYNTAX INTEGER
				{
				disable(0),
				enable(1)
				}
			MAX-ACCESS read-write
			STATUS current
			DESCRIPTION
				"Mirroring on egress packets. 
				Valid only for physical ports. "
			DEFVAL { 0 }
			::= { sleBridgePortControl 12 }

		
--  1.3.6.1.4.1.6296.9.8.2.2.12
		sleBridgePortControlBcastThreshold OBJECT-TYPE
			SYNTAX INTEGER (0..2097150)
			MAX-ACCESS read-write
			STATUS current
			DESCRIPTION
				"Broadcast packet rate limit (unit: packets/s), 
				Valid only for physical ports. Value 0 is used to clear.
				Value Range: 0-262142(TX/FX),0-2097150(GBIC)."
			DEFVAL { 0 }
			::= { sleBridgePortControl 13 }

		
--  1.3.6.1.4.1.6296.9.8.2.2.13
		sleBridgePortControlMcastThreshold OBJECT-TYPE
			SYNTAX INTEGER (0..2097150)
			MAX-ACCESS read-write
			STATUS current
			DESCRIPTION
				"Multicast packet rate limit (unit: packets/s), 
				Valid only for physical ports. Value 0 is used to clear.
				Value Range: 0-262142(TX/FX),0-2097150(GBIC)."
			DEFVAL { 0 }
			::= { sleBridgePortControl 14 }

		
--  1.3.6.1.4.1.6296.9.8.2.2.14
		sleBridgePortControlDlfThreshold OBJECT-TYPE
			SYNTAX INTEGER (0..2097150)
			MAX-ACCESS read-write
			STATUS current
			DESCRIPTION
				"DLF packet rate limit (unit: packets/s), 
				Valid only for physical ports. Value 0 is used to clear.
				Value Range: 0-262142(TX/FX),0-2097150(GBIC)."
			DEFVAL { 0 }
			::= { sleBridgePortControl 15 }

		
--  1.3.6.1.4.1.6296.9.8.2.2.15
		sleBridgePortControlQinQStatus OBJECT-TYPE
			SYNTAX INTEGER
				{
				disable(0),
				enable(1)
				}
			MAX-ACCESS read-write
			STATUS current
			DESCRIPTION
				"QinQ Status of the port. 
				Valid only for physical ports. "
			DEFVAL { 0 }
			::= { sleBridgePortControl 16 }

		
--  1.3.6.1.4.1.6296.9.8.2.2.16
		sleBridgePortControlAdminLinktype OBJECT-TYPE
			SYNTAX INTEGER
				{
				shared(0),
				pointTopoint(1),
				automatic(2)
				}
			MAX-ACCESS read-write
			STATUS current
			DESCRIPTION
				"The administrative link-type of port on the xSTP. "
			DEFVAL { 2 }
			::= { sleBridgePortControl 17 }

		
--  1.3.6.1.4.1.6296.9.8.2.2.17
		sleBridgePortControlAdminEdgemode OBJECT-TYPE
			SYNTAX INTEGER
				{
				disable(0),
				enable(1)
				}
			MAX-ACCESS read-write
			STATUS current
			DESCRIPTION
				"The administrative edgemode of port on the xSTP. "
			DEFVAL { 0 }
			::= { sleBridgePortControl 18 }

		
		sleBridgePortControlStpBpduFilter OBJECT-TYPE
			SYNTAX INTEGER
				{
				disable(0),
				enable(1)
				}
			MAX-ACCESS read-write
			STATUS current
			DESCRIPTION
				"The stp bpdu-filter of the port on the xSTP. Default value is 0."
			DEFVAL { 0 }
			::= { sleBridgePortControl 19 }

		
		sleBridgePortControlPvlanIsolatedStatus OBJECT-TYPE
			SYNTAX INTEGER
				{
				disable(0),
				enable(1)
				}
			MAX-ACCESS read-write
			STATUS current
			DESCRIPTION
				"Isolated status of this port. Default value is disable(0)."
			DEFVAL { 0 }
			::= { sleBridgePortControl 20 }

		
		sleBridgePortControlPvlanPromPort OBJECT-TYPE
			SYNTAX INTEGER (1..65535)
			MAX-ACCESS read-write
			STATUS current
			DESCRIPTION
				"Portlist for promiscuous ports of this port. The OctetString is a list of pairs of octets each identify an sheBridgePortIndex. The least significant byte is the second octet."
			::= { sleBridgePortControl 21 }

		
		sleBridgePortControlStpBpduGuardErrRcv OBJECT-TYPE
			SYNTAX TruthValue
			MAX-ACCESS read-write
			STATUS current
			DESCRIPTION
				"Trigger manual recovery for the port disabled by Bpdu Guard.
				 false : sustain current state.
				 true  : trigger recovery."
			DEFVAL { false }
			::= { sleBridgePortControl 22 }

		
		sleBridgePortControlDhcpFilterServer OBJECT-TYPE
			SYNTAX INTEGER
				{
				disable(0),
				enable(1)
				}
			MAX-ACCESS read-write
			STATUS current
			DESCRIPTION
				"DHCP filter server status
				0: disabled
				1: enabled"
			::= { sleBridgePortControl 23 }

		
		sleBridgePortControlLoopDetectStatus OBJECT-TYPE
			SYNTAX INTEGER
				{
				enable(1),
				disable(2)
				}
			MAX-ACCESS read-write
			STATUS current
			DESCRIPTION
				"The adminStatus of loop-detect per ports."
			::= { sleBridgePortControl 24 }

		
		sleBridgePortControlLoopDetectBlock OBJECT-TYPE
			SYNTAX INTEGER
				{
				enable(1),
				disable(2)
				}
			MAX-ACCESS read-only
			STATUS current
			DESCRIPTION
				"The adminBlock mode of loop-detect per ports.
				Indicate whether block port or not."
			::= { sleBridgePortControl 25 }

		
		sleBridgePortControlLoopDetectPeriod OBJECT-TYPE
			SYNTAX INTEGER (1..60)
			MAX-ACCESS read-write
			STATUS current
			DESCRIPTION
				"The sending period of detection packet."
			::= { sleBridgePortControl 26 }

		
		sleBridgePortControlLoopDetectTimer OBJECT-TYPE
			SYNTAX INTEGER (0 | 1..86400)
			MAX-ACCESS read-write
			STATUS current
			DESCRIPTION
				"The Blocked list expire timer."
			::= { sleBridgePortControl 27 }

		
		sleBridgePortControlNetBIOSFilter OBJECT-TYPE
			SYNTAX INTEGER
				{
				disable(0),
				enable(1)
				}
			MAX-ACCESS read-write
			STATUS current
			DESCRIPTION
				"The netBios filter status per ports"
			::= { sleBridgePortControl 28 }

		
		sleBridgePortControlPushInnertag OBJECT-TYPE
			SYNTAX INTEGER
				{
				disable(0),
				enable(1)
				}
			MAX-ACCESS read-write
			STATUS current
			DESCRIPTION
				"Push inner-tag for incoming untagged packet."
			::= { sleBridgePortControl 29 }

		
		sleBridgePortControlPopInnertag OBJECT-TYPE
			SYNTAX INTEGER
				{
				disable(0),
				enable(1)
				}
			MAX-ACCESS read-write
			STATUS current
			DESCRIPTION
				"Pop inner-tag for double tagged packet."
			::= { sleBridgePortControl 30 }

		
		sleBridgePortControlInnertag OBJECT-TYPE
			SYNTAX INTEGER (0..4096)
			MAX-ACCESS read-write
			STATUS current
			DESCRIPTION
				"Inner-tag value to push for incoming untagged packet."
			::= { sleBridgePortControl 31 }

		
		sleBridgePortControlPriority OBJECT-TYPE
			SYNTAX INTEGER (0..7)
			MAX-ACCESS read-write
			STATUS current
			DESCRIPTION
				"The priority value per port.
				Assign priority for untagged packet from port.
				"
			::= { sleBridgePortControl 32 }

		
		sleBridgePortControlInner2outerPri OBJECT-TYPE
			SYNTAX INTEGER
				{
				disable(0),
				enable(1)
				}
			MAX-ACCESS read-write
			STATUS current
			DESCRIPTION
				"If enable, use inner-tag's priority as outer-tag's priority.
				Otherwise, use outer-tag's priority"
			::= { sleBridgePortControl 33 }

		
		sleBridgePortControlInner2outerVid OBJECT-TYPE
			SYNTAX INTEGER
				{
				disable(0),
				enable(1)
				}
			MAX-ACCESS read-write
			STATUS current
			DESCRIPTION
				"If enable, use inner-tag's vlan-id as outer-tag's vlan-id.
				Otherwise, use outer-tag's vlan-id"
			::= { sleBridgePortControl 34 }

		
		sleBridgePortControlMACLearningStatus OBJECT-TYPE
			SYNTAX INTEGER
				{
				enable(1),
				disable(2)
				}
			MAX-ACCESS read-write
			STATUS current
			DESCRIPTION
				"If enable, SLF packet is forwarded with mac-learning.
				Otherwise, SLF packet is forwarded without mac-learning."
			::= { sleBridgePortControl 35 }

		
		sleBridgePortControlPortBridgeStatus OBJECT-TYPE
			SYNTAX INTEGER
				{
				enable(1),
				disable(2)
				}
			MAX-ACCESS read-write
			STATUS current
			DESCRIPTION
				"Port Bridge Feature for transmitting the packet out on the same port of which is received."
			::= { sleBridgePortControl 36 }

		
		sleBridgePortControlUnknownMcastBlock OBJECT-TYPE
			SYNTAX INTEGER
				{
				enable(1),
				disable(2)
				}
			MAX-ACCESS read-write
			STATUS current
			DESCRIPTION
				"Unknown multicast block setting for a port."
			::= { sleBridgePortControl 37 }

		
		sleBridgePortControlDescription OBJECT-TYPE
			SYNTAX OCTET STRING (SIZE (1..128))
			MAX-ACCESS read-write
			STATUS current
			DESCRIPTION
				"The Port Description."
			::= { sleBridgePortControl 38 }

		
		sleBridgePortControlHoldTime OBJECT-TYPE
			SYNTAX Integer32 (1..65535)
			MAX-ACCESS read-write
			STATUS current
			DESCRIPTION
				"The hold-time"
			::= { sleBridgePortControl 39 }

		
		sleBridgePortControlMacAntiSpoofing OBJECT-TYPE
			SYNTAX TruthValue
			MAX-ACCESS read-write
			STATUS current
			DESCRIPTION
				"The mac anti-spoofing per port."
			::= { sleBridgePortControl 40 }

		
		sleBridgePortControlSwitchStatus OBJECT-TYPE
			SYNTAX INTEGER
				{
				switchedPort(1),
				routedPort(2)
				}
			MAX-ACCESS read-write
			STATUS current
			DESCRIPTION
				"The interface mode to switched port or routed port."
			::= { sleBridgePortControl 41 }

		
		sleBridgePortControlSwitchMode OBJECT-TYPE
			SYNTAX INTEGER
				{
				access(1),
				hybrid(2),
				trunk(3),
				ce(4),
				cn(5),
				pn(6),
				pe(7),
				cnp(8),
				vip(9),
				pip(10),
				cbp(11),
				invalid(255)
				}
			MAX-ACCESS read-write
			STATUS current
			DESCRIPTION
				"The switching mode of L2 interface.
				"
			::= { sleBridgePortControl 42 }

		
		sleBridgePortControlSwitchSubMode OBJECT-TYPE
			SYNTAX INTEGER
				{
				access(1),
				hybrid(2),
				trunk(3),
				ce(4),
				cn(5),
				pn(6),
				pe(7),
				cnp(8),
				vip(9),
				pip(10),
				cbp(11),
				invalid(255)
				}
			MAX-ACCESS read-write
			STATUS current
			DESCRIPTION
				"The switching sub mode of L2 interface.
				"
			::= { sleBridgePortControl 43 }

		
		sleBridgePortControlSwitchDefaultVlan OBJECT-TYPE
			SYNTAX Integer32 (1..4094)
			MAX-ACCESS read-write
			STATUS current
			DESCRIPTION
				"The dafulat VLAN of L2 interface"
			::= { sleBridgePortControl 44 }

		
		sleBridgePortControlSwitchIngressFilter OBJECT-TYPE
			SYNTAX INTEGER
				{
				enable(1),
				disable(2)
				}
			MAX-ACCESS read-write
			STATUS current
			DESCRIPTION
				"Set the ingress filtering for 
the received frames
				"
			::= { sleBridgePortControl 45 }

		
		sleBridgePortControlSwitchAccFrameType OBJECT-TYPE
			SYNTAX BITS
				{
				allType(0),
				tagged(1),
				unTagged(2)
				}
			MAX-ACCESS read-write
			STATUS current
			DESCRIPTION
				"Set the Layer 2 interface acceptable frame types.
				This processing occurs
after VLAN classification.
vlan-tagged Accept only classified frames 
				which belong to the port's member set.

Hybridge interface only."
			::= { sleBridgePortControl 46 }

		
		sleBridgePortControlSwitchNativeVid OBJECT-TYPE
			SYNTAX Integer32 (1..4094)
			MAX-ACCESS read-write
			STATUS current
			DESCRIPTION
				"The native VLAN is used for classifying the incoming untagged packets.
				"
			::= { sleBridgePortControl 47 }

		
		sleBridgePortControlSwitchAllowedVlan OBJECT-TYPE
			SYNTAX OCTET STRING
			MAX-ACCESS read-write
			STATUS current
			DESCRIPTION
				"Both tagged and untagged
				frames will be classified over interfaces."
			::= { sleBridgePortControl 48 }

		
		sleBridgePortControlSwitchAllowedVlanEtag OBJECT-TYPE
			SYNTAX OCTET STRING
			MAX-ACCESS read-write
			STATUS current
			DESCRIPTION
				"egress Port string"
			::= { sleBridgePortControl 49 }

		
		sleBridgePortControlSwitchStaticChannelGroup OBJECT-TYPE
			SYNTAX OCTET STRING
			MAX-ACCESS read-write
			STATUS current
			DESCRIPTION
				"Static channel group name"
			::= { sleBridgePortControl 50 }

		
		sleBridgePortControlSwitchChannelLoadbalance OBJECT-TYPE
			SYNTAX INTEGER
				{
				dstMac(1),
				srcMac(2),
				srcDstMac(3),
				srcIp(4),
				dstIp(5),
				srcDstIp(6),
				srcPort(7),
				dstPort(8),
				srcDstPort(9)
				}
			MAX-ACCESS read-write
			STATUS current
			DESCRIPTION
				"Channel group hash method."
			::= { sleBridgePortControl 51 }

		
--   Node definitions
-- 
-- 1.3.6.1.4.1.6296.9.8.2.3
		sleBridgePortNotification OBJECT IDENTIFIER ::= { sleBridgePort 3 }

		
--  1.3.6.1.4.1.6296.9.8.2.3.1
		sleBridgePortPVidChanged NOTIFICATION-TYPE
			OBJECTS { sleBridgePortPVid, sleBridgePortControlRequest, sleBridgePortControlTimeStamp, sleBridgePortControlReqResult }
			STATUS current
			DESCRIPTION 
				"PVid changed"
			::= { sleBridgePortNotification 1 }

		
--  1.3.6.1.4.1.6296.9.8.2.3.2
		sleBridgePortMaxHostsChanged NOTIFICATION-TYPE
			OBJECTS { sleBridgePortMaxHosts, sleBridgePortControlRequest, sleBridgePortControlTimeStamp, sleBridgePortControlReqResult }
			STATUS current
			DESCRIPTION 
				"MaxHosts changed"
			::= { sleBridgePortNotification 2 }

		
		sleBridgePortMaxLearnPerUnitChanged NOTIFICATION-TYPE
			OBJECTS { sleBridgePortControlRequest, sleBridgePortControlTimeStamp, sleBridgePortControlReqResult, sleBridgePortMaxLearnPerUnit }
			STATUS current
			DESCRIPTION 
				"Description."
			::= { sleBridgePortNotification 3 }

		
--  1.3.6.1.4.1.6296.9.8.2.3.3
		sleBridgePortMACFilterPermissionChanged NOTIFICATION-TYPE
			OBJECTS { sleBridgePortMACFilterPermission, sleBridgePortControlRequest, sleBridgePortControlTimeStamp, sleBridgePortControlReqResult }
			STATUS current
			DESCRIPTION 
				"MAC filter permission changed"
			::= { sleBridgePortNotification 4 }

		
--  1.3.6.1.4.1.6296.9.8.2.3.4
		sleBridgePortMirrorProfileChanged NOTIFICATION-TYPE
			OBJECTS { sleBridgePortIngMirrorStatus, sleBridgePortEgMirrorStatus, sleBridgePortControlRequest, sleBridgePortControlTimeStamp, sleBridgePortControlReqResult
				 }
			STATUS current
			DESCRIPTION 
				"Mirror profile changed"
			::= { sleBridgePortNotification 5 }

		
--  1.3.6.1.4.1.6296.9.8.2.3.5
		sleBridgePortBcscThresholdProfileChanged NOTIFICATION-TYPE
			OBJECTS { sleBridgePortBcastThreshold, sleBridgePortMcastThreshold, sleBridgePortDlfThreshold, sleBridgePortControlRequest, sleBridgePortControlTimeStamp, 
				sleBridgePortControlReqResult }
			STATUS current
			DESCRIPTION 
				"BCSC threshold profile changed"
			::= { sleBridgePortNotification 6 }

		
--  1.3.6.1.4.1.6296.9.8.2.3.6
		sleBridgePortQinQStatusChanged NOTIFICATION-TYPE
			OBJECTS { sleBridgePortQinQStatus, sleBridgePortControlRequest, sleBridgePortControlTimeStamp, sleBridgePortControlReqResult }
			STATUS current
			DESCRIPTION 
				"QinQ status changed"
			::= { sleBridgePortNotification 7 }

		
--  1.3.6.1.4.1.6296.9.8.2.3.7
		sleBridgePortLinktypeChanged NOTIFICATION-TYPE
			OBJECTS { sleBridgePortAdminLinktype, sleBridgePortControlRequest, sleBridgePortControlTimeStamp, sleBridgePortControlReqResult }
			STATUS current
			DESCRIPTION 
				"Admin link-type changed"
			::= { sleBridgePortNotification 8 }

		
--  1.3.6.1.4.1.6296.9.8.2.3.8
		sleBridgePortEdgemodeChanged NOTIFICATION-TYPE
			OBJECTS { sleBridgePortAdminEdgemode, sleBridgePortControlRequest, sleBridgePortControlTimeStamp, sleBridgePortControlReqResult }
			STATUS current
			DESCRIPTION 
				"Admin edge-mode changed"
			::= { sleBridgePortNotification 9 }

		
		sleBridgePortStpBpduFilterChanged NOTIFICATION-TYPE
			OBJECTS { sleBridgePortStpBpduFilter, sleBridgePortControlTimeStamp, sleBridgePortControlReqResult, sleBridgePortControlRequest }
			STATUS current
			DESCRIPTION 
				"Description."
			::= { sleBridgePortNotification 10 }

		
		sleBridgePortPvlanIsolatedStatusChanged NOTIFICATION-TYPE
			OBJECTS { sleBridgePortPvlanIsolatedStatus, sleBridgePortPvlanPromPorts, sleBridgePortControlRequest, sleBridgePortControlTimeStamp, sleBridgePortControlReqResult
				 }
			STATUS current
			DESCRIPTION 
				"Description."
			::= { sleBridgePortNotification 11 }

		
		sleBridgePortStpBpduGuardErrRcvChanged NOTIFICATION-TYPE
			OBJECTS { sleBridgePortControlRequest, sleBridgePortControlTimeStamp, sleBridgePortControlReqResult }
			STATUS current
			DESCRIPTION 
				"Description."
			::= { sleBridgePortNotification 12 }

		
		sleBridgePortDhcpFilterServerChanged NOTIFICATION-TYPE
			OBJECTS { sleBridgePortControlRequest, sleBridgePortControlTimeStamp, sleBridgePortControlReqResult, sleBridgePortDhcpFilterServer }
			STATUS current
			DESCRIPTION 
				"Description."
			::= { sleBridgePortNotification 13 }

		
		sleBridgePortLoopDetectProfileChanged NOTIFICATION-TYPE
			OBJECTS { sleBridgePortControlRequest, sleBridgePortControlTimeStamp, sleBridgePortControlReqResult, sleBridgePortLoopDetectStatus, sleBridgePortLoopDetectBlock, 
				sleBridgePortLoopDetectPeriod, sleBridgePortLoopDetectTimer }
			STATUS current
			DESCRIPTION 
				"Description."
			::= { sleBridgePortNotification 14 }

		
		sleBridgePortLoopDetectUnblock NOTIFICATION-TYPE
			OBJECTS { sleBridgePortControlRequest, sleBridgePortControlTimeStamp, sleBridgePortControlReqResult, sleBridgePortLoopDetectBlockStatus }
			STATUS current
			DESCRIPTION 
				"Description."
			::= { sleBridgePortNotification 15 }

		
		sleBridgePortNetBIOSFilterChanged NOTIFICATION-TYPE
			OBJECTS { sleBridgePortControlRequest, sleBridgePortControlTimeStamp, sleBridgePortControlReqResult, sleBridgePortNetBIOSFilter }
			STATUS current
			DESCRIPTION 
				"Description."
			::= { sleBridgePortNotification 16 }

		
		sleBridgePortPushInnertagChanged NOTIFICATION-TYPE
			OBJECTS { sleBridgePortControlRequest, sleBridgePortControlReqResult, sleBridgePortControlTimeStamp, sleBridgePortControlIndex, sleBridgePortControlPushInnertag
				 }
			STATUS current
			DESCRIPTION 
				"setBridgePortPushInnertag"
			::= { sleBridgePortNotification 17 }

		
		sleBridgePortPopInnertagChanged NOTIFICATION-TYPE
			OBJECTS { sleBridgePortControlRequest, sleBridgePortControlReqResult, sleBridgePortControlTimeStamp, sleBridgePortControlIndex, sleBridgePortControlPopInnertag
				 }
			STATUS current
			DESCRIPTION 
				"setBridgePortPopInnertag"
			::= { sleBridgePortNotification 18 }

		
		sleBridgePortInnertagChanged NOTIFICATION-TYPE
			OBJECTS { sleBridgePortControlRequest, sleBridgePortControlReqResult, sleBridgePortControlTimeStamp, sleBridgePortControlIndex, sleBridgePortControlInnertag
				 }
			STATUS current
			DESCRIPTION 
				"setBridgePortInnertag"
			::= { sleBridgePortNotification 19 }

		
		sleBridgePortPriorityChanged NOTIFICATION-TYPE
			OBJECTS { sleBridgePortControlRequest, sleBridgePortControlReqResult, sleBridgePortControlTimeStamp, sleBridgePortControlIndex, sleBridgePortControlPriority
				 }
			STATUS current
			DESCRIPTION 
				"setBridgePortPriority"
			::= { sleBridgePortNotification 20 }

		
		sleBridgePortInner2outerPriChanged NOTIFICATION-TYPE
			OBJECTS { sleBridgePortControlRequest, sleBridgePortControlReqResult, sleBridgePortControlTimeStamp, sleBridgePortControlIndex, sleBridgePortControlInner2outerPri
				 }
			STATUS current
			DESCRIPTION 
				"setBridgePortInner2outerPri"
			::= { sleBridgePortNotification 21 }

		
		sleBridgePortInner2outerVidChanged NOTIFICATION-TYPE
			OBJECTS { sleBridgePortControlRequest, sleBridgePortControlReqResult, sleBridgePortControlTimeStamp, sleBridgePortControlIndex, sleBridgePortControlInner2outerVid
				 }
			STATUS current
			DESCRIPTION 
				"setBridgePortInner2outerVid"
			::= { sleBridgePortNotification 22 }

		
		sleBridgePortMACLearningStatusChanged NOTIFICATION-TYPE
			OBJECTS { sleBridgePortControlRequest, sleBridgePortControlReqResult, sleBridgePortControlTimeStamp, sleBridgePortControlIndex, sleBridgePortControlMACLearningStatus
				 }
			STATUS current
			DESCRIPTION 
				"sleBridgePortMACLearningStatus"
			::= { sleBridgePortNotification 23 }

		
		sleBridgePortPortBridgeStatusChanged NOTIFICATION-TYPE
			OBJECTS { sleBridgePortControlRequest, sleBridgePortControlReqResult, sleBridgePortControlTimeStamp, sleBridgePortControlIndex, sleBridgePortControlPortBridgeStatus
				 }
			STATUS current
			DESCRIPTION 
				"sleBridgePortPortBridgeStatus"
			::= { sleBridgePortNotification 24 }

		
		sleBridgePortUnknownMcastBlockChanged NOTIFICATION-TYPE
			OBJECTS { sleBridgePortControlRequest, sleBridgePortControlTimeStamp, sleBridgePortControlReqResult, sleBridgePortControlIndex, sleBridgePortControlUnknownMcastBlock
				 }
			STATUS current
			DESCRIPTION 
				"Description."
			::= { sleBridgePortNotification 25 }

		
		sleBridgePortDescriptionChanged NOTIFICATION-TYPE
			OBJECTS { sleBridgePortControlRequest, sleBridgePortControlTimeStamp, sleBridgePortControlReqResult, sleBridgePortControlIndex, sleBridgePortControlDescription
				 }
			STATUS current
			DESCRIPTION 
				"Description."
			::= { sleBridgePortNotification 26 }

		
		sleBridgePortHoldTimeChanged NOTIFICATION-TYPE
			OBJECTS { sleBridgePortControlRequest, sleBridgePortControlTimeStamp, sleBridgePortControlReqResult, sleBridgePortControlIndex, sleBridgePortControlHoldTime
				 }
			STATUS current
			DESCRIPTION 
				"Description."
			::= { sleBridgePortNotification 27 }

		
		sleBridgePortMacAntiSpoofChanged NOTIFICATION-TYPE
			OBJECTS { sleBridgePortControlRequest, sleBridgePortControlTimeStamp, sleBridgePortControlReqResult, sleBridgePortControlIndex, sleBridgePortControlMacAntiSpoofing
				 }
			STATUS current
			DESCRIPTION 
				"Description."
			::= { sleBridgePortNotification 28 }

		
		sleBridgePortSwitchStatusChanged NOTIFICATION-TYPE
			OBJECTS { sleBridgePortControlRequest, sleBridgePortControlTimeStamp, sleBridgePortControlReqResult, sleBridgePortControlIndex, sleBridgePortControlSwitchStatus
				 }
			STATUS current
			DESCRIPTION 
				"setBridgePortSwitchStatus"
			::= { sleBridgePortNotification 29 }

		
		sleBridgePortSwitchModeChanged NOTIFICATION-TYPE
			OBJECTS { sleBridgePortControlRequest, sleBridgePortControlTimeStamp, sleBridgePortControlReqResult, sleBridgePortControlIndex, sleBridgePortControlSwitchMode, 
				sleBridgePortControlSwitchSubMode, sleBridgePortControlSwitchIngressFilter }
			STATUS current
			DESCRIPTION 
				"setBridgePortSwitchMode"
			::= { sleBridgePortNotification 30 }

		
		sleBridgePortSwitchDefaultVlanChanged NOTIFICATION-TYPE
			OBJECTS { sleBridgePortControlRequest, sleBridgePortControlTimeStamp, sleBridgePortControlReqResult, sleBridgePortControlIndex, sleBridgePortControlSwitchDefaultVlan
				 }
			STATUS current
			DESCRIPTION 
				"setBridgePortSwitchDefaultVlan"
			::= { sleBridgePortNotification 31 }

		
		sleBridgePortSwitchNativeVlanChanged NOTIFICATION-TYPE
			OBJECTS { sleBridgePortControlRequest, sleBridgePortControlTimeStamp, sleBridgePortControlReqResult, sleBridgePortControlIndex, sleBridgePortControlSwitchNativeVid
				 }
			STATUS current
			DESCRIPTION 
				"setBridgePortSwitchNativeVlan"
			::= { sleBridgePortNotification 32 }

		
		sleBridgePortSwitchAccFramTypeChanged NOTIFICATION-TYPE
			OBJECTS { sleBridgePortControlRequest, sleBridgePortControlTimeStamp, sleBridgePortControlReqResult, sleBridgePortControlIndex, sleBridgePortControlSwitchAccFrameType
				 }
			STATUS current
			DESCRIPTION 
				"setBridgePortSwitchAccFramType"
			::= { sleBridgePortNotification 33 }

		
		sleBridgePortSwitchAllowdVlanAdded NOTIFICATION-TYPE
			OBJECTS { sleBridgePortControlRequest, sleBridgePortControlTimeStamp, sleBridgePortControlReqResult, sleBridgePortControlIndex, sleBridgePortControlSwitchAllowedVlan, 
				sleBridgePortControlSwitchAllowedVlanEtag }
			STATUS current
			DESCRIPTION 
				"setBridgePortSwitchAddAllowdVlan"
			::= { sleBridgePortNotification 34 }

		
		sleBridgePortSwitchAllowdVlanDeleted NOTIFICATION-TYPE
			OBJECTS { sleBridgePortControlRequest, sleBridgePortControlTimeStamp, sleBridgePortControlReqResult, sleBridgePortControlIndex, sleBridgePortControlSwitchAllowedVlan, 
				sleBridgePortControlSwitchAllowedVlanEtag }
			STATUS current
			DESCRIPTION 
				"setBridgePortSwitchRemoveAllowdVlan"
			::= { sleBridgePortNotification 35 }

		
		sleBridgePortSwitchStaticChannelChanged NOTIFICATION-TYPE
			OBJECTS { sleBridgePortControlRequest, sleBridgePortControlTimeStamp, sleBridgePortControlReqResult, sleBridgePortControlIndex, sleBridgePortControlSwitchStaticChannelGroup
				 }
			STATUS current
			DESCRIPTION 
				"setBridgePortSwitchStaticChannel"
			::= { sleBridgePortNotification 36 }

		
		sleBridgePortSwitchChannelLoadbalanceChanged NOTIFICATION-TYPE
			OBJECTS { sleBridgePortControlRequest, sleBridgePortControlTimeStamp, sleBridgePortControlReqResult, sleBridgePortControlIndex, sleBridgePortControlSwitchChannelLoadbalance
				 }
			STATUS current
			DESCRIPTION 
				"setBridgePortSwitchChannelLoadbalance"
			::= { sleBridgePortNotification 37 }

		
--  			::= { sle 4 }
-- 
-- Node definitions
-- 
-- 1.3.6.1.4.1.6296.9.8.3
		sleVlan OBJECT IDENTIFIER ::= { sleBridge 3 }

		
--  1.3.6.1.4.1.6296.9.8.3.1
		sleVlanTable OBJECT-TYPE
			SYNTAX SEQUENCE OF SleVlanEntry
			MAX-ACCESS not-accessible
			STATUS current
			DESCRIPTION
				" sle vlan table"
			::= { sleVlan 1 }

		
--  1.3.6.1.4.1.6296.9.8.3.1.1
		sleVlanEntry OBJECT-TYPE
			SYNTAX SleVlanEntry
			MAX-ACCESS not-accessible
			STATUS current
			DESCRIPTION
				" key: sleVlanIndex"
			INDEX { sleVlanIndex }
			::= { sleVlanTable 1 }

		
		SleVlanEntry ::=
			SEQUENCE { 
				sleVlanIndex
					INTEGER,
				sleVlanIfIndex
					Integer32,
				sleVlanName
					OCTET STRING,
				sleVlanStatus
					INTEGER,
				sleVlanEgressPorts
					OCTET STRING,
				sleVlanUnTaggedPorts
					OCTET STRING,
				sleVlanCreationTime
					TimeTicks,
				sleVlanAgeingTime
					INTEGER,
				sleVlanTagTxCounter
					Counter64,
				sleVlanDescription
					OCTET STRING,
				sleVlanElineEnable
					INTEGER,
				sleVlanOperStatus
					INTEGER,
				sleVlanMtu
					Integer32
			 }

--  1.3.6.1.4.1.6296.9.8.3.1.1.1
		sleVlanIndex OBJECT-TYPE
			SYNTAX INTEGER (1..4094)
			MAX-ACCESS read-only
			STATUS current
			DESCRIPTION
				"A vlan-identifier."
			::= { sleVlanEntry 1 }

		
		sleVlanIfIndex OBJECT-TYPE
			SYNTAX Integer32
			MAX-ACCESS read-only
			STATUS current
			DESCRIPTION
				"Same as ifIndex (for appropriated ifTable entries)."
			::= { sleVlanEntry 2 }

		
--  1.3.6.1.4.1.6296.9.8.3.1.1.2
		sleVlanName OBJECT-TYPE
			SYNTAX OCTET STRING
			MAX-ACCESS read-only
			STATUS current
			DESCRIPTION
				"A descriptional name for that vlan."
			::= { sleVlanEntry 3 }

		
--  1.3.6.1.4.1.6296.9.8.3.1.1.3
		sleVlanStatus OBJECT-TYPE
			SYNTAX INTEGER
				{
				static(1),
				dynamic(2)
				}
			MAX-ACCESS read-only
			STATUS current
			DESCRIPTION
				"static, in future gvrp"
			::= { sleVlanEntry 4 }

		
--  1.3.6.1.4.1.6296.9.8.3.1.1.4
		sleVlanEgressPorts OBJECT-TYPE
			SYNTAX OCTET STRING
			MAX-ACCESS read-only
			STATUS current
			DESCRIPTION
				"Portlist for all member of this VLAN, they will send tagged or untagged frames.
				The octet string is a list of pairs of octets each identify
				an sleBridgePortIndex. The least significant byte is the
				second octet."
			::= { sleVlanEntry 5 }

		
--  1.3.6.1.4.1.6296.9.8.3.1.1.5
		sleVlanUnTaggedPorts OBJECT-TYPE
			SYNTAX OCTET STRING
			MAX-ACCESS read-only
			STATUS current
			DESCRIPTION
				"Portlist for members of this Vlan they will send only untagged frames.
				The octet string is a list of pairs of octets each identify
				an sleBridgePortIndex. The least significant byte is the second
				octet."
			::= { sleVlanEntry 6 }

		
--  1.3.6.1.4.1.6296.9.8.3.1.1.8
		sleVlanCreationTime OBJECT-TYPE
			SYNTAX TimeTicks
			MAX-ACCESS read-only
			STATUS current
			DESCRIPTION
				"Only useful in case of gvrp."
			::= { sleVlanEntry 7 }

		
		sleVlanAgeingTime OBJECT-TYPE
			SYNTAX INTEGER (-1 | 0 | 10..21474830)
			MAX-ACCESS read-only
			STATUS current
			DESCRIPTION
				"The ageing time per vlan"
			::= { sleVlanEntry 8 }

		
		sleVlanTagTxCounter OBJECT-TYPE
			SYNTAX Counter64
			MAX-ACCESS read-only
			STATUS current
			DESCRIPTION
				"The VLAN tag tx counter."
			::= { sleVlanEntry 9 }

		
		sleVlanDescription OBJECT-TYPE
			SYNTAX OCTET STRING (SIZE (0..32))
			MAX-ACCESS read-only
			STATUS current
			DESCRIPTION
				"createVlan:
				(sleVlanControlIndex)
				sleVlanControlName
				sleVlanControlMulticastPermision"
			::= { sleVlanEntry 10 }

		
		sleVlanElineEnable OBJECT-TYPE
			SYNTAX INTEGER
				{
				disable(0),
				enable(1)
				}
			MAX-ACCESS read-only
			STATUS current
			DESCRIPTION
				"Indicate whether E-line service enable or not"
			::= { sleVlanEntry 11 }

		
		sleVlanOperStatus OBJECT-TYPE
			SYNTAX INTEGER
				{
				invalid(0),
				inactive(1),
				active(2)
				}
			MAX-ACCESS read-only
			STATUS current
			DESCRIPTION
				"The Vlan operation status."
			::= { sleVlanEntry 12 }

		
		sleVlanMtu OBJECT-TYPE
			SYNTAX Integer32
			MAX-ACCESS read-only
			STATUS current
			DESCRIPTION
				"The Vlan MTU."
			::= { sleVlanEntry 13 }

		
--  1.3.6.1.4.1.6296.9.8.3.2
		sleVlanControl OBJECT IDENTIFIER ::= { sleVlan 2 }

		
--   Node definitions
-- 
-- 1.3.6.1.4.1.6296.9.8.3.2.1
		sleVlanControlRequest OBJECT-TYPE
			SYNTAX INTEGER
				{
				createVlan(1),
				destroyVlan(2),
				setVlanPortProfile(3),
				setVlanAgeingTime(4),
				createVlanRange(5),
				setVlanDesc(6),
				createElineVlan(7),
				setVlanOperStatus(8),
				setVlanMtu(9)
				}
			MAX-ACCESS read-write
			STATUS current
			DESCRIPTION
				"
				createVlan:
				(sleVlanControlIndex)
				sleVlanControlName
				sleVlanControlMulticastPermision
				
				destroyVlan:
				sleVlanControlIndex
				
				setVlanPortProfile:
				sleVlanControlIndex
				sleVlanControlEgressPorts
				sleVlanControlUnTaggedPorts
				
				setVlanMulticastPermission:
				sleVlanControlIndex
				sleVlanControlMulticastPermission
				
				"
			::= { sleVlanControl 1 }

		
--  1.3.6.1.4.1.6296.9.8.3.2.3
		sleVlanControlStatus OBJECT-TYPE
			SYNTAX SleControlStatusType
			MAX-ACCESS read-only
			STATUS current
			DESCRIPTION
				"The status of a user command. 
				"
			::= { sleVlanControl 2 }

		
--  1.3.6.1.4.1.6296.9.8.3.2.4
		sleVlanControlTimer OBJECT-TYPE
			SYNTAX Gauge32
			MAX-ACCESS read-write
			STATUS current
			DESCRIPTION
				"The maximum wait time for the manager for a long running user command. 
				"
			::= { sleVlanControl 3 }

		
--  1.3.6.1.4.1.6296.9.8.3.2.6
		sleVlanControlTimeStamp OBJECT-TYPE
			SYNTAX TimeTicks
			MAX-ACCESS read-only
			STATUS current
			DESCRIPTION
				"The time stamp of the last command (end of command)."
			::= { sleVlanControl 4 }

		
--  1.3.6.1.4.1.6296.9.8.3.2.5
		sleVlanControlReqResult OBJECT-TYPE
			SYNTAX SleControlRequestResultType
			MAX-ACCESS read-only
			STATUS current
			DESCRIPTION
				"The result of the last user command."
			::= { sleVlanControl 5 }

		
--  1.3.6.1.4.1.6296.9.8.3.2.2
		sleVlanControlIndex OBJECT-TYPE
			SYNTAX Integer32 (1..4094)
			MAX-ACCESS read-write
			STATUS current
			DESCRIPTION
				"Vlan's ID
				"
			::= { sleVlanControl 6 }

		
--  1.3.6.1.4.1.6296.9.8.3.2.7
		sleVlanControlName OBJECT-TYPE
			SYNTAX OCTET STRING
			MAX-ACCESS read-write
			STATUS current
			DESCRIPTION
				"Vlan's name."
			::= { sleVlanControl 7 }

		
--  1.3.6.1.4.1.6296.9.8.3.2.8
		sleVlanControlEgressPorts OBJECT-TYPE
			SYNTAX OCTET STRING
			MAX-ACCESS read-write
			STATUS current
			DESCRIPTION
				" Portlist for all member of this VLAN, they will send tagged or untagged frames. The OctetString is a list of pairs of octets each identify an sheBridgePortIndex. The least significant byte is the second octet."
			::= { sleVlanControl 8 }

		
--  1.3.6.1.4.1.6296.9.8.3.2.9
		sleVlanControlUnTaggedPorts OBJECT-TYPE
			SYNTAX OCTET STRING
			MAX-ACCESS read-write
			STATUS current
			DESCRIPTION
				" Portlist for members of this Vlan they will send only untagged frames. The OctetString is a list of pairs of octets each identify an sleBridgePortIndex. The least significant byte is the second octet."
			::= { sleVlanControl 9 }

		
		sleVlanControlAgeingTime OBJECT-TYPE
			SYNTAX INTEGER (-1 | 0 | 10..21474830)
			MAX-ACCESS read-write
			STATUS current
			DESCRIPTION
				"The ageing time per vlan
				(supported only model 5924N)"
			::= { sleVlanControl 10 }

		
		sleVlanControlIndexTo OBJECT-TYPE
			SYNTAX Integer32 (1..4094)
			MAX-ACCESS read-write
			STATUS current
			DESCRIPTION
				"Vlan's ID
				"
			::= { sleVlanControl 11 }

		
		sleVlanControlDescription OBJECT-TYPE
			SYNTAX OCTET STRING (SIZE (0..32))
			MAX-ACCESS read-write
			STATUS current
			DESCRIPTION
				"createVlan:
				(sleVlanControlIndex)
				sleVlanControlName
				sleVlanControlMulticastPermision"
			::= { sleVlanControl 12 }

		
		sleVlanControlElineEnable OBJECT-TYPE
			SYNTAX INTEGER
				{
				disable(0),
				enable(1)
				}
			MAX-ACCESS read-write
			STATUS current
			DESCRIPTION
				"Indicate whether E-line service enable or not"
			::= { sleVlanControl 13 }

		
		sleVlanControlOperStatus OBJECT-TYPE
			SYNTAX INTEGER
				{
				invalid(0),
				inactive(1),
				active(2)
				}
			MAX-ACCESS read-write
			STATUS current
			DESCRIPTION
				"The Vlan operation status."
			::= { sleVlanControl 14 }

		
		sleVlanControlMtu OBJECT-TYPE
			SYNTAX Integer32
			MAX-ACCESS read-write
			STATUS current
			DESCRIPTION
				"The Vlan MTU."
			::= { sleVlanControl 15 }

		
--  1.3.6.1.4.1.6296.9.8.3.3
		sleVlanNotification OBJECT IDENTIFIER ::= { sleVlan 3 }

		
--  1.3.6.1.4.1.6296.9.8.3.3.1
		sleVlanCreated NOTIFICATION-TYPE
			OBJECTS { sleVlanName, sleVlanEgressPorts, sleVlanUnTaggedPorts, sleVlanControlRequest, sleVlanControlTimeStamp, 
				sleVlanControlReqResult, sleVlanIfIndex, sleVlanStatus }
			STATUS current
			DESCRIPTION 
				"Description."
			::= { sleVlanNotification 1 }

		
--  1.3.6.1.4.1.6296.9.8.3.3.2
		sleVlanDestroyed NOTIFICATION-TYPE
			OBJECTS { sleVlanControlRequest, sleVlanControlTimeStamp, sleVlanControlReqResult, sleVlanControlIndex }
			STATUS current
			DESCRIPTION 
				" "
			::= { sleVlanNotification 2 }

		
--  1.3.6.1.4.1.6296.9.8.3.3.3
		sleVlanPortProfileChanged NOTIFICATION-TYPE
			OBJECTS { sleVlanEgressPorts, sleVlanUnTaggedPorts, sleVlanControlRequest, sleVlanControlTimeStamp, sleVlanControlReqResult
				 }
			STATUS current
			DESCRIPTION 
				" "
			::= { sleVlanNotification 3 }

		
		sleVlanAgeingTimeChanged NOTIFICATION-TYPE
			OBJECTS { sleVlanControlRequest, sleVlanControlTimeStamp, sleVlanControlAgeingTime, sleVlanControlIndex, sleVlanControlReqResult
				 }
			STATUS current
			DESCRIPTION 
				"Description."
			::= { sleVlanNotification 4 }

		
		sleVlanRangeCreated NOTIFICATION-TYPE
			OBJECTS { sleVlanControlRequest, sleVlanControlTimeStamp, sleVlanControlReqResult, sleVlanControlIndex, sleVlanControlIndexTo
				 }
			STATUS current
			DESCRIPTION 
				"Description."
			::= { sleVlanNotification 5 }

		
		sleVlanDescriptionChanged NOTIFICATION-TYPE
			OBJECTS { sleVlanControlRequest, sleVlanControlTimeStamp, sleVlanControlReqResult, sleVlanControlIndex, sleVlanControlDescription
				 }
			STATUS current
			DESCRIPTION 
				"setVlanDesc"
			::= { sleVlanNotification 6 }

		
		sleVlanElineVlanCreated NOTIFICATION-TYPE
			OBJECTS { sleVlanControlRequest, sleVlanControlTimeStamp, sleVlanControlReqResult, sleVlanControlIndex, sleVlanControlElineEnable
				 }
			STATUS current
			DESCRIPTION 
				"createElineVlan"
			::= { sleVlanNotification 7 }

		
		sleVlanOperStatusChagned NOTIFICATION-TYPE
			OBJECTS { sleVlanControlRequest, sleVlanControlTimeStamp, sleVlanControlReqResult, sleVlanControlIndex, sleVlanControlOperStatus
				 }
			STATUS current
			DESCRIPTION 
				"setVlanOperStatus"
			::= { sleVlanNotification 8 }

		
		sleVlanMtuChagned NOTIFICATION-TYPE
			OBJECTS { sleVlanControlRequest, sleVlanControlTimeStamp, sleVlanControlReqResult, sleVlanControlIndex, sleVlanControlMtu
				 }
			STATUS current
			DESCRIPTION 
				"sleVlanMtuChanged"
			::= { sleVlanNotification 9 }

		
--   sleVlanMap Group
-- 1.3.6.1.4.1.6296.9.8.4
		sleVlanMap OBJECT IDENTIFIER ::= { sleBridge 4 }

		
--  1.3.6.1.4.1.6296.9.8.4.1
		sleVlanMapTable OBJECT-TYPE
			SYNTAX SEQUENCE OF SleVlanMapEntry
			MAX-ACCESS not-accessible
			STATUS current
			DESCRIPTION
				"vlan map table."
			::= { sleVlanMap 1 }

		
--  1.3.6.1.4.1.6296.9.8.4.1.1
		sleVlanMapEntry OBJECT-TYPE
			SYNTAX SleVlanMapEntry
			MAX-ACCESS not-accessible
			STATUS current
			DESCRIPTION
				" key: sleVlanIndex"
			INDEX { sleVlanIndex }
			::= { sleVlanMapTable 1 }

		
		SleVlanMapEntry ::=
			SEQUENCE { 
				sleVlanMapFid
					Unsigned32,
				sleVlanMapStpId
					Unsigned32,
				sleVlanMapErpDomainId
					Unsigned32
			 }

--  1.3.6.1.4.1.6296.9.8.4.1.1.2
		sleVlanMapFid OBJECT-TYPE
			SYNTAX Unsigned32
			MAX-ACCESS read-only
			STATUS current
			DESCRIPTION
				"Index of the used Filtering Table entry."
			::= { sleVlanMapEntry 1 }

		
--  1.3.6.1.4.1.6296.9.8.4.1.1.3
		sleVlanMapStpId OBJECT-TYPE
			SYNTAX Unsigned32
			MAX-ACCESS read-only
			STATUS current
			DESCRIPTION
				"Index of the used STP instance."
			::= { sleVlanMapEntry 2 }

		
--  1.3.6.1.4.1.6296.9.8.4.1.1.4
		sleVlanMapErpDomainId OBJECT-TYPE
			SYNTAX Unsigned32
			MAX-ACCESS read-only
			STATUS current
			DESCRIPTION
				"Index of the used Erp Domain."
			::= { sleVlanMapEntry 3 }

		
--  1.3.6.1.4.1.6296.9.8.4.2
		sleVlanMapControl OBJECT IDENTIFIER ::= { sleVlanMap 2 }

		
--   Node definitions
-- 
-- 1.3.6.1.4.1.6296.9.8.4.2.1
		sleVlanMapControlRequest OBJECT-TYPE
			SYNTAX INTEGER
				{
				setVlanMapFid(1),
				setVlanMapStpId(2),
				setVlanMapErpDomainId(3)
				}
			MAX-ACCESS read-write
			STATUS current
			DESCRIPTION
				"
				setVlanMapFid:
				sleVlanMapControlIndex
				sleVlanMapFid
				
				setVlanMapStpId:
				sleVlanMapControlIndex
				sleVlanMapStpId
				
				setVlanMapErpDomainId:
				sleVlanMapControlIndex
				sleVlanMapErpDomainId
				
				"
			::= { sleVlanMapControl 1 }

		
--  1.3.6.1.4.1.6296.9.8.4.2.3
		sleVlanMapControlStatus OBJECT-TYPE
			SYNTAX SleControlStatusType
			MAX-ACCESS read-only
			STATUS current
			DESCRIPTION
				"The status of a user command. 
				"
			::= { sleVlanMapControl 2 }

		
--  1.3.6.1.4.1.6296.9.8.4.2.4
		sleVlanMapControlTimer OBJECT-TYPE
			SYNTAX Gauge32
			MAX-ACCESS read-write
			STATUS current
			DESCRIPTION
				"The maximum wait time for the manager for a long running user command. 
				"
			::= { sleVlanMapControl 3 }

		
--  1.3.6.1.4.1.6296.9.8.4.2.6
		sleVlanMapControlTimeStamp OBJECT-TYPE
			SYNTAX TimeTicks
			MAX-ACCESS read-only
			STATUS current
			DESCRIPTION
				"The time stamp of the last command (end of command)."
			::= { sleVlanMapControl 4 }

		
--  1.3.6.1.4.1.6296.9.8.4.2.5
		sleVlanMapControlReqResult OBJECT-TYPE
			SYNTAX SleControlRequestResultType
			MAX-ACCESS read-only
			STATUS current
			DESCRIPTION
				"The result of the last user command."
			::= { sleVlanMapControl 5 }

		
--  1.3.6.1.4.1.6296.9.8.4.2.2
		sleVlanMapControlIndex OBJECT-TYPE
			SYNTAX Integer32 (1..4094)
			MAX-ACCESS read-write
			STATUS current
			DESCRIPTION
				"vlan map index."
			::= { sleVlanMapControl 6 }

		
--  1.3.6.1.4.1.6296.9.8.4.2.7
		sleVlanMapControlFid OBJECT-TYPE
			SYNTAX Unsigned32
			MAX-ACCESS read-write
			STATUS current
			DESCRIPTION
				" FDB identifier"
			::= { sleVlanMapControl 7 }

		
--  1.3.6.1.4.1.6296.9.8.4.2.8
		sleVlanMapControlStpId OBJECT-TYPE
			SYNTAX Unsigned32
			MAX-ACCESS read-write
			STATUS current
			DESCRIPTION
				" STP Instance Identifier"
			::= { sleVlanMapControl 8 }

		
--  1.3.6.1.4.1.6296.9.8.4.2.9
		sleVlanMapControlErpDomainId OBJECT-TYPE
			SYNTAX Unsigned32
			MAX-ACCESS read-write
			STATUS current
			DESCRIPTION
				" The Erp Domain ID."
			::= { sleVlanMapControl 9 }

		
--  1.3.6.1.4.1.6296.9.8.4.3
		sleVlanMapNotification OBJECT IDENTIFIER ::= { sleVlanMap 3 }

		
--  1.3.6.1.4.1.6296.9.8.4.3.1
		sleVlanMapFidChanged NOTIFICATION-TYPE
			OBJECTS { sleVlanMapControlTimeStamp, sleVlanMapControlReqResult, sleVlanMapControlRequest, sleVlanMapFid }
			STATUS current
			DESCRIPTION 
				" "
			::= { sleVlanMapNotification 1 }

		
--  1.3.6.1.4.1.6296.9.8.4.3.2
		sleVlanMapStpIdChanged NOTIFICATION-TYPE
			OBJECTS { sleVlanMapStpId, sleVlanMapControlRequest, sleVlanMapControlTimeStamp, sleVlanMapControlReqResult }
			STATUS current
			DESCRIPTION 
				" "
			::= { sleVlanMapNotification 2 }

		
--  1.3.6.1.4.1.6296.9.8.4.3.3
		sleVlanMapErpDomainIdChanged NOTIFICATION-TYPE
			OBJECTS { sleVlanMapErpDomainId, sleVlanMapControlRequest, sleVlanMapControlTimeStamp, sleVlanMapControlReqResult }
			STATUS current
			DESCRIPTION 
				" "
			::= { sleVlanMapNotification 3 }

		
-- 
--   Node definitions
-- 
		sleStp OBJECT IDENTIFIER ::= { sleBridge 5 }

		
		sleStpInfo OBJECT IDENTIFIER ::= { sleStp 1 }

		
		sleStpOperationMode OBJECT-TYPE
			SYNTAX INTEGER
				{
				stp(0),
				rstp(1),
				mstp(3),
				pvstp(4),
				pvrstp(5),
				pvrstpPlus(6),
				pvstpPlus(7)
				}
			MAX-ACCESS read-only
			STATUS current
			DESCRIPTION
				"The operation mode of running the STP at the switch."
			::= { sleStpInfo 1 }

		
		sleStpFormatSelector OBJECT-TYPE
			SYNTAX INTEGER (0..65535)
			MAX-ACCESS read-only
			STATUS current
			DESCRIPTION
				"The MST configuration format selector."
			::= { sleStpInfo 2 }

		
		sleStpConfigureName OBJECT-TYPE
			SYNTAX OCTET STRING (SIZE (0..32))
			MAX-ACCESS read-write
			STATUS current
			DESCRIPTION
				"The MST configuration name of at most 32 characters."
			::= { sleStpInfo 3 }

		
		sleStpRevisionLevel OBJECT-TYPE
			SYNTAX INTEGER (0..65535)
			MAX-ACCESS read-only
			STATUS current
			DESCRIPTION
				"The MST configuration revision."
			::= { sleStpInfo 4 }

		
		sleStpFwdDelay OBJECT-TYPE
			SYNTAX INTEGER (4..300)
			MAX-ACCESS read-only
			STATUS current
			DESCRIPTION
				"The STP bridge forward delay."
			::= { sleStpInfo 5 }

		
		sleStpHelloTime OBJECT-TYPE
			SYNTAX INTEGER (1..10)
			MAX-ACCESS read-only
			STATUS current
			DESCRIPTION
				"The STP bridge hello time."
			::= { sleStpInfo 6 }

		
		sleStpMaxAge OBJECT-TYPE
			SYNTAX INTEGER (6..40)
			MAX-ACCESS read-only
			STATUS current
			DESCRIPTION
				"The STP bridge max age."
			::= { sleStpInfo 7 }

		
		sleStpMaxHops OBJECT-TYPE
			SYNTAX INTEGER (1..40)
			MAX-ACCESS read-only
			STATUS current
			DESCRIPTION
				"The MST bridge max hops."
			::= { sleStpInfo 8 }

		
		sleStpExtRootBridgeId OBJECT-TYPE
			SYNTAX OCTET STRING (SIZE (8))
			MAX-ACCESS read-only
			STATUS current
			DESCRIPTION
				"The MST CST root identifier."
			::= { sleStpInfo 9 }

		
		sleStpExtPathcost OBJECT-TYPE
			SYNTAX Unsigned32
			MAX-ACCESS read-only
			STATUS current
			DESCRIPTION
				"The MST CST root path cost."
			::= { sleStpInfo 10 }

		
		sleStpBpduGuardMode OBJECT-TYPE
			SYNTAX INTEGER
				{
				disable(0),
				enable(1)
				}
			MAX-ACCESS read-only
			STATUS current
			DESCRIPTION
				"Indicates the mode of Bpdu Guard Feature on the switch. 
				 	When the system with Bpdu Guard enabled 
				 	receives a BPDU from any port, that port is 
				 	immediately disabled.  	 
				 	
				 	disable -- the Bpdu Guard feature is disabled on this
					           switch.
				 	
				 	enable -- the Bpdu Guard feature is enabled on this
					           switch. 
				 	
				 	           Whether the Bpdu Guard feature is enabled
				 	           or not on this switch depends on the object
				 	           value of sleStpControlBpduGuardMode."
			DEFVAL { 0 }
			::= { sleStpInfo 11 }

		
		sleStpBpduGuardAutoRcvMode OBJECT-TYPE
			SYNTAX INTEGER
				{
				disable(0),
				enable(1)
				}
			MAX-ACCESS read-only
			STATUS current
			DESCRIPTION
				"Indicates the automatic recovery mode for the ports disabled by Bpdu Guard.
				 	
				 	disable -- the Bpdu Guard Auto Recovery feature is disabled on this
					           switch.
				 	
				 	enable -- the Bpdu Guard Auto Recovery feature is enabled on this
					           switch. 
				 	
				 	           Whether the Bpdu Guard Auto Recovery feature is enabled
				 	           or not on this switch depends on the object
				 	           value of sleStpControlBpduGuardAutoRcvMode."
			DEFVAL { 0 }
			::= { sleStpInfo 12 }

		
		sleStpBpduGuardAutoRcvTime OBJECT-TYPE
			SYNTAX INTEGER (10..1000000)
			MAX-ACCESS read-only
			STATUS current
			DESCRIPTION
				"Indicates the automatic recovery time for the ports disabled by Bpdu Guard.
				 	Unit: second
				 	
				The Bpdu Guard Auto Recovery time depends on the object value 
				 	of sleStpControlBpduGuardAutoRcvTime."
			DEFVAL { 300 }
			::= { sleStpInfo 13 }

		
		sleStpControl OBJECT IDENTIFIER ::= { sleStp 2 }

		
		sleStpControlRequest OBJECT-TYPE
			SYNTAX INTEGER
				{
				setStpOperationMode(1),
				setStpConfigureProfile(2),
				setStpTimerProfile(3),
				setStpBpduGuardProfile(4)
				}
			MAX-ACCESS read-write
			STATUS current
			DESCRIPTION
				"
				setStpOperationMode:
				sleStpControlOperationMode
				
				setStpConfigureProfile:
				sleStpControlConfigureName
				sleStpControlRevisionLevel
				
				setStpTimerProfile
				sleStpControlFwdDelay
				sleStpControlHelloTime
				sleStpControlMaxAge
				sleStpControlMaxHops
				"
			::= { sleStpControl 1 }

		
		sleStpControlStatus OBJECT-TYPE
			SYNTAX SleControlStatusType
			MAX-ACCESS read-only
			STATUS current
			DESCRIPTION
				"The status of a user command. 
				"
			::= { sleStpControl 2 }

		
		sleStpControlTimer OBJECT-TYPE
			SYNTAX Gauge32
			MAX-ACCESS read-write
			STATUS current
			DESCRIPTION
				"The maximum wait time for the manager for a long running user command. 
				"
			::= { sleStpControl 3 }

		
		sleStpControlTimeStamp OBJECT-TYPE
			SYNTAX TimeTicks
			MAX-ACCESS read-only
			STATUS current
			DESCRIPTION
				"The time stamp of the last command (end of command)."
			::= { sleStpControl 4 }

		
		sleStpControlReqResult OBJECT-TYPE
			SYNTAX SleControlRequestResultType
			MAX-ACCESS read-only
			STATUS current
			DESCRIPTION
				"The result of the last user command."
			::= { sleStpControl 5 }

		
		sleStpControlOperationMode OBJECT-TYPE
			SYNTAX INTEGER
				{
				stp(0),
				rstp(1),
				mstp(3),
				pvstp(4),
				pvrstp(5),
				pvrstpPlus(6),
				pvstpPlus(7)
				}
			MAX-ACCESS read-write
			STATUS current
			DESCRIPTION
				" The operation mode of running the STP at the switch."
			::= { sleStpControl 6 }

		
		sleStpControlConfigureName OBJECT-TYPE
			SYNTAX OCTET STRING (SIZE (0..32))
			MAX-ACCESS read-write
			STATUS current
			DESCRIPTION
				" The MST configuration name of at most 32 characters."
			::= { sleStpControl 7 }

		
		sleStpControlRevisionLevel OBJECT-TYPE
			SYNTAX INTEGER (0..65535)
			MAX-ACCESS read-write
			STATUS current
			DESCRIPTION
				" The MST configuration revision."
			::= { sleStpControl 8 }

		
		sleStpControlFwdDelay OBJECT-TYPE
			SYNTAX INTEGER (4..30)
			MAX-ACCESS read-write
			STATUS current
			DESCRIPTION
				" The STP bridge forward delay."
			::= { sleStpControl 9 }

		
		sleStpControlHelloTime OBJECT-TYPE
			SYNTAX INTEGER (1..10)
			MAX-ACCESS read-write
			STATUS current
			DESCRIPTION
				" The STP bridge hello time."
			::= { sleStpControl 10 }

		
		sleStpControlMaxAge OBJECT-TYPE
			SYNTAX INTEGER (4..60)
			MAX-ACCESS read-write
			STATUS current
			DESCRIPTION
				" The STP bridge max age."
			::= { sleStpControl 11 }

		
		sleStpControlMaxHops OBJECT-TYPE
			SYNTAX INTEGER (1..40)
			MAX-ACCESS read-write
			STATUS current
			DESCRIPTION
				" The MST bridge max hops."
			::= { sleStpControl 12 }

		
		sleStpControlBpduGuardMode OBJECT-TYPE
			SYNTAX INTEGER
				{
				disable(0),
				enable(1)
				}
			MAX-ACCESS read-write
			STATUS current
			DESCRIPTION
				"Configures the mode of Bpdu Guard Feature on the switch. 
				 	When the system with Bpdu Guard enabled 
				 	receives a BPDU from any port, that port is 
				 	immediately disabled.  	 
				 	
				 	disable -- the Bpdu Guard feature is disabled on this
					           switch.
				 	
				 	enable -- the Bpdu Guard feature is enabled on this
					           switch. 
				"
			DEFVAL { 0 }
			::= { sleStpControl 13 }

		
		sleStpControlBpduGuardAutoRcvMode OBJECT-TYPE
			SYNTAX INTEGER
				{
				disable(0),
				enable(1)
				}
			MAX-ACCESS read-write
			STATUS current
			DESCRIPTION
				"Configures the automatic recovery mode for the ports disabled by Bpdu Guard.
				 	
				 	disable -- the Bpdu Guard Auto Recovery feature is disabled on this
					           switch.
				 	
				 	enable -- the Bpdu Guard Auto Recovery feature is enabled on this
					           switch. "
			DEFVAL { 0 }
			::= { sleStpControl 14 }

		
		sleStpControlBpduGuardAutoRcvTime OBJECT-TYPE
			SYNTAX INTEGER (10..1000000)
			MAX-ACCESS read-write
			STATUS current
			DESCRIPTION
				"Configures the automatic recovery time for the ports disabled by Bpdu Guard.
				 	Unit: second"
			DEFVAL { 300 }
			::= { sleStpControl 15 }

		
		sleStpNotification OBJECT IDENTIFIER ::= { sleStp 3 }

		
		sleStpOperationModeChanged NOTIFICATION-TYPE
			OBJECTS { sleStpControlRequest, sleStpControlReqResult, sleStpControlTimeStamp, sleStpOperationMode }
			STATUS current
			DESCRIPTION 
				" "
			::= { sleStpNotification 1 }

		
		sleStpConfigureProfileChanged NOTIFICATION-TYPE
			OBJECTS { sleStpControlRequest, sleStpControlReqResult, sleStpControlTimeStamp, sleStpRevisionLevel, sleStpConfigureName
				 }
			STATUS current
			DESCRIPTION 
				" "
			::= { sleStpNotification 2 }

		
		sleStpTimerProfileChanged NOTIFICATION-TYPE
			OBJECTS { sleStpControlRequest, sleStpControlReqResult, sleStpControlTimeStamp, sleStpFwdDelay, sleStpHelloTime, 
				sleStpMaxAge, sleStpMaxHops }
			STATUS current
			DESCRIPTION 
				" "
			::= { sleStpNotification 3 }

		
		sleStpBpduGuardProfileChanged NOTIFICATION-TYPE
			OBJECTS { sleStpControlRequest, sleStpControlReqResult, sleStpControlTimeStamp, sleStpBpduGuardMode, sleStpBpduGuardAutoRcvMode, 
				sleStpBpduGuardAutoRcvTime }
			STATUS current
			DESCRIPTION 
				" "
			::= { sleStpNotification 4 }

		
		sleStpInstance OBJECT IDENTIFIER ::= { sleBridge 6 }

		
		sleStpInstanceTable OBJECT-TYPE
			SYNTAX SEQUENCE OF SleStpInstanceEntry
			MAX-ACCESS not-accessible
			STATUS current
			DESCRIPTION
				" STP instance table."
			::= { sleStpInstance 1 }

		
		sleStpInstanceEntry OBJECT-TYPE
			SYNTAX SleStpInstanceEntry
			MAX-ACCESS not-accessible
			STATUS current
			DESCRIPTION
				" key: sleStpInstanceIndex"
			INDEX { sleStpInstanceIndex }
			::= { sleStpInstanceTable 1 }

		
		SleStpInstanceEntry ::=
			SEQUENCE { 
				sleStpInstanceIndex
					INTEGER,
				sleStpInstanceEnable
					INTEGER,
				sleStpInstancePriority
					Integer32,
				sleStpInstanceRootBridgeId
					OCTET STRING,
				sleStpInstanceRootPathcost
					Integer32,
				sleStpInstanceDesignatedBridgeId
					OCTET STRING,
				sleStpInstanceDesignatedPortId
					INTEGER,
				sleStpInstanceRootPortId
					INTEGER,
				sleStpInstanceFwdDelay
					INTEGER,
				sleStpInstanceHelloTime
					INTEGER,
				sleStpInstanceMaxAge
					INTEGER,
				sleStpInstanceRemainHops
					Integer32,
				sleStpInstanceBrFwdDelay
					INTEGER,
				sleStpInstanceBrHelloTime
					INTEGER,
				sleStpInstanceBrMaxAge
					INTEGER
			 }

		sleStpInstanceIndex OBJECT-TYPE
			SYNTAX INTEGER (0..4096)
			MAX-ACCESS read-only
			STATUS current
			DESCRIPTION
				"The STP instance ID."
			::= { sleStpInstanceEntry 1 }

		
		sleStpInstanceEnable OBJECT-TYPE
			SYNTAX INTEGER
				{
				enable(0),
				disable(1)
				}
			MAX-ACCESS read-only
			STATUS current
			DESCRIPTION
				"The enabled/disabled status of the pvst."
			::= { sleStpInstanceEntry 2 }

		
		sleStpInstancePriority OBJECT-TYPE
			SYNTAX Integer32
			MAX-ACCESS read-only
			STATUS current
			DESCRIPTION
				"The bridge priority."
			::= { sleStpInstanceEntry 3 }

		
		sleStpInstanceRootBridgeId OBJECT-TYPE
			SYNTAX OCTET STRING (SIZE (8))
			MAX-ACCESS read-only
			STATUS current
			DESCRIPTION
				"The STP designated root bridge identifier in a specific instance. Size: 8."
			::= { sleStpInstanceEntry 4 }

		
		sleStpInstanceRootPathcost OBJECT-TYPE
			SYNTAX Integer32
			MAX-ACCESS read-only
			STATUS current
			DESCRIPTION
				"The STP root path cost in a specific instance."
			::= { sleStpInstanceEntry 5 }

		
		sleStpInstanceDesignatedBridgeId OBJECT-TYPE
			SYNTAX OCTET STRING (SIZE (8))
			MAX-ACCESS read-only
			STATUS current
			DESCRIPTION
				"TThe STP designated bridge identifier."
			::= { sleStpInstanceEntry 6 }

		
		sleStpInstanceDesignatedPortId OBJECT-TYPE
			SYNTAX INTEGER (0..256)
			MAX-ACCESS read-only
			STATUS current
			DESCRIPTION
				"The STP designated port identifier."
			::= { sleStpInstanceEntry 7 }

		
		sleStpInstanceRootPortId OBJECT-TYPE
			SYNTAX INTEGER (0..256)
			MAX-ACCESS read-only
			STATUS current
			DESCRIPTION
				"The port number of the port which offers the lowest
				cost path from the this STP instance of this bridge
				to the root bridge."
			::= { sleStpInstanceEntry 8 }

		
		sleStpInstanceFwdDelay OBJECT-TYPE
			SYNTAX INTEGER (4..30)
			MAX-ACCESS read-only
			STATUS current
			DESCRIPTION
				"The current forward delay of the STP Instance."
			::= { sleStpInstanceEntry 9 }

		
		sleStpInstanceHelloTime OBJECT-TYPE
			SYNTAX INTEGER (1..10)
			MAX-ACCESS read-only
			STATUS current
			DESCRIPTION
				"The current hello time of the STP Instance."
			::= { sleStpInstanceEntry 10 }

		
		sleStpInstanceMaxAge OBJECT-TYPE
			SYNTAX INTEGER (4..60)
			MAX-ACCESS read-only
			STATUS current
			DESCRIPTION
				"The current max age of the STP Instance."
			::= { sleStpInstanceEntry 11 }

		
		sleStpInstanceRemainHops OBJECT-TYPE
			SYNTAX Integer32
			MAX-ACCESS read-only
			STATUS current
			DESCRIPTION
				"The current remain hops of the MSTI or pvst."
			::= { sleStpInstanceEntry 12 }

		
		sleStpInstanceBrFwdDelay OBJECT-TYPE
			SYNTAX INTEGER (4..30)
			MAX-ACCESS read-only
			STATUS current
			DESCRIPTION
				"The Setting forward delay of the STP Instance."
			::= { sleStpInstanceEntry 13 }

		
		sleStpInstanceBrHelloTime OBJECT-TYPE
			SYNTAX INTEGER (1..10)
			MAX-ACCESS read-only
			STATUS current
			DESCRIPTION
				"The current hello time of the STP Instance."
			::= { sleStpInstanceEntry 14 }

		
		sleStpInstanceBrMaxAge OBJECT-TYPE
			SYNTAX INTEGER (4..60)
			MAX-ACCESS read-only
			STATUS current
			DESCRIPTION
				"The Setting max age of the STP Instance."
			::= { sleStpInstanceEntry 15 }

		
		sleStpInstanceControl OBJECT IDENTIFIER ::= { sleStpInstance 2 }

		
		sleStpInstanceControlRequest OBJECT-TYPE
			SYNTAX INTEGER
				{
				setStpInstanceEnable(1),
				setStpInstanceConfigProfile(2)
				}
			MAX-ACCESS read-write
			STATUS current
			DESCRIPTION
				"
				createStpInstance:
				sleStpInstanceControlIndex
				sleStpInstanceControlEnable
				sleStpInstanceControlPriority
				sleStpInstanceControlBrFwdDelay
				sleStpInstanceControlBrHelloTime
				sleStpInstanceControlBrMaxAge
				
				destroyStpInstance:
				sleStpInstanceControlIndex
				
				setStpInstanceEnable:
				sleStpInstanceControlIndex
				sleStpInstanceControlEnable
				
				setStpInstanceConfigProfile:
				sleStpInstanceControlIndex
				sleStpInstanceControlPriority
				sleStpInstanceControlBrFwdDelay
				sleStpInstanceControlBrHelloTime
				sleStpInstanceControlBrMaxAge
				"
			::= { sleStpInstanceControl 1 }

		
		sleStpInstanceControlStatus OBJECT-TYPE
			SYNTAX SleControlStatusType
			MAX-ACCESS read-only
			STATUS current
			DESCRIPTION
				"The status of a user command. 
				"
			::= { sleStpInstanceControl 2 }

		
		sleStpInstanceControlTimer OBJECT-TYPE
			SYNTAX Gauge32
			MAX-ACCESS read-write
			STATUS current
			DESCRIPTION
				"The maximum wait time for the manager for a long running user command. 
				"
			::= { sleStpInstanceControl 3 }

		
		sleStpInstanceControlTimeStamp OBJECT-TYPE
			SYNTAX TimeTicks
			MAX-ACCESS read-only
			STATUS current
			DESCRIPTION
				"The time stamp of the last command (end of command)."
			::= { sleStpInstanceControl 4 }

		
		sleStpInstanceControlReqResult OBJECT-TYPE
			SYNTAX SleControlRequestResultType
			MAX-ACCESS read-only
			STATUS current
			DESCRIPTION
				"The result of the last user command."
			::= { sleStpInstanceControl 5 }

		
		sleStpInstanceControlIndex OBJECT-TYPE
			SYNTAX INTEGER (0..4096)
			MAX-ACCESS read-write
			STATUS current
			DESCRIPTION
				" sleStpInstanceIndex"
			::= { sleStpInstanceControl 6 }

		
		sleStpInstanceControlEnable OBJECT-TYPE
			SYNTAX INTEGER
				{
				disable(0),
				enable(1)
				}
			MAX-ACCESS read-write
			STATUS current
			DESCRIPTION
				" The enabled/disabled status of the pvst."
			::= { sleStpInstanceControl 7 }

		
		sleStpInstanceControlPriority OBJECT-TYPE
			SYNTAX INTEGER (0..16)
			MAX-ACCESS read-write
			STATUS current
			DESCRIPTION
				"The Setting bridge priority in a specific instance. 
				This values are matched specific values in CLI.
				sleStpInstanceControlPriority X 4096 is equal to priority value in CLI.
				(ex. 2 in SNMP means 8192 in CLI)"
			DEFVAL { 8 }
			::= { sleStpInstanceControl 8 }

		
		sleStpInstanceControlBrFwdDelay OBJECT-TYPE
			SYNTAX INTEGER (4..30)
			MAX-ACCESS read-write
			STATUS current
			DESCRIPTION
				" The Setting forward delay of the MSTI or pvst."
			DEFVAL { 15 }
			::= { sleStpInstanceControl 9 }

		
		sleStpInstanceControlBrHelloTime OBJECT-TYPE
			SYNTAX INTEGER (1..10)
			MAX-ACCESS read-write
			STATUS current
			DESCRIPTION
				" The current hello time of the MSTI or pvst."
			DEFVAL { 2 }
			::= { sleStpInstanceControl 10 }

		
		sleStpInstanceControlBrMaxAge OBJECT-TYPE
			SYNTAX INTEGER (4..60)
			MAX-ACCESS read-write
			STATUS current
			DESCRIPTION
				" The Setting max age of the MSTI or pvst."
			DEFVAL { 30 }
			::= { sleStpInstanceControl 11 }

		
		sleStpInstanceNotification OBJECT IDENTIFIER ::= { sleStpInstance 3 }

		
		sleStpInstanceEnableChanged NOTIFICATION-TYPE
			OBJECTS { sleStpInstanceControlRequest, sleStpInstanceControlReqResult, sleStpInstanceControlIndex, sleStpInstanceControlEnable, sleStpInstanceControlTimeStamp
				 }
			STATUS current
			DESCRIPTION 
				" "
			::= { sleStpInstanceNotification 1 }

		
		sleStpInstanceConfigProfileChanged NOTIFICATION-TYPE
			OBJECTS { sleStpInstanceControlRequest, sleStpInstanceControlReqResult, sleStpInstanceControlIndex, sleStpInstanceControlPriority, sleStpInstanceControlBrFwdDelay, 
				sleStpInstanceControlBrHelloTime, sleStpInstanceControlBrMaxAge, sleStpInstanceControlTimeStamp }
			STATUS current
			DESCRIPTION 
				" "
			::= { sleStpInstanceNotification 2 }

		
		sleStpInstancePort OBJECT IDENTIFIER ::= { sleBridge 7 }

		
		sleStpInstancePortTable OBJECT-TYPE
			SYNTAX SEQUENCE OF SleStpInstancePortEntry
			MAX-ACCESS not-accessible
			STATUS current
			DESCRIPTION
				" STP instance port table"
			::= { sleStpInstancePort 1 }

		
		sleStpInstancePortEntry OBJECT-TYPE
			SYNTAX SleStpInstancePortEntry
			MAX-ACCESS not-accessible
			STATUS current
			DESCRIPTION
				" key: sleStpInstanceIndex, sleStpInstancePortIndex"
			INDEX { sleStpInstanceIndex, sleStpInstancePortIndex }
			::= { sleStpInstancePortTable 1 }

		
		SleStpInstancePortEntry ::=
			SEQUENCE { 
				sleStpInstancePortIndex
					InterfaceIndex,
				sleStpInstancePortPathcost
					INTEGER,
				sleStpInstancePortPriority
					INTEGER,
				sleStpInstancePortRole
					INTEGER,
				sleStpInstancePortState
					INTEGER,
				sleStpInstancePortRootBridgeId
					OCTET STRING,
				sleStpInstancePortRootPathcost
					Integer32,
				sleStpInstancePortDesignateBridgeId
					OCTET STRING,
				sleStpInstancePortDesignatePortId
					INTEGER,
				sleStpInstancePortRootGuardMode
					INTEGER
			 }

		sleStpInstancePortIndex OBJECT-TYPE
			SYNTAX InterfaceIndex
			MAX-ACCESS read-only
			STATUS current
			DESCRIPTION
				"The Port ID."
			::= { sleStpInstancePortEntry 1 }

		
		sleStpInstancePortPathcost OBJECT-TYPE
			SYNTAX INTEGER (0..200000000)
			MAX-ACCESS read-write
			STATUS current
			DESCRIPTION
				"The STP port path cost."
			::= { sleStpInstancePortEntry 2 }

		
		sleStpInstancePortPriority OBJECT-TYPE
			SYNTAX INTEGER (0..255)
			MAX-ACCESS read-only
			STATUS current
			DESCRIPTION
				"The STP port priority."
			::= { sleStpInstancePortEntry 3 }

		
		sleStpInstancePortRole OBJECT-TYPE
			SYNTAX INTEGER
				{
				disable(0),
				designated(1),
				root(2),
				master(3),
				alternate(4),
				backup(5)
				}
			MAX-ACCESS read-only
			STATUS current
			DESCRIPTION
				"The current STP Role of the Port."
			::= { sleStpInstancePortEntry 4 }

		
		sleStpInstancePortState OBJECT-TYPE
			SYNTAX INTEGER
				{
				disabled(0),
				listening(1),
				learning(2),
				forwarding(3),
				blocking(4)
				}
			MAX-ACCESS read-only
			STATUS current
			DESCRIPTION
				"The STP forwarding state of a specific port."
			::= { sleStpInstancePortEntry 5 }

		
		sleStpInstancePortRootBridgeId OBJECT-TYPE
			SYNTAX OCTET STRING (SIZE (8))
			MAX-ACCESS read-only
			STATUS current
			DESCRIPTION
				"The unique Bridge Identifier of the Bridge recorded
				as the Root in the Configuration BPDUs transmitted
				by the Designated Bridge for the segment to which
				the port is attached."
			::= { sleStpInstancePortEntry 6 }

		
		sleStpInstancePortRootPathcost OBJECT-TYPE
			SYNTAX Integer32
			MAX-ACCESS read-only
			STATUS current
			DESCRIPTION
				"The path cost of the Designated Port of the segment
				connected to this port."
			::= { sleStpInstancePortEntry 7 }

		
		sleStpInstancePortDesignateBridgeId OBJECT-TYPE
			SYNTAX OCTET STRING (SIZE (8))
			MAX-ACCESS read-only
			STATUS current
			DESCRIPTION
				"The Bridge Identifier of the bridge which this port
				considers to be the Designated Bridge for this
				port's segment."
			::= { sleStpInstancePortEntry 8 }

		
		sleStpInstancePortDesignatePortId OBJECT-TYPE
			SYNTAX INTEGER (0..256)
			MAX-ACCESS read-only
			STATUS current
			DESCRIPTION
				"The Port Identifier of the port on the Designated
				Bridge for this port's segment."
			::= { sleStpInstancePortEntry 9 }

		
		sleStpInstancePortRootGuardMode OBJECT-TYPE
			SYNTAX INTEGER
				{
				disable(0),
				enable(1)
				}
			MAX-ACCESS read-only
			STATUS current
			DESCRIPTION
				"An indication of whether the RootGuard capability is enabled
					on this port or not.
				 This configuration will be applied to the VLAN or MSTP instance
					in which this port exists.
				
				 Whether the RootGuard capability is enabled or not 
					on this switch depends on the object value of 
					sleStpInstancePortControlRootGuardMode."
			DEFVAL { 0 }
			::= { sleStpInstancePortEntry 10 }

		
		sleStpInstancePortControl OBJECT IDENTIFIER ::= { sleStpInstancePort 2 }

		
		sleStpInstancePortControlRequest OBJECT-TYPE
			SYNTAX INTEGER { setStpInstancePortProfile(1) }
			MAX-ACCESS read-write
			STATUS current
			DESCRIPTION
				"
				setStpInstancePortProfile:
				sleStpInstancePortControlIndex
				sleStpInstancePortControlInstanceId
				sleStpInstancePortControlPathcost
				sleStpInstancePortControlPriority
				"
			::= { sleStpInstancePortControl 1 }

		
		sleStpInstancePortControlStatus OBJECT-TYPE
			SYNTAX SleControlStatusType
			MAX-ACCESS read-only
			STATUS current
			DESCRIPTION
				"The status of a user command. 
				"
			::= { sleStpInstancePortControl 2 }

		
		sleStpInstancePortControlTimer OBJECT-TYPE
			SYNTAX Gauge32
			MAX-ACCESS read-write
			STATUS current
			DESCRIPTION
				"The maximum wait time for the manager for a long running user command. 
				"
			::= { sleStpInstancePortControl 3 }

		
		sleStpInstancePortControlTimeStamp OBJECT-TYPE
			SYNTAX TimeTicks
			MAX-ACCESS read-only
			STATUS current
			DESCRIPTION
				"The time stamp of the last command (end of command)."
			::= { sleStpInstancePortControl 4 }

		
		sleStpInstancePortControlReqResult OBJECT-TYPE
			SYNTAX SleControlRequestResultType
			MAX-ACCESS read-only
			STATUS current
			DESCRIPTION
				"The result of the last user command."
			::= { sleStpInstancePortControl 5 }

		
		sleStpInstancePortControlIndex OBJECT-TYPE
			SYNTAX INTEGER (0..65535)
			MAX-ACCESS read-write
			STATUS current
			DESCRIPTION
				"sleStpInstancePortIndex"
			::= { sleStpInstancePortControl 6 }

		
		sleStpInstancePortControlInstanceId OBJECT-TYPE
			SYNTAX INTEGER (0..4096)
			MAX-ACCESS read-write
			STATUS current
			DESCRIPTION
				" sleStpInstanceId"
			::= { sleStpInstancePortControl 7 }

		
		sleStpInstancePortControlPathcost OBJECT-TYPE
			SYNTAX INTEGER (0..200000000)
			MAX-ACCESS read-write
			STATUS current
			DESCRIPTION
				" The path cost of the Designated Port of the segment
				connected to this port."
			::= { sleStpInstancePortControl 8 }

		
		sleStpInstancePortControlPriority OBJECT-TYPE
			SYNTAX INTEGER (0..255)
			MAX-ACCESS read-write
			STATUS current
			DESCRIPTION
				" The STP port priority."
			DEFVAL { 128 }
			::= { sleStpInstancePortControl 9 }

		
		sleStpInstancePortControlRootGuardMode OBJECT-TYPE
			SYNTAX INTEGER
				{
				disable(0),
				enable(1)
				}
			MAX-ACCESS read-write
			STATUS current
			DESCRIPTION
				"Enable or disable RootGuard capability on this port.
				 This configuration will be applied to the VLAN or MSTP instance
					in which this port exists."
			DEFVAL { 0 }
			::= { sleStpInstancePortControl 10 }

		
		sleStpInstancePortNotification OBJECT IDENTIFIER ::= { sleStpInstancePort 3 }

		
		sleStpInstancePortProfileChanged NOTIFICATION-TYPE
			OBJECTS { sleStpInstancePortControlRequest, sleStpInstancePortControlReqResult, sleStpInstancePortControlTimeStamp, sleStpInstancePortPathcost, sleStpInstancePortPriority, 
				sleStpInstancePortRootGuardMode }
			STATUS current
			DESCRIPTION 
				" "
			::= { sleStpInstancePortNotification 1 }

		
--   sleSubnetVlan Group
-- 1.3.6.1.4.1.6296.9.8.8
		sleSubnetVlan OBJECT IDENTIFIER ::= { sleBridge 8 }

		
--  1.3.6.1.4.1.6296.9.8.8.1
		sleSubnetVlanTable OBJECT-TYPE
			SYNTAX SEQUENCE OF SleSubnetVlanEntry
			MAX-ACCESS not-accessible
			STATUS current
			DESCRIPTION
				" subnet vlan table."
			::= { sleSubnetVlan 1 }

		
--  1.3.6.1.4.1.6296.9.8.8.1.1
		sleSubnetVlanEntry OBJECT-TYPE
			SYNTAX SleSubnetVlanEntry
			MAX-ACCESS not-accessible
			STATUS current
			DESCRIPTION
				" key: sleSubnetVlanIp, sleSubnetVlanMask"
			INDEX { sleSubnetVlanIp, sleSubnetVlanMask }
			::= { sleSubnetVlanTable 1 }

		
		SleSubnetVlanEntry ::=
			SEQUENCE { 
				sleSubnetVlanIp
					IpAddress,
				sleSubnetVlanMask
					Integer32,
				sleSubnetVlanVid
					Integer32
			 }

--  1.3.6.1.4.1.6296.9.8.8.1.1.2
		sleSubnetVlanIp OBJECT-TYPE
			SYNTAX IpAddress
			MAX-ACCESS read-only
			STATUS current
			DESCRIPTION
				"Ip address of Subnet"
			::= { sleSubnetVlanEntry 1 }

		
--  1.3.6.1.4.1.6296.9.8.8.1.1.3
		sleSubnetVlanMask OBJECT-TYPE
			SYNTAX Integer32 (1..32)
			MAX-ACCESS read-only
			STATUS current
			DESCRIPTION
				"Mask bit."
			::= { sleSubnetVlanEntry 2 }

		
--  1.3.6.1.4.1.6296.9.8.8.1.1.4
		sleSubnetVlanVid OBJECT-TYPE
			SYNTAX Integer32 (1..4094)
			MAX-ACCESS read-only
			STATUS current
			DESCRIPTION
				"Index of the VLAN."
			::= { sleSubnetVlanEntry 3 }

		
--  1.3.6.1.4.1.6296.9.8.8.2
		sleSubnetVlanControl OBJECT IDENTIFIER ::= { sleSubnetVlan 2 }

		
--   Node definitions
-- 
-- 1.3.6.1.4.1.6296.9.8.8.2.1
		sleSubnetVlanControlRequest OBJECT-TYPE
			SYNTAX INTEGER
				{
				createSubnetVlan(1),
				destorySubnetVlan(2)
				}
			MAX-ACCESS read-write
			STATUS current
			DESCRIPTION
				"
				createSubnetVlan:
				sleSubnetVlanControlPortIndex
				sleSubnetVlanControlIp
				sleSubnetVlanControlMask
				sleSubnetVlanControlVid
				
				destorySubnetVlan:
				sleSubnetVlanControlPortIndex
				
				"
			::= { sleSubnetVlanControl 1 }

		
--  1.3.6.1.4.1.6296.9.8.8.2.3
		sleSubnetVlanControlStatus OBJECT-TYPE
			SYNTAX SleControlStatusType
			MAX-ACCESS read-only
			STATUS current
			DESCRIPTION
				"The status of a user command. 
				"
			::= { sleSubnetVlanControl 2 }

		
--  1.3.6.1.4.1.6296.9.8.8.2.4
		sleSubnetVlanControlTimer OBJECT-TYPE
			SYNTAX Gauge32
			MAX-ACCESS read-write
			STATUS current
			DESCRIPTION
				"The maximum wait time for the manager for a long running user command. 
				"
			::= { sleSubnetVlanControl 3 }

		
--  1.3.6.1.4.1.6296.9.8.8.2.6
		sleSubnetVlanControlTimeStamp OBJECT-TYPE
			SYNTAX TimeTicks
			MAX-ACCESS read-only
			STATUS current
			DESCRIPTION
				"The time stamp of the last command (end of command)."
			::= { sleSubnetVlanControl 4 }

		
--  1.3.6.1.4.1.6296.9.8.8.2.5
		sleSubnetVlanControlReqResult OBJECT-TYPE
			SYNTAX SleControlRequestResultType
			MAX-ACCESS read-only
			STATUS current
			DESCRIPTION
				"The result of the last user command."
			::= { sleSubnetVlanControl 5 }

		
--  1.3.6.1.4.1.6296.9.8.8.2.7
		sleSubnetVlanControlIp OBJECT-TYPE
			SYNTAX IpAddress
			MAX-ACCESS read-write
			STATUS current
			DESCRIPTION
				"IP address"
			::= { sleSubnetVlanControl 6 }

		
--  1.3.6.1.4.1.6296.9.8.8.2.8
		sleSubnetVlanControlMask OBJECT-TYPE
			SYNTAX Integer32 (1..32)
			MAX-ACCESS read-write
			STATUS current
			DESCRIPTION
				"Mask bit
				"
			::= { sleSubnetVlanControl 7 }

		
--  1.3.6.1.4.1.6296.9.8.8.2.9
		sleSubnetVlanControlVid OBJECT-TYPE
			SYNTAX Integer32 (1..4094)
			MAX-ACCESS read-write
			STATUS current
			DESCRIPTION
				"Vlan's ID"
			::= { sleSubnetVlanControl 8 }

		
--  1.3.6.1.4.1.6296.9.8.8.3
		sleSubnetVlanNotification OBJECT IDENTIFIER ::= { sleSubnetVlan 3 }

		
--  1.3.6.1.4.1.6296.9.8.8.3.1
		sleSubnetVlanCreated NOTIFICATION-TYPE
			OBJECTS { sleSubnetVlanControlTimeStamp, sleSubnetVlanControlReqResult, sleSubnetVlanControlRequest, sleSubnetVlanVid }
			STATUS current
			DESCRIPTION 
				" "
			::= { sleSubnetVlanNotification 1 }

		
--  1.3.6.1.4.1.6296.9.8.8.3.2
		sleSubnetVlanDestroyed NOTIFICATION-TYPE
			OBJECTS { sleSubnetVlanControlRequest, sleSubnetVlanControlTimeStamp, sleSubnetVlanControlReqResult, sleSubnetVlanVid }
			STATUS current
			DESCRIPTION 
				" "
			::= { sleSubnetVlanNotification 2 }

		
--   sleProtocolVlan Group
-- 1.3.6.1.4.1.6296.9.8.9
		sleProtocolVlan OBJECT IDENTIFIER ::= { sleBridge 9 }

		
--  1.3.6.1.4.1.6296.9.8.9.1
		sleProtocolVlanTable OBJECT-TYPE
			SYNTAX SEQUENCE OF SleProtocolVlanEntry
			MAX-ACCESS not-accessible
			STATUS current
			DESCRIPTION
				" protocol vlan table."
			::= { sleProtocolVlan 1 }

		
--  1.3.6.1.4.1.6296.9.8.9.1.1
		sleProtocolVlanEntry OBJECT-TYPE
			SYNTAX SleProtocolVlanEntry
			MAX-ACCESS not-accessible
			STATUS current
			DESCRIPTION
				" key: sleBridgePortIndex, sleProtocolVlanEtype"
			INDEX { sleBridgePortIndex, sleProtocolVlanEtype }
			::= { sleProtocolVlanTable 1 }

		
		SleProtocolVlanEntry ::=
			SEQUENCE { 
				sleProtocolVlanEtype
					Unsigned32,
				sleProtocolVlanVid
					Integer32
			 }

--  1.3.6.1.4.1.6296.9.8.9.1.1.2
		sleProtocolVlanEtype OBJECT-TYPE
			SYNTAX Unsigned32 (1..65535)
			MAX-ACCESS read-only
			STATUS current
			DESCRIPTION
				"Ethernet type"
			::= { sleProtocolVlanEntry 1 }

		
--  1.3.6.1.4.1.6296.9.8.9.1.1.3
		sleProtocolVlanVid OBJECT-TYPE
			SYNTAX Integer32 (1..4094)
			MAX-ACCESS read-only
			STATUS current
			DESCRIPTION
				"Index of the VLAN."
			::= { sleProtocolVlanEntry 2 }

		
--  1.3.6.1.4.1.6296.9.8.9.2
		sleProtocolVlanControl OBJECT IDENTIFIER ::= { sleProtocolVlan 2 }

		
--   Node definitions
-- 
-- 1.3.6.1.4.1.6296.9.8.9.2.1
		sleProtocolVlanControlRequest OBJECT-TYPE
			SYNTAX INTEGER
				{
				createProtocolVlan(1),
				destoryProtocolVlan(2)
				}
			MAX-ACCESS read-write
			STATUS current
			DESCRIPTION
				"
				createProtocolVlan:
				sleProtocolVlanControlPortIndex
				sleProtocolVlanControlEtype
				sleProtocolVlanControlVid
				
				destoryProtocolVlan:
				sleProtocolVlanControlPortIndex
				
				"
			::= { sleProtocolVlanControl 1 }

		
--  1.3.6.1.4.1.6296.9.8.9.2.3
		sleProtocolVlanControlStatus OBJECT-TYPE
			SYNTAX SleControlStatusType
			MAX-ACCESS read-only
			STATUS current
			DESCRIPTION
				"The status of a user command. 
				"
			::= { sleProtocolVlanControl 2 }

		
--  1.3.6.1.4.1.6296.9.8.9.2.4
		sleProtocolVlanControlTimer OBJECT-TYPE
			SYNTAX Gauge32
			MAX-ACCESS read-write
			STATUS current
			DESCRIPTION
				"The maximum wait time for the manager for a long running user command. 
				"
			::= { sleProtocolVlanControl 3 }

		
--  1.3.6.1.4.1.6296.9.8.9.2.6
		sleProtocolVlanControlTimeStamp OBJECT-TYPE
			SYNTAX TimeTicks
			MAX-ACCESS read-only
			STATUS current
			DESCRIPTION
				"The time stamp of the last command (end of command)."
			::= { sleProtocolVlanControl 4 }

		
--  1.3.6.1.4.1.6296.9.8.9.2.5
		sleProtocolVlanControlReqResult OBJECT-TYPE
			SYNTAX SleControlRequestResultType
			MAX-ACCESS read-only
			STATUS current
			DESCRIPTION
				"The result of the last user command."
			::= { sleProtocolVlanControl 5 }

		
--  1.3.6.1.4.1.6296.9.8.9.2.2
		sleProtocolVlanControlPortIndex OBJECT-TYPE
			SYNTAX InterfaceIndex
			MAX-ACCESS read-write
			STATUS current
			DESCRIPTION
				" sleBridgePortIndex, sleProtocolVlanEtype"
			::= { sleProtocolVlanControl 6 }

		
--  1.3.6.1.4.1.6296.9.8.9.2.7
		sleProtocolVlanControlEtype OBJECT-TYPE
			SYNTAX Unsigned32
			MAX-ACCESS read-write
			STATUS current
			DESCRIPTION
				"Ethernet Type"
			::= { sleProtocolVlanControl 7 }

		
--  1.3.6.1.4.1.6296.9.8.9.2.8
		sleProtocolVlanControlVid OBJECT-TYPE
			SYNTAX Integer32 (1..4094)
			MAX-ACCESS read-write
			STATUS current
			DESCRIPTION
				" sleProtocolVlanControlVid"
			::= { sleProtocolVlanControl 8 }

		
--  1.3.6.1.4.1.6296.9.8.9.3
		sleProtocolVlanNotification OBJECT IDENTIFIER ::= { sleProtocolVlan 3 }

		
--  1.3.6.1.4.1.6296.9.8.9.3.1
		sleProtocolVlanCreated NOTIFICATION-TYPE
			OBJECTS { sleProtocolVlanVid, sleProtocolVlanControlRequest, sleProtocolVlanControlTimeStamp, sleProtocolVlanControlReqResult }
			STATUS current
			DESCRIPTION 
				" "
			::= { sleProtocolVlanNotification 1 }

		
--  1.3.6.1.4.1.6296.9.8.9.3.2
		sleProtocolVlanDestroyed NOTIFICATION-TYPE
			OBJECTS { sleProtocolVlanControlRequest, sleProtocolVlanControlTimeStamp, sleProtocolVlanControlReqResult, sleProtocolVlanVid }
			STATUS current
			DESCRIPTION 
				" "
			::= { sleProtocolVlanNotification 2 }

		
--  1.3.6.1.4.1.6296.9.8.10
		sleLag OBJECT IDENTIFIER ::= { sleBridge 10 }

		
--  1.3.6.1.4.1.6296.9.8.10.1
		sleLagTable OBJECT-TYPE
			SYNTAX SEQUENCE OF SleLagEntry
			MAX-ACCESS not-accessible
			STATUS current
			DESCRIPTION
				" lag table."
			::= { sleLag 1 }

		
--  1.3.6.1.4.1.6296.9.8.10.1.1
		sleLagEntry OBJECT-TYPE
			SYNTAX SleLagEntry
			MAX-ACCESS not-accessible
			STATUS current
			DESCRIPTION
				" key: sleLagIndex"
			INDEX { sleLagIndex }
			::= { sleLagTable 1 }
-- key: sleLagIndex
		
		SleLagEntry ::=
			SEQUENCE { 
				sleLagIndex
					Integer32,
				sleLagPortId
					InterfaceIndex,
				sleLagDistMode
					INTEGER,
				sleLagPortMap
					OCTET STRING,
				sleLagMode
					INTEGER,
				sleLagLeastActive
					INTEGER
			 }

--  1.3.6.1.4.1.6296.9.8.10.1.1.1
		sleLagIndex OBJECT-TYPE
			SYNTAX Integer32 (0..13)
			MAX-ACCESS read-only
			STATUS current
			DESCRIPTION
				"This value assigned to the aggregation ID."
			::= { sleLagEntry 1 }

		
--  1.3.6.1.4.1.6296.9.8.10.1.1.2
		sleLagPortId OBJECT-TYPE
			SYNTAX InterfaceIndex
			MAX-ACCESS read-only
			STATUS current
			DESCRIPTION
				"Port ID of aggregation."
			::= { sleLagEntry 2 }

		
--  1.3.6.1.4.1.6296.9.8.10.1.1.3
		sleLagDistMode OBJECT-TYPE
			SYNTAX INTEGER
				{
				none(0),
				srcmac(1),
				dstmac(2),
				srcdstmac(3),
				srcip(4),
				dstip(5),
				srcdstip(6),
				srcdstl4(7),
				label(80)
				}
			MAX-ACCESS read-only
			STATUS current
			DESCRIPTION
				"This value assigned to the distributing 
				mode of link aggregation."
			::= { sleLagEntry 3 }

		
--  1.3.6.1.4.1.6296.9.8.10.1.1.4
		sleLagPortMap OBJECT-TYPE
			SYNTAX OCTET STRING
			MAX-ACCESS read-only
			STATUS current
			DESCRIPTION
				"The value assigned to the port list of  the aggregation."
			::= { sleLagEntry 4 }

		
--  1.3.6.1.4.1.6296.9.8.10.1.1.5
		sleLagMode OBJECT-TYPE
			SYNTAX INTEGER
				{
				inactive(0),
				trunk(1),
				lacp(2)
				}
			MAX-ACCESS read-only
			STATUS current
			DESCRIPTION
				"The operation mode of  link aggregation."
			::= { sleLagEntry 5 }

		
--  1.3.6.1.4.1.6296.101.3.10.1.1.6
		sleLagLeastActive OBJECT-TYPE
			SYNTAX INTEGER
			MAX-ACCESS read-only
			STATUS current
			DESCRIPTION
				"Description."
			::= { sleLagEntry 6 }

		
--  1.3.6.1.4.1.6296.9.8.10.2
		sleLagControl OBJECT IDENTIFIER ::= { sleLag 2 }

		
--  1.3.6.1.4.1.6296.9.8.10.2.1
		sleLagControlRequest OBJECT-TYPE
			SYNTAX INTEGER { setLagProfile(1) }
			MAX-ACCESS read-write
			STATUS current
			DESCRIPTION
				"The MIB object for the user command.."
			::= { sleLagControl 1 }

		
--  1.3.6.1.4.1.6296.9.8.10.2.2
		sleLagControlStatus OBJECT-TYPE
			SYNTAX SleControlStatusType
			MAX-ACCESS read-only
			STATUS current
			DESCRIPTION
				"Describes the status of a user command group, 
				used for block commands while a command execution in process."
			::= { sleLagControl 2 }

		
--  1.3.6.1.4.1.6296.9.8.10.2.3
		sleLagControlTimer OBJECT-TYPE
			SYNTAX Gauge32
			MAX-ACCESS read-write
			STATUS current
			DESCRIPTION
				"Maximum command duration time in case of long running"
			::= { sleLagControl 3 }

		
--  1.3.6.1.4.1.6296.9.8.10.2.5
		sleLagControlTimeStamp OBJECT-TYPE
			SYNTAX TimeTicks
			MAX-ACCESS read-only
			STATUS current
			DESCRIPTION
				"Command result attribute"
			::= { sleLagControl 4 }

		
--  1.3.6.1.4.1.6296.9.8.10.2.4
		sleLagControlReqResult OBJECT-TYPE
			SYNTAX SleControlRequestResultType
			MAX-ACCESS read-only
			STATUS current
			DESCRIPTION
				"Time stamp attribute set at end of command."
			::= { sleLagControl 5 }

		
--  1.3.6.1.4.1.6296.9.8.10.2.6
		sleLagControlIndex OBJECT-TYPE
			SYNTAX Integer32
			MAX-ACCESS read-write
			STATUS current
			DESCRIPTION
				"This value assigned to the aggregation ID."
			::= { sleLagControl 6 }

		
--  1.3.6.1.4.1.6296.9.8.10.2.7
		sleLagControlDistMode OBJECT-TYPE
			SYNTAX INTEGER
				{
				srcmac(1),
				dstmac(2),
				srcdstmac(3),
				srcip(4),
				dstip(5),
				srcdstip(6),
				srcdstl4(7),
				label(80)
				}
			MAX-ACCESS read-write
			STATUS current
			DESCRIPTION
				"This value assigned to the distributing mode of link aggregation."
			::= { sleLagControl 7 }

		
--  1.3.6.1.4.1.6296.9.8.10.2.8
		sleLagControlPortMap OBJECT-TYPE
			SYNTAX OCTET STRING
			MAX-ACCESS read-write
			STATUS current
			DESCRIPTION
				"Port ID of aggregation."
			::= { sleLagControl 8 }

		
--  1.3.6.1.4.1.6296.9.8.10.2.9
		sleLagControlMode OBJECT-TYPE
			SYNTAX INTEGER
				{
				trunk(1),
				lacp(2)
				}
			MAX-ACCESS read-write
			STATUS current
			DESCRIPTION
				"The operation mode of  link aggregation."
			::= { sleLagControl 9 }

		
--  1.3.6.1.4.1.6296.101.3.10.2.10
		sleLagControlLeastActive OBJECT-TYPE
			SYNTAX INTEGER
			MAX-ACCESS read-write
			STATUS current
			DESCRIPTION
				"Description."
			::= { sleLagControl 10 }

		
--  1.3.6.1.4.1.6296.9.8.10.3
		sleLagNotification OBJECT IDENTIFIER ::= { sleLag 3 }

		
--  1.3.6.1.4.1.6296.9.8.10.3.1
		sleLagProfileChanged NOTIFICATION-TYPE
			OBJECTS { sleLagControlRequest, sleLagControlReqResult, sleLagControlTimeStamp, sleLagLeastActive, sleLagPortMap, 
				sleLagDistMode, sleLagMode }
			STATUS current
			DESCRIPTION 
				" "
			::= { sleLagNotification 1 }

		
--  1.3.6.1.4.1.6296.9.8.11
		sleLagLacp OBJECT IDENTIFIER ::= { sleBridge 11 }

		
--  1.3.6.1.4.1.6296.9.8.11.1
		sleLagLacpTable OBJECT-TYPE
			SYNTAX SEQUENCE OF SleLagLacpEntry
			MAX-ACCESS not-accessible
			STATUS current
			DESCRIPTION
				" lag LACP table."
			::= { sleLagLacp 1 }

		
--  1.3.6.1.4.1.6296.9.8.11.1.1
		sleLagLacpEntry OBJECT-TYPE
			SYNTAX SleLagLacpEntry
			MAX-ACCESS not-accessible
			STATUS current
			DESCRIPTION
				" key: sleLagLacpIndex"
			INDEX { sleLagLacpIndex }
			::= { sleLagLacpTable 1 }

		
		SleLagLacpEntry ::=
			SEQUENCE { 
				sleLagLacpIndex
					Integer32,
				sleLagLacpActorAggregatorKey
					Integer32,
				sleLagLacpActorSystemMAC
					OCTET STRING,
				sleLagLacpPartnerSystemMAC
					OCTET STRING,
				sleLagLacpPartnerSystemPriority
					Integer32,
				sleLagLacpPartnerAggregatorKey
					Integer32
			 }

--  1.3.6.1.4.1.6296.9.8.11.1.1.1
		sleLagLacpIndex OBJECT-TYPE
			SYNTAX Integer32 (0..13)
			MAX-ACCESS read-only
			STATUS current
			DESCRIPTION
				"Location of authentication."
			::= { sleLagLacpEntry 1 }

		
--  1.3.6.1.4.1.6296.9.8.11.1.1.2
		sleLagLacpActorAggregatorKey OBJECT-TYPE
			SYNTAX Integer32 (1..65535)
			MAX-ACCESS read-only
			STATUS current
			DESCRIPTION
				"The kind of authentication."
			::= { sleLagLacpEntry 2 }

		
		sleLagLacpActorSystemMAC OBJECT-TYPE
			SYNTAX OCTET STRING
			MAX-ACCESS read-write
			STATUS current
			DESCRIPTION
				"The Actor’s System ID, encoded as a MAC address."
			::= { sleLagLacpEntry 3 }

		
--  1.3.6.1.4.1.6296.9.8.11.1.1.3
		sleLagLacpPartnerSystemMAC OBJECT-TYPE
			SYNTAX OCTET STRING
			MAX-ACCESS read-only
			STATUS current
			DESCRIPTION
				"Enable or disable the corresponding authen method."
			::= { sleLagLacpEntry 4 }

		
--  1.3.6.1.4.1.6296.9.8.11.1.1.4
		sleLagLacpPartnerSystemPriority OBJECT-TYPE
			SYNTAX Integer32 (1..65535)
			MAX-ACCESS read-only
			STATUS current
			DESCRIPTION
				"The primary priority of the corresponding authen method."
			::= { sleLagLacpEntry 5 }

		
--  1.3.6.1.4.1.6296.9.8.11.1.1.5
		sleLagLacpPartnerAggregatorKey OBJECT-TYPE
			SYNTAX Integer32 (1..65535)
			MAX-ACCESS read-only
			STATUS current
			DESCRIPTION
				" "
			::= { sleLagLacpEntry 6 }

		
		sleLagLacpStats OBJECT IDENTIFIER ::= { sleLagLacp 2 }

		
		sleLagLacpStatsPduReceived OBJECT-TYPE
			SYNTAX Counter32
			MAX-ACCESS read-only
			STATUS current
			DESCRIPTION
				"The received LACP PDUs"
			::= { sleLagLacpStats 1 }

		
		sleLagLacpStatsPduReceivedErrrors OBJECT-TYPE
			SYNTAX Counter32
			MAX-ACCESS read-only
			STATUS current
			DESCRIPTION
				"The received LACP PDUs"
			::= { sleLagLacpStats 2 }

		
		sleLagLacpStatsPduSent OBJECT-TYPE
			SYNTAX Counter32
			MAX-ACCESS read-only
			STATUS current
			DESCRIPTION
				"The sent LACP PDUs"
			::= { sleLagLacpStats 3 }

		
		sleLagLacpStatsPduSentError OBJECT-TYPE
			SYNTAX Counter32
			MAX-ACCESS read-only
			STATUS current
			DESCRIPTION
				"The sent LACP PDUs error"
			::= { sleLagLacpStats 4 }

		
		sleLagLacpStatsMarkerReceived OBJECT-TYPE
			SYNTAX Counter32
			MAX-ACCESS read-only
			STATUS current
			DESCRIPTION
				"The received LACP Marker"
			::= { sleLagLacpStats 5 }

		
		sleLagLacpStatsMarkerSent OBJECT-TYPE
			SYNTAX Counter32
			MAX-ACCESS read-only
			STATUS current
			DESCRIPTION
				"The sent LACP Marker"
			::= { sleLagLacpStats 6 }

		
		sleLagLacpStatsMarkerSentError OBJECT-TYPE
			SYNTAX Counter32
			MAX-ACCESS read-only
			STATUS current
			DESCRIPTION
				"The sent LACP Marker error."
			::= { sleLagLacpStats 7 }

		
		sleLagLacpControl OBJECT IDENTIFIER ::= { sleLagLacp 3 }

		
		sleLagLacpControlRequest OBJECT-TYPE
			SYNTAX INTEGER { clearLacpStats(1) }
			MAX-ACCESS read-write
			STATUS current
			DESCRIPTION
				"The request of a user command"
			::= { sleLagLacpControl 1 }

		
		sleLagLacpControlStatus OBJECT-TYPE
			SYNTAX SleControlStatusType
			MAX-ACCESS read-only
			STATUS current
			DESCRIPTION
				"The status of user command"
			::= { sleLagLacpControl 2 }

		
		sleLagLacpControlTimer OBJECT-TYPE
			SYNTAX Gauge32
			MAX-ACCESS read-write
			STATUS current
			DESCRIPTION
				"The maximum time for the manager for a long running user command"
			::= { sleLagLacpControl 3 }

		
		sleLagLacpControlTimeStamp OBJECT-TYPE
			SYNTAX TimeTicks
			MAX-ACCESS read-only
			STATUS current
			DESCRIPTION
				"The time stamp of the last command(end of command)"
			::= { sleLagLacpControl 4 }

		
		sleLagLacpControlReqResult OBJECT-TYPE
			SYNTAX SleControlRequestResultType
			MAX-ACCESS read-only
			STATUS current
			DESCRIPTION
				"The result of the last user command"
			::= { sleLagLacpControl 5 }

		
		sleLagLacpNotification OBJECT IDENTIFIER ::= { sleLagLacp 4 }

		
		sleLagLacpStatsCleared NOTIFICATION-TYPE
			OBJECTS { sleLagLacpControlRequest, sleLagLacpControlTimeStamp, sleLagLacpControlReqResult }
			STATUS current
			DESCRIPTION 
				"Description."
			::= { sleLagLacpNotification 1 }

		
--  1.3.6.1.4.1.6296.9.8.12
		sleLagLacpPort OBJECT IDENTIFIER ::= { sleBridge 12 }

		
--  1.3.6.1.4.1.6296.9.8.12.1
		sleLagLacpPortTable OBJECT-TYPE
			SYNTAX SEQUENCE OF SleLagLacpPortEntry
			MAX-ACCESS not-accessible
			STATUS current
			DESCRIPTION
				" lag LACP port table."
			::= { sleLagLacpPort 1 }

		
--  1.3.6.1.4.1.6296.9.8.12.1.1
		sleLagLacpPortEntry OBJECT-TYPE
			SYNTAX SleLagLacpPortEntry
			MAX-ACCESS not-accessible
			STATUS current
			DESCRIPTION
				" key: sleLagLacpPortIndex"
			INDEX { sleLagLacpPortIndex }
			::= { sleLagLacpPortTable 1 }

		
		SleLagLacpPortEntry ::=
			SEQUENCE { 
				sleLagLacpPortIndex
					InterfaceIndex,
				sleLagLacpPortActivity
					INTEGER,
				sleLagLacpPortActorPriority
					INTEGER,
				sleLagLacpPortActorAggregatorId
					Integer32,
				sleLagLacpPortActorAdminKey
					INTEGER,
				sleLagLacpPortActorAdminState
					BITS,
				sleLagLacpPortActorOperKey
					Integer32,
				sleLagLacpPortActorOperState
					BITS,
				sleLagLacpPortPartnerAdminSystemMAC
					OCTET STRING,
				sleLagLacpPortPartnerAdminSystemPriority
					Integer32,
				sleLagLacpPortPartnerAdminKey
					Integer32,
				sleLagLacpPortPartnerAdminNum
					InterfaceIndex,
				sleLagLacpPortPartnerAdminPriority
					Integer32,
				sleLagLacpPortPartnerAdminState
					BITS,
				sleLagLacpPortPartnerOperSystemMAC
					OCTET STRING,
				sleLagLacpPortPartnerOperSystemPriority
					Integer32,
				sleLagLacpPortPartnerOperKey
					Integer32,
				sleLagLacpPortPartnerOperNum
					InterfaceIndex,
				sleLagLacpPortPartnerOperPriority
					Integer32,
				sleLagLacpPortPartnerOperState
					BITS
			 }

--  1.3.6.1.4.1.6296.9.8.12.1.1.1
		sleLagLacpPortIndex OBJECT-TYPE
			SYNTAX InterfaceIndex
			MAX-ACCESS read-only
			STATUS current
			DESCRIPTION
				"The IP address of the RADIUS server referred 
				to in this table entry."
			::= { sleLagLacpPortEntry 1 }

		
		sleLagLacpPortActivity OBJECT-TYPE
			SYNTAX INTEGER
				{
				disable(0),
				enable(1)
				}
			MAX-ACCESS read-only
			STATUS current
			DESCRIPTION
				"show lacp activity of port"
			::= { sleLagLacpPortEntry 2 }

		
--  1.3.6.1.4.1.6296.9.8.12.1.1.2
		sleLagLacpPortActorPriority OBJECT-TYPE
			SYNTAX INTEGER (1..65535)
			MAX-ACCESS read-only
			STATUS current
			DESCRIPTION
				"The priority assigned to the port by Actor."
			::= { sleLagLacpPortEntry 3 }

		
--  1.3.6.1.4.1.6296.9.8.12.1.1.3
		sleLagLacpPortActorAggregatorId OBJECT-TYPE
			SYNTAX Integer32
			MAX-ACCESS read-only
			STATUS current
			DESCRIPTION
				" The aggregator index."
			::= { sleLagLacpPortEntry 4 }

		
--  1.3.6.1.4.1.6296.9.8.12.1.1.4
		sleLagLacpPortActorAdminKey OBJECT-TYPE
			SYNTAX INTEGER (1..65535)
			MAX-ACCESS read-only
			STATUS current
			DESCRIPTION
				"The administrable Key value assigned to the 
				port by the Actor."
			::= { sleLagLacpPortEntry 5 }

		
--  1.3.6.1.4.1.6296.9.8.12.1.1.5
		sleLagLacpPortActorAdminState OBJECT-TYPE
			SYNTAX BITS
				{
				expired(0),
				defaulted(1),
				destributing(2),
				collecting(3),
				synchronization(4),
				aggregation(5),
				lacpTimeout(6),
				lacpActivity(7)
				}
			MAX-ACCESS read-only
			STATUS current
			DESCRIPTION
				"The Actor's administrable state variables for the port."
			::= { sleLagLacpPortEntry 6 }

		
--  1.3.6.1.4.1.6296.9.8.12.1.1.6
		sleLagLacpPortActorOperKey OBJECT-TYPE
			SYNTAX Integer32 (1..65535)
			MAX-ACCESS read-only
			STATUS current
			DESCRIPTION
				"The operational Key value assigned to the 
				port by the Actor."
			::= { sleLagLacpPortEntry 7 }

		
--  1.3.6.1.4.1.6296.9.8.12.1.1.7
		sleLagLacpPortActorOperState OBJECT-TYPE
			SYNTAX BITS
				{
				expired(0),
				defaulted(1),
				destributing(2),
				collecting(3),
				synchronization(4),
				aggregation(5),
				lacpTmeout(6),
				lacpActivity(7)
				}
			MAX-ACCESS read-only
			STATUS current
			DESCRIPTION
				"The Actor's operational state variables for the port."
			::= { sleLagLacpPortEntry 8 }

		
--  1.3.6.1.4.1.6296.9.8.12.1.1.8
		sleLagLacpPortPartnerAdminSystemMAC OBJECT-TYPE
			SYNTAX OCTET STRING
			MAX-ACCESS read-only
			STATUS current
			DESCRIPTION
				"The Partner's Administrable System ID, 
				encoded as a MAC address."
			::= { sleLagLacpPortEntry 9 }

		
--  1.3.6.1.4.1.6296.9.8.12.1.1.9
		sleLagLacpPortPartnerAdminSystemPriority OBJECT-TYPE
			SYNTAX Integer32 (1..65535)
			MAX-ACCESS read-only
			STATUS current
			DESCRIPTION
				"The administrable priority assigned to the 
				Partner System."
			::= { sleLagLacpPortEntry 10 }

		
--  1.3.6.1.4.1.6296.9.8.12.1.1.10
		sleLagLacpPortPartnerAdminKey OBJECT-TYPE
			SYNTAX Integer32 (1..65535)
			MAX-ACCESS read-only
			STATUS current
			DESCRIPTION
				"The administrable Key value assigned to 
				the port by the Partner."
			::= { sleLagLacpPortEntry 11 }

		
--  1.3.6.1.4.1.6296.9.8.12.1.1.11
		sleLagLacpPortPartnerAdminNum OBJECT-TYPE
			SYNTAX InterfaceIndex
			MAX-ACCESS read-only
			STATUS current
			DESCRIPTION
				"The administrable number value assigned 
				to the port by the Partner."
			::= { sleLagLacpPortEntry 12 }

		
--  1.3.6.1.4.1.6296.9.8.12.1.1.12
		sleLagLacpPortPartnerAdminPriority OBJECT-TYPE
			SYNTAX Integer32 (1..65535)
			MAX-ACCESS read-only
			STATUS current
			DESCRIPTION
				"The administrable priority assigned to 
				this port by the Partner."
			::= { sleLagLacpPortEntry 13 }

		
--  1.3.6.1.4.1.6296.9.8.12.1.1.13
		sleLagLacpPortPartnerAdminState OBJECT-TYPE
			SYNTAX BITS
				{
				expired(0),
				defaulted(1),
				destributing(2),
				collecting(3),
				synchronization(4),
				aggregation(5),
				lacpTmeout(6),
				lacpActivity(7)
				}
			MAX-ACCESS read-only
			STATUS current
			DESCRIPTION
				"The administrable state assigned to this 
				port by the Partner."
			::= { sleLagLacpPortEntry 14 }

		
--  1.3.6.1.4.1.6296.9.8.12.1.1.14
		sleLagLacpPortPartnerOperSystemMAC OBJECT-TYPE
			SYNTAX OCTET STRING
			MAX-ACCESS read-only
			STATUS current
			DESCRIPTION
				"The Partner's operational System ID, 
				encoded as a MAC address."
			::= { sleLagLacpPortEntry 15 }

		
--  1.3.6.1.4.1.6296.9.8.12.1.1.15
		sleLagLacpPortPartnerOperSystemPriority OBJECT-TYPE
			SYNTAX Integer32 (1..65535)
			MAX-ACCESS read-only
			STATUS current
			DESCRIPTION
				"The operational priority assigned to 
				the Partner System."
			::= { sleLagLacpPortEntry 16 }

		
--  1.3.6.1.4.1.6296.9.8.12.1.1.16
		sleLagLacpPortPartnerOperKey OBJECT-TYPE
			SYNTAX Integer32 (1..65535)
			MAX-ACCESS read-only
			STATUS current
			DESCRIPTION
				"The operational Key value assigned to the 
				port by the Partner."
			::= { sleLagLacpPortEntry 17 }

		
--  1.3.6.1.4.1.6296.9.8.12.1.1.17
		sleLagLacpPortPartnerOperNum OBJECT-TYPE
			SYNTAX InterfaceIndex
			MAX-ACCESS read-only
			STATUS current
			DESCRIPTION
				"The operational number value assigned to 
				the port by the Partner."
			::= { sleLagLacpPortEntry 18 }

		
--  1.3.6.1.4.1.6296.9.8.12.1.1.18
		sleLagLacpPortPartnerOperPriority OBJECT-TYPE
			SYNTAX Integer32 (1..65535)
			MAX-ACCESS read-only
			STATUS current
			DESCRIPTION
				"The operational priority assigned to 
				this port by the Partner."
			::= { sleLagLacpPortEntry 19 }

		
--  1.3.6.1.4.1.6296.9.8.12.1.1.19
		sleLagLacpPortPartnerOperState OBJECT-TYPE
			SYNTAX BITS
				{
				expired(0),
				defaulted(1),
				destributing(2),
				collecting(3),
				synchronization(4),
				aggregation(5),
				lacpTimeout(6),
				lacpActivity(7)
				}
			MAX-ACCESS read-only
			STATUS current
			DESCRIPTION
				"The operational state assigned to this 
				port by the Partner."
			::= { sleLagLacpPortEntry 20 }

		
--  1.3.6.1.4.1.6296.9.8.12.2
		sleLagLacpPortControl OBJECT IDENTIFIER ::= { sleLagLacpPort 2 }

		
--  1.3.6.1.4.1.6296.9.8.12.2.1
		sleLagLacpPortControlRequest OBJECT-TYPE
			SYNTAX INTEGER { setLagLacpPortProfile(1) }
			MAX-ACCESS read-write
			STATUS current
			DESCRIPTION
				"The MIB object for the user command."
			::= { sleLagLacpPortControl 1 }

		
--  1.3.6.1.4.1.6296.9.8.12.2.2
		sleLagLacpPortControlStatus OBJECT-TYPE
			SYNTAX SleControlStatusType
			MAX-ACCESS read-only
			STATUS current
			DESCRIPTION
				"Describes the status of a user command group, 
				used for block commands while a command execution in process."
			::= { sleLagLacpPortControl 2 }

		
--  1.3.6.1.4.1.6296.9.8.12.2.3
		sleLagLacpPortControlTimer OBJECT-TYPE
			SYNTAX Gauge32
			MAX-ACCESS read-write
			STATUS current
			DESCRIPTION
				"Maximum command duration time in case of long running"
			::= { sleLagLacpPortControl 3 }

		
--  1.3.6.1.4.1.6296.9.8.12.2.5
		sleLagLacpPortControlTimeStamp OBJECT-TYPE
			SYNTAX TimeStamp
			MAX-ACCESS read-only
			STATUS current
			DESCRIPTION
				"Time stamp attribute set at end of command."
			::= { sleLagLacpPortControl 4 }

		
--  1.3.6.1.4.1.6296.9.8.12.2.4
		sleLagLacpPortControlReqResult OBJECT-TYPE
			SYNTAX SleControlRequestResultType
			MAX-ACCESS read-only
			STATUS current
			DESCRIPTION
				"Command result attribute."
			::= { sleLagLacpPortControl 5 }

		
--  1.3.6.1.4.1.6296.9.8.12.2.6
		sleLagLacpPortControlIndex OBJECT-TYPE
			SYNTAX InterfaceIndex
			MAX-ACCESS read-write
			STATUS current
			DESCRIPTION
				"The IP address of the RADIUS server referred to 
				in this table entry."
			::= { sleLagLacpPortControl 6 }

		
		sleLagLacpPortControlActivity OBJECT-TYPE
			SYNTAX INTEGER
				{
				disable(0),
				enable(1)
				}
			MAX-ACCESS read-write
			STATUS current
			DESCRIPTION
				"show lacp activity of port"
			::= { sleLagLacpPortControl 7 }

		
--  1.3.6.1.4.1.6296.9.8.12.2.7
		sleLagLacpPortControlMode OBJECT-TYPE
			SYNTAX INTEGER
				{
				active(1),
				passive(2)
				}
			MAX-ACCESS read-write
			STATUS current
			DESCRIPTION
				"set LACP_Activity in sleLagLacpPortActorAdminState"
			::= { sleLagLacpPortControl 8 }

		
--  1.3.6.1.4.1.6296.9.8.12.2.8
		sleLagLacpPortControlAdminKey OBJECT-TYPE
			SYNTAX Integer32 (0..15)
			MAX-ACCESS read-write
			STATUS current
			DESCRIPTION
				"The administrable Key value assigned to the 
				port by the Actor."
			::= { sleLagLacpPortControl 9 }

		
--  1.3.6.1.4.1.6296.9.8.12.2.9
		sleLagLacpPortControlAggregation OBJECT-TYPE
			SYNTAX INTEGER
				{
				aggregatable(1),
				individual(2)
				}
			MAX-ACCESS read-write
			STATUS current
			DESCRIPTION
				"set Aggregation in sleLagLacpPortActorAdminState."
			::= { sleLagLacpPortControl 10 }

		
--  Radius Server operation mode: if set bit 0, is used 
-- in login, and if set bit 1, is used in 802.1X (dot1x).
-- 1.3.6.1.4.1.6296.9.8.12.2.10
		sleLagLacpPortControlPriority OBJECT-TYPE
			SYNTAX Integer32 (1..65535)
			MAX-ACCESS read-write
			STATUS current
			DESCRIPTION
				"The priority assigned to the port by Actor."
			::= { sleLagLacpPortControl 11 }

		
--  1.3.6.1.4.1.6296.9.8.12.2.11
		sleLagLacpPortControlTimeout OBJECT-TYPE
			SYNTAX INTEGER
				{
				short(1),
				long(2)
				}
			MAX-ACCESS read-write
			STATUS current
			DESCRIPTION
				"set LACP_Timeout in sleLagLacpPortActorAdminState."
			::= { sleLagLacpPortControl 12 }

		
--  1.3.6.1.4.1.6296.9.8.12.3
		sleLagLacpPortNotification OBJECT IDENTIFIER ::= { sleLagLacpPort 3 }

		
--  1.3.6.1.4.1.6296.9.8.12.3.1
		sleLagLacpPortProfileChanged NOTIFICATION-TYPE
			OBJECTS { sleLagLacpPortControlRequest, sleLagLacpPortControlReqResult, sleLagLacpPortControlTimeStamp, sleLagLacpPortActorAdminKey, sleLagLacpPortActorPriority, 
				sleLagLacpPortActorAdminState }
			STATUS current
			DESCRIPTION 
				" "
			::= { sleLagLacpPortNotification 1 }

		
--  1.3.6.1.4.1.6296.9.8.12.3.2
		sleLagLacpPortAggreChanged NOTIFICATION-TYPE
			OBJECTS { sleLagLacpPortControlRequest, sleLagLacpPortControlReqResult, sleLagLacpPortControlTimeStamp, sleLagLacpPortActorAggregatorId }
			STATUS current
			DESCRIPTION 
				" "
			::= { sleLagLacpPortNotification 2 }

		
--  1.3.6.1.4.1.6296.9.8.13
		sleFdb OBJECT IDENTIFIER ::= { sleBridge 13 }

		
--  1.3.6.1.4.1.6296.9.8.13.2
		sleFdbTable OBJECT-TYPE
			SYNTAX SEQUENCE OF SleFdbEntry
			MAX-ACCESS not-accessible
			STATUS current
			DESCRIPTION
				"The table of FDB entries."
			::= { sleFdb 1 }

		
--  1.3.6.1.4.1.6296.9.8.13.2.1
		sleFdbEntry OBJECT-TYPE
			SYNTAX SleFdbEntry
			MAX-ACCESS not-accessible
			STATUS current
			DESCRIPTION
				"The table entry of FDB table.
				key: sleFdbEntryFid, sleFdbEntryPort, sleFdbEntryMacAddress"
			INDEX { sleFdbEntryFid, sleFdbEntryPort, sleFdbEntryMacAddress }
			::= { sleFdbTable 1 }

		
		SleFdbEntry ::=
			SEQUENCE { 
				sleFdbEntryFid
					INTEGER,
				sleFdbEntryPort
					INTEGER,
				sleFdbEntryMacAddress
					OCTET STRING,
				sleFdbEntryVid
					INTEGER,
				sleFdbEntryMode
					INTEGER,
				sleFdbEntryPermission
					INTEGER,
				sleFdbEntryElapsedTime
					Unsigned32
			 }

--  1.3.6.1.4.1.6296.9.8.13.2.1.1
		sleFdbEntryFid OBJECT-TYPE
			SYNTAX INTEGER (1..4094)
			MAX-ACCESS read-only
			STATUS current
			DESCRIPTION
				"FDB identify."
			::= { sleFdbEntry 1 }

		
--  1.3.6.1.4.1.6296.9.8.13.2.1.2
		sleFdbEntryPort OBJECT-TYPE
			SYNTAX INTEGER (1..255)
			MAX-ACCESS read-only
			STATUS current
			DESCRIPTION
				"The port number of the port on which 
				a frame having a source address equal 
				to the value of the corresponding instance 
				of dasanFdbAddress has been seen."
			::= { sleFdbEntry 2 }

		
--  1.3.6.1.4.1.6296.9.8.13.2.1.3
		sleFdbEntryMacAddress OBJECT-TYPE
			SYNTAX OCTET STRING (SIZE (0..6))
			MAX-ACCESS read-only
			STATUS current
			DESCRIPTION
				"A unicast MAC address for which the device has
				forwarding or filtering information."
			::= { sleFdbEntry 3 }

		
--  1.3.6.1.4.1.6296.9.8.13.2.1.5
		sleFdbEntryVid OBJECT-TYPE
			SYNTAX INTEGER (1..4094)
			MAX-ACCESS read-only
			STATUS current
			DESCRIPTION
				"VLAN ID."
			::= { sleFdbEntry 4 }

		
--  1.3.6.1.4.1.6296.9.8.13.2.1.4
		sleFdbEntryMode OBJECT-TYPE
			SYNTAX INTEGER
				{
				local(0),
				static(1),
				dynamic(2)
				}
			MAX-ACCESS read-only
			STATUS current
			DESCRIPTION
				"FDB Entry's mode.
				The status of this entry.  The meanings of the values
				are:
				    local(0)   - the value of the corresponding instance 
				                 of sleFdbMacAddress was own.
				    static(1)  - the value of the corresponding instance 
				                 of sleFdbMacAddress was specified by management. 
				    dynamic(2) - the value of the corresponding instance
				                 of sleFdbMacAddress was learned."
			::= { sleFdbEntry 5 }

		
--  1.3.6.1.4.1.6296.9.8.13.2.1.6
		sleFdbEntryPermission OBJECT-TYPE
			SYNTAX INTEGER
				{
				deny(0),
				permit(1)
				}
			MAX-ACCESS read-only
			STATUS current
			DESCRIPTION
				"The permission of dasanFdbAddress.
				The meanings of the values are:
				    deny(0)   - the value of the corresponding instance
				                of dasanFdbAddress will be dropped.
				    permit(1) - the value of the corresponding instance
				                of dasanFdbAddress will be flooded.
				"
			::= { sleFdbEntry 6 }

		
--  1.3.6.1.4.1.6296.9.8.13.2.1.7
		sleFdbEntryElapsedTime OBJECT-TYPE
			SYNTAX Unsigned32
			MAX-ACCESS read-only
			STATUS current
			DESCRIPTION
				"Elapsed time after registered"
			::= { sleFdbEntry 7 }

		
--  1.3.6.1.4.1.6296.9.8.13.3
		sleFdbControl OBJECT IDENTIFIER ::= { sleFdb 2 }

		
--  1.3.6.1.4.1.6296.9.8.13.3.1
		sleFdbEntryControlRequest OBJECT-TYPE
			SYNTAX INTEGER
				{
				createFdbEntry(1),
				destoryFdbEntry(2),
				clearFdbTableEntries(3)
				}
			MAX-ACCESS read-write
			STATUS current
			DESCRIPTION
				"Control Request."
			::= { sleFdbControl 1 }

		
--  1.3.6.1.4.1.6296.9.8.13.3.2
		sleFdbEntryControlStatus OBJECT-TYPE
			SYNTAX SleControlStatusType
			MAX-ACCESS read-only
			STATUS current
			DESCRIPTION
				"Control Status."
			::= { sleFdbControl 2 }

		
--  1.3.6.1.4.1.6296.9.8.13.3.3
		sleFdbEntryControlTimer OBJECT-TYPE
			SYNTAX Gauge32
			MAX-ACCESS read-write
			STATUS current
			DESCRIPTION
				"Cotrol Timer."
			::= { sleFdbControl 3 }

		
--  1.3.6.1.4.1.6296.9.8.13.3.5
		sleFdbEntryControlTImeStamp OBJECT-TYPE
			SYNTAX TimeTicks
			MAX-ACCESS read-only
			STATUS current
			DESCRIPTION
				" The time stamp of the last command(end of command)"
			::= { sleFdbControl 4 }

		
--  1.3.6.1.4.1.6296.9.8.13.3.4
		sleFdbEntryControlReqResult OBJECT-TYPE
			SYNTAX SleControlRequestResultType
			MAX-ACCESS read-only
			STATUS current
			DESCRIPTION
				" The result of the last user command"
			::= { sleFdbControl 5 }

		
--  1.3.6.1.4.1.6296.9.8.13.3.6
		sleFdbEntryControlFid OBJECT-TYPE
			SYNTAX Integer32 (1..4094)
			MAX-ACCESS read-write
			STATUS current
			DESCRIPTION
				"FDB identifier."
			::= { sleFdbControl 6 }

		
--  1.3.6.1.4.1.6296.9.8.13.3.7
		sleFdbEntryControlPort OBJECT-TYPE
			SYNTAX INTEGER (0..255)
			MAX-ACCESS read-write
			STATUS current
			DESCRIPTION
				"The port number of FDB entry.
				 0 : any (all) port."
			::= { sleFdbControl 7 }

		
--  1.3.6.1.4.1.6296.9.8.13.3.8
		sleFdbEntryControlMacAddress OBJECT-TYPE
			SYNTAX OCTET STRING (SIZE (0..6))
			MAX-ACCESS read-write
			STATUS current
			DESCRIPTION
				"MAC address of FDB entry."
			::= { sleFdbControl 8 }

		
--  1.3.6.1.4.1.6296.9.8.13.4
		sleFdbNotification OBJECT IDENTIFIER ::= { sleFdb 3 }

		
--  1.3.6.1.4.1.6296.9.8.13.4.2
		sleFdbEntryCreated NOTIFICATION-TYPE
			OBJECTS { sleFdbEntryControlRequest, sleFdbEntryControlTImeStamp, sleFdbEntryControlReqResult, sleFdbEntryPermission }
			STATUS current
			DESCRIPTION 
				"Created FDB Entry."
			::= { sleFdbNotification 1 }

		
--  1.3.6.1.4.1.6296.9.8.13.4.3
		sleFdbEntryDestoryed NOTIFICATION-TYPE
			OBJECTS { sleFdbEntryControlRequest, sleFdbEntryControlTImeStamp, sleFdbEntryControlMacAddress, sleFdbEntryControlReqResult }
			STATUS current
			DESCRIPTION 
				"Destroyed FDB Entry."
			::= { sleFdbNotification 2 }

		
		sleFdbTableEntriesCleared NOTIFICATION-TYPE
			OBJECTS { sleFdbEntryControlRequest, sleFdbEntryControlTImeStamp, sleFdbEntryControlMacAddress, sleFdbEntryControlReqResult }
			STATUS current
			DESCRIPTION 
				"clearFdbTableEntries.
				 In this notification PDU, key of sleFdbEntryPort 
				 is fid.port.6.0.0.0.0.0.0.
				 If port is 0, is cleared on all ports in fid."
			::= { sleFdbNotification 3 }

		
--  1.3.6.1.4.1.6296.9.8.14
		sleMfdbOld OBJECT IDENTIFIER ::= { sleBridge 14 }

		
--  1.3.6.1.4.1.6296.9.8.14.1
		sleMfdbOldTable OBJECT-TYPE
			SYNTAX SEQUENCE OF SleMfdbOldEntry
			MAX-ACCESS not-accessible
			STATUS current
			DESCRIPTION
				"The table of MFDB entries."
			::= { sleMfdbOld 1 }

		
--  1.3.6.1.4.1.6296.9.8.14.1.1
		sleMfdbOldEntry OBJECT-TYPE
			SYNTAX SleMfdbOldEntry
			MAX-ACCESS not-accessible
			STATUS current
			DESCRIPTION
				"Information about a specific MAC address that
				should be forwarding or dropping.
				key: sleMfdbMacAddress"
			INDEX { sleMfdbMacAddress }
			::= { sleMfdbOldTable 1 }

		
		SleMfdbOldEntry ::=
			SEQUENCE { 
				sleMfdbOldMacAddress
					OCTET STRING,
				sleMfdbOldEntryPermission
					INTEGER,
				sleMfdbOldVlanIndex
					INTEGER,
				sleMfdbOldPorts
					OCTET STRING
			 }

--  1.3.6.1.4.1.6296.9.8.14.1.1.1
		sleMfdbOldMacAddress OBJECT-TYPE
			SYNTAX OCTET STRING (SIZE (0..6))
			MAX-ACCESS read-only
			STATUS current
			DESCRIPTION
				"A unicast MAC address for which the device has
				forwarding or filtering information."
			::= { sleMfdbOldEntry 1 }

		
--  1.3.6.1.4.1.6296.9.8.14.1.1.2
		sleMfdbOldEntryPermission OBJECT-TYPE
			SYNTAX INTEGER
				{
				deny(0),
				permit(1)
				}
			MAX-ACCESS read-only
			STATUS current
			DESCRIPTION
				"The permission of sleMFdbMacAddress.
				The meanings of the values are: 
				    deny(0)   - the value of the corresponding instance
				                of sleMfdbMacAddress will be dropped.
				    permit(1) - the value of the corresponding instance
				                of sleMfdbMacAddress will be flooded.
				"
			::= { sleMfdbOldEntry 2 }

		
		sleMfdbOldVlanIndex OBJECT-TYPE
			SYNTAX INTEGER (0 | 1..4094)
			MAX-ACCESS read-only
			STATUS current
			DESCRIPTION
				"vlan index
				"
			::= { sleMfdbOldEntry 3 }

		
		sleMfdbOldPorts OBJECT-TYPE
			SYNTAX OCTET STRING (SIZE (0..32))
			MAX-ACCESS read-write
			STATUS current
			DESCRIPTION
				"Port Map"
			::= { sleMfdbOldEntry 4 }

		
--  1.3.6.1.4.1.6296.9.8.14.2
		sleMfdbOldControl OBJECT IDENTIFIER ::= { sleMfdbOld 2 }

		
--  1.3.6.1.4.1.6296.9.8.14.2.1
		sleMfdbOldControlRequest OBJECT-TYPE
			SYNTAX INTEGER
				{
				createMfdbEntry(1),
				destoryMfdbEntry(2),
				setMfdbEntryPermission(3),
				clearMfdbEntryTable(4)
				}
			MAX-ACCESS read-write
			STATUS current
			DESCRIPTION
				" The request of a user command"
			::= { sleMfdbOldControl 1 }

		
--  1.3.6.1.4.1.6296.9.8.14.2.2
		sleMfdbOldControlStatus OBJECT-TYPE
			SYNTAX SleControlStatusType
			MAX-ACCESS read-only
			STATUS current
			DESCRIPTION
				" The status of user command"
			::= { sleMfdbOldControl 2 }

		
--  1.3.6.1.4.1.6296.9.8.14.2.3
		sleMfdbOldControlTimer OBJECT-TYPE
			SYNTAX Gauge32
			MAX-ACCESS read-write
			STATUS current
			DESCRIPTION
				" The maximum time for the manager for a long running user command"
			::= { sleMfdbOldControl 3 }

		
--  1.3.6.1.4.1.6296.9.8.14.2.5
		sleMfdbOldControlTimeStamp OBJECT-TYPE
			SYNTAX TimeTicks
			MAX-ACCESS read-only
			STATUS current
			DESCRIPTION
				" The time stamp of the last command(end of command)"
			::= { sleMfdbOldControl 4 }

		
--  1.3.6.1.4.1.6296.9.8.14.2.4
		sleMfdbOldControlReqResult OBJECT-TYPE
			SYNTAX SleControlRequestResultType
			MAX-ACCESS read-only
			STATUS current
			DESCRIPTION
				" The result of the last user command"
			::= { sleMfdbOldControl 5 }

		
--  1.3.6.1.4.1.6296.9.8.14.2.6
		sleMfdbOldControlMacAddress OBJECT-TYPE
			SYNTAX OCTET STRING (SIZE (0..6))
			MAX-ACCESS read-write
			STATUS current
			DESCRIPTION
				"A unicast MAC address for which the device has
				forwarding or filtering information.
				  If MAC address is NULL apply mac-filter list 
				  from file '/etc/mfdb.conf'."
			::= { sleMfdbOldControl 6 }

		
--  1.3.6.1.4.1.6296.9.8.14.2.7
		sleMfdbOldControlEntryPermission OBJECT-TYPE
			SYNTAX INTEGER
				{
				deny(0),
				permit(1)
				}
			MAX-ACCESS read-write
			STATUS current
			DESCRIPTION
				"The permission of sleMFdbControlMacAddress."
			::= { sleMfdbOldControl 7 }

		
		sleMfdbOldControlVlanIndex OBJECT-TYPE
			SYNTAX INTEGER (0 | 1..4094)
			MAX-ACCESS read-write
			STATUS current
			DESCRIPTION
				"vlan index
				The value of 0 is all vlan"
			::= { sleMfdbOldControl 8 }

		
		sleMfdbOldControlPorts OBJECT-TYPE
			SYNTAX OCTET STRING (SIZE (0..32))
			MAX-ACCESS read-write
			STATUS current
			DESCRIPTION
				"Port Map 
				The value of 0x00 is all port
				"
			::= { sleMfdbOldControl 9 }

		
--  1.3.6.1.4.1.6296.9.8.14.3
		sleMfdbOldNotification OBJECT IDENTIFIER ::= { sleMfdbOld 3 }

		
--  1.3.6.1.4.1.6296.9.8.14.3.1
		sleMfdbOldEntryCreated NOTIFICATION-TYPE
			OBJECTS { sleMfdbOldControlRequest, sleMfdbOldControlTimeStamp, sleMfdbOldControlReqResult, sleMfdbOldControlEntryPermission }
			STATUS current
			DESCRIPTION 
				"Create new MFDB entry."
			::= { sleMfdbOldNotification 1 }

		
--  1.3.6.1.4.1.6296.9.8.14.3.2
		sleMfdbOldEntryDestoryed NOTIFICATION-TYPE
			OBJECTS { sleMfdbOldControlRequest, sleMfdbOldControlTimeStamp, sleMfdbOldControlReqResult, sleMfdbOldControlMacAddress }
			STATUS current
			DESCRIPTION 
				"Destroyed MFDB entry."
			::= { sleMfdbOldNotification 2 }

		
--  1.3.6.1.4.1.6296.9.8.14.3.3
		sleMfdbOldEntryPermissionChanged NOTIFICATION-TYPE
			OBJECTS { sleMfdbOldControlRequest, sleMfdbOldControlTimeStamp, sleMfdbOldControlReqResult, sleMfdbOldEntryPermission }
			STATUS current
			DESCRIPTION 
				"Changed permission of MFDB entry."
			::= { sleMfdbOldNotification 3 }

		
		sleMfdbOldEntryTableCleared NOTIFICATION-TYPE
			OBJECTS { sleMfdbOldControlRequest, sleMfdbOldControlTimeStamp, sleMfdbOldControlReqResult }
			STATUS current
			DESCRIPTION 
				"Description."
			::= { sleMfdbOldNotification 4 }

		
		sleIgmpConf OBJECT IDENTIFIER ::= { sleBridge 15 }

		
		sleIgmpConfTable OBJECT-TYPE
			SYNTAX SEQUENCE OF SleIgmpConfEntry
			MAX-ACCESS not-accessible
			STATUS current
			DESCRIPTION
				"IGMP configuration table."
			::= { sleIgmpConf 1 }

		
		sleIgmpConfEntry OBJECT-TYPE
			SYNTAX SleIgmpConfEntry
			MAX-ACCESS not-accessible
			STATUS current
			DESCRIPTION
				"key: sleVlanIndex"
			INDEX { sleVlanIndex }
			::= { sleIgmpConfTable 1 }

		
		SleIgmpConfEntry ::=
			SEQUENCE { 
				sleIgmpConfVlanIndex
					Integer32,
				sleIgmpConfEnable
					INTEGER,
				sleIgmpConfMulticastFilter
					INTEGER,
				sleIgmpConfOutmostVlan
					INTEGER,
				sleIgmpConfSnoopEnable
					INTEGER,
				sleIgmpConfSnoopJoinDelay
					Integer32,
				sleIgmpConfSnoopQueryDelay
					Integer32,
				sleIgmpConfSnoopMrouter
					Integer32,
				sleIgmpConfSnoopFastLeave
					INTEGER,
				sleIgmpConfSnoopQuerier
					INTEGER
			 }

		sleIgmpConfVlanIndex OBJECT-TYPE
			SYNTAX Integer32 (0..4094)
			MAX-ACCESS read-only
			STATUS current
			DESCRIPTION
				"sleVlanIndex in sleVlanTable"
			::= { sleIgmpConfEntry 1 }

		
		sleIgmpConfEnable OBJECT-TYPE
			SYNTAX INTEGER
				{
				disable(0),
				enable(1)
				}
			MAX-ACCESS read-only
			STATUS current
			DESCRIPTION
				"If this flag is true, IGMP multicasting is enabled. (not supported)"
			::= { sleIgmpConfEntry 2 }

		
		sleIgmpConfMulticastFilter OBJECT-TYPE
			SYNTAX INTEGER
				{
				disable(0),
				enable(1)
				}
			MAX-ACCESS read-only
			STATUS current
			DESCRIPTION
				"If this flag is true, mac address that is unregistered into IGMP table is filtered. (not supported)"
			::= { sleIgmpConfEntry 3 }

		
		sleIgmpConfOutmostVlan OBJECT-TYPE
			SYNTAX INTEGER
				{
				disable(0),
				enable(1)
				}
			MAX-ACCESS read-only
			STATUS current
			DESCRIPTION
				"Configures outmost VLAN. (not supported)"
			::= { sleIgmpConfEntry 4 }

		
		sleIgmpConfSnoopEnable OBJECT-TYPE
			SYNTAX INTEGER
				{
				disable(0),
				enable(1)
				}
			MAX-ACCESS read-only
			STATUS current
			DESCRIPTION
				"The IGMP snooping enable/disable flag"
			::= { sleIgmpConfEntry 5 }

		
		sleIgmpConfSnoopJoinDelay OBJECT-TYPE
			SYNTAX Integer32 (0..1000)
			MAX-ACCESS read-only
			STATUS current
			DESCRIPTION
				"After join message is received, the time interval until be registered into multicast group. (not supported)"
			::= { sleIgmpConfEntry 6 }

		
		sleIgmpConfSnoopQueryDelay OBJECT-TYPE
			SYNTAX Integer32 (100..900)
			MAX-ACCESS read-only
			STATUS current
			DESCRIPTION
				"After query message is send, the time interval for response waiting."
			::= { sleIgmpConfEntry 7 }

		
		sleIgmpConfSnoopMrouter OBJECT-TYPE
			SYNTAX Integer32
			MAX-ACCESS read-only
			STATUS current
			DESCRIPTION
				"The index of interface connected with multicast router."
			::= { sleIgmpConfEntry 8 }

		
		sleIgmpConfSnoopFastLeave OBJECT-TYPE
			SYNTAX INTEGER
				{
				disable(0),
				enable(1)
				}
			MAX-ACCESS read-only
			STATUS current
			DESCRIPTION
				"If this flag is true, immediately this entry is deleted, when leave message is received,"
			::= { sleIgmpConfEntry 9 }

		
		sleIgmpConfSnoopQuerier OBJECT-TYPE
			SYNTAX INTEGER
				{
				disable(0),
				enable(1)
				}
			MAX-ACCESS read-only
			STATUS current
			DESCRIPTION
				"If this flag is true, perform IGMP snooping querier."
			::= { sleIgmpConfEntry 10 }

		
		sleIgmpConfControl OBJECT IDENTIFIER ::= { sleIgmpConf 2 }

		
		sleIgmpConfControlRequest OBJECT-TYPE
			SYNTAX SleIgmpConfControlRequestType
			MAX-ACCESS read-write
			STATUS current
			DESCRIPTION
				"The request of a user command"
			::= { sleIgmpConfControl 1 }

		
		sleIgmpConfControlStatus OBJECT-TYPE
			SYNTAX SleControlStatusType
			MAX-ACCESS read-only
			STATUS current
			DESCRIPTION
				"The status of user command"
			::= { sleIgmpConfControl 2 }

		
		sleIgmpConfControlTimer OBJECT-TYPE
			SYNTAX Gauge32
			MAX-ACCESS read-write
			STATUS current
			DESCRIPTION
				"The maximum time for the manager for a long running user command"
			::= { sleIgmpConfControl 3 }

		
		sleIgmpConfControlTimeStamp OBJECT-TYPE
			SYNTAX TimeTicks
			MAX-ACCESS read-only
			STATUS current
			DESCRIPTION
				"The time stamp of the last command(end of command)"
			::= { sleIgmpConfControl 4 }

		
		sleIgmpConfControlReqResult OBJECT-TYPE
			SYNTAX SleControlRequestResultType
			MAX-ACCESS read-only
			STATUS current
			DESCRIPTION
				"The result of the last user command"
			::= { sleIgmpConfControl 5 }

		
		sleIgmpConfControlVlanIndex OBJECT-TYPE
			SYNTAX Integer32 (1..4094)
			MAX-ACCESS read-write
			STATUS current
			DESCRIPTION
				"sleVlanIndex in sleVlanTable"
			::= { sleIgmpConfControl 6 }

		
		sleIgmpConfControlEnable OBJECT-TYPE
			SYNTAX INTEGER
				{
				disable(0),
				enable(1)
				}
			MAX-ACCESS read-write
			STATUS current
			DESCRIPTION
				"If this flag is true, IGMP multicasting is enabled."
			::= { sleIgmpConfControl 7 }

		
		sleIgmpConfControlMulticastFilter OBJECT-TYPE
			SYNTAX INTEGER
				{
				disable(0),
				enable(1)
				}
			MAX-ACCESS read-write
			STATUS current
			DESCRIPTION
				"If this flag is true, mac address that is unregistered into IGMP table is filtered."
			::= { sleIgmpConfControl 8 }

		
		sleIgmpConfControlOutmostVlan OBJECT-TYPE
			SYNTAX INTEGER
				{
				disable(0),
				enable(1)
				}
			MAX-ACCESS read-write
			STATUS current
			DESCRIPTION
				"Configures outmost VLAN. (not supported)"
			::= { sleIgmpConfControl 9 }

		
		sleIgmpConfControlSnoopEnable OBJECT-TYPE
			SYNTAX INTEGER
				{
				disable(0),
				enable(1)
				}
			MAX-ACCESS read-write
			STATUS current
			DESCRIPTION
				"The IGMP snooping enable/disable flag"
			::= { sleIgmpConfControl 10 }

		
		sleIgmpConfControlSnoopJoinDelay OBJECT-TYPE
			SYNTAX Integer32 (0..1000)
			MAX-ACCESS read-write
			STATUS current
			DESCRIPTION
				"After join message is received, the time interval until be registered into multicast group. (not supported)"
			::= { sleIgmpConfControl 11 }

		
		sleIgmpConfControlSnoopQueryDelay OBJECT-TYPE
			SYNTAX Integer32 (100..900)
			MAX-ACCESS read-write
			STATUS current
			DESCRIPTION
				"After query message is send, the time interval for response waiting."
			::= { sleIgmpConfControl 12 }

		
		sleIgmpConfControlSnoopMrouter OBJECT-TYPE
			SYNTAX Integer32 (1..255)
			MAX-ACCESS read-write
			STATUS current
			DESCRIPTION
				"The index of interface connected with multicast router."
			DEFVAL { -1 }
			::= { sleIgmpConfControl 13 }

		
		sleIgmpConfControlSnoopFastLeave OBJECT-TYPE
			SYNTAX INTEGER
				{
				disable(0),
				enable(1)
				}
			MAX-ACCESS read-write
			STATUS current
			DESCRIPTION
				"If this flag is true, immediately this entry is deleted, when leave message is received,"
			::= { sleIgmpConfControl 14 }

		
		sleIgmpConfControlSnoopQuerier OBJECT-TYPE
			SYNTAX INTEGER
				{
				disable(0),
				enable(1)
				}
			MAX-ACCESS read-write
			STATUS current
			DESCRIPTION
				"If this flag is true, perform IGMP snooping querier."
			::= { sleIgmpConfControl 15 }

		
		sleIgmpConfNotification OBJECT IDENTIFIER ::= { sleIgmpConf 3 }

		
		sleIgmpConfProfileChanged NOTIFICATION-TYPE
			OBJECTS { sleIgmpConfControlRequest, sleIgmpConfControlReqResult, sleIgmpConfControlTimeStamp, sleIgmpConfSnoopMrouter, sleIgmpConfEnable, 
				sleIgmpConfMulticastFilter, sleIgmpConfOutmostVlan, sleIgmpConfSnoopEnable, sleIgmpConfSnoopJoinDelay, sleIgmpConfSnoopQueryDelay, 
				sleIgmpConfSnoopFastLeave, sleIgmpConfSnoopQuerier }
			STATUS current
			DESCRIPTION 
				"Description."
			::= { sleIgmpConfNotification 1 }

		
--  1.3.6.1.4.1.6296.9.8.15
		sleIgmpMcast OBJECT IDENTIFIER ::= { sleBridge 16 }

		
--  1.3.6.1.4.1.6296.9.8.15.1
		sleIgmpMcastTable OBJECT-TYPE
			SYNTAX SEQUENCE OF SleIgmpMcastEntry
			MAX-ACCESS not-accessible
			STATUS current
			DESCRIPTION
				" IGMP multicast table."
			::= { sleIgmpMcast 1 }

		
--  1.3.6.1.4.1.6296.9.8.15.1.1
		sleIgmpMcastEntry OBJECT-TYPE
			SYNTAX SleIgmpMcastEntry
			MAX-ACCESS not-accessible
			STATUS current
			DESCRIPTION
				" key: sleVlanIndex, sleIgmpMcastIPAddress, sleIgmpMcastPortIndex"
			INDEX { sleVlanIndex, sleIgmpMcastIPAddress, sleIgmpMcastPortIndex }
			::= { sleIgmpMcastTable 1 }

		
		SleIgmpMcastEntry ::=
			SEQUENCE { 
				sleIgmpMcastVlanIndex
					Integer32,
				sleIgmpMcastIPAddress
					IpAddress,
				sleIgmpMcastPortIndex
					Integer32,
				sleIgmpMcastType
					INTEGER,
				sleIgmpMcastExpireTime
					Integer32
			 }

		sleIgmpMcastVlanIndex OBJECT-TYPE
			SYNTAX Integer32 (1..4094)
			MAX-ACCESS read-only
			STATUS current
			DESCRIPTION
				"sleVlanIndex in sleVlanTable"
			::= { sleIgmpMcastEntry 1 }

		
--  1.3.6.1.4.1.6296.9.8.15.1.1.2
		sleIgmpMcastIPAddress OBJECT-TYPE
			SYNTAX IpAddress
			MAX-ACCESS read-only
			STATUS current
			DESCRIPTION
				"The IP multicast group address for which this entry contains information."
			::= { sleIgmpMcastEntry 2 }

		
		sleIgmpMcastPortIndex OBJECT-TYPE
			SYNTAX Integer32 (1..255)
			MAX-ACCESS read-only
			STATUS current
			DESCRIPTION
				"Port index"
			::= { sleIgmpMcastEntry 3 }

		
		sleIgmpMcastType OBJECT-TYPE
			SYNTAX INTEGER
				{
				static(0),
				dynamic(1)
				}
			MAX-ACCESS read-only
			STATUS current
			DESCRIPTION
				"indicate either static- or dynamic- IP multicast group address"
			::= { sleIgmpMcastEntry 4 }

		
		sleIgmpMcastExpireTime OBJECT-TYPE
			SYNTAX Integer32
			MAX-ACCESS read-only
			STATUS current
			DESCRIPTION
				"Expiry time of this dynamic multicast table entry."
			::= { sleIgmpMcastEntry 5 }

		
--  1.3.6.1.4.1.6296.9.8.15.2
		sleIgmpMcastControl OBJECT IDENTIFIER ::= { sleIgmpMcast 2 }

		
--  1.3.6.1.4.1.6296.9.8.15.2.1
		sleIgmpMcastControlReqest OBJECT-TYPE
			SYNTAX SleIgmpMcastControlRequestType
			MAX-ACCESS read-write
			STATUS current
			DESCRIPTION
				" The request of a user command"
			::= { sleIgmpMcastControl 1 }

		
--  1.3.6.1.4.1.6296.9.8.15.2.2
		sleIgmpMcastControlStatus OBJECT-TYPE
			SYNTAX SleControlStatusType
			MAX-ACCESS read-only
			STATUS current
			DESCRIPTION
				"The status of user command"
			::= { sleIgmpMcastControl 2 }

		
--  1.3.6.1.4.1.6296.9.8.15.2.3
		sleIgmpMcastControlTimer OBJECT-TYPE
			SYNTAX Gauge32
			MAX-ACCESS read-write
			STATUS current
			DESCRIPTION
				" The maximum time for the manager for a long running user command"
			::= { sleIgmpMcastControl 3 }

		
--  1.3.6.1.4.1.6296.9.8.15.2.4
		sleIgmpMcastControlTimeStamp OBJECT-TYPE
			SYNTAX TimeTicks
			MAX-ACCESS read-only
			STATUS current
			DESCRIPTION
				" The time stamp of the last command(end of command)"
			::= { sleIgmpMcastControl 4 }

		
--  1.3.6.1.4.1.6296.9.8.15.2.5
		sleIgmpMcastControlReqResult OBJECT-TYPE
			SYNTAX SleControlRequestResultType
			MAX-ACCESS read-only
			STATUS current
			DESCRIPTION
				" The result of the last user command"
			::= { sleIgmpMcastControl 5 }

		
--  1.3.6.1.4.1.6296.9.8.15.2.6
		sleIgmpMcastControlVlanIndex OBJECT-TYPE
			SYNTAX Integer32 (1..4094)
			MAX-ACCESS read-write
			STATUS current
			DESCRIPTION
				" sleVlanIndex in sleVlanTable"
			::= { sleIgmpMcastControl 6 }

		
--  Vlan ID
-- 1.3.6.1.4.1.6296.9.8.15.2.7
		sleIgmpMcastControlIPAddress OBJECT-TYPE
			SYNTAX IpAddress
			MAX-ACCESS read-write
			STATUS current
			DESCRIPTION
				" The multicast group address."
			::= { sleIgmpMcastControl 7 }

		
		sleIgmpMcastControlPortIndex OBJECT-TYPE
			SYNTAX Integer32 (1..255)
			MAX-ACCESS read-write
			STATUS current
			DESCRIPTION
				"Port index"
			::= { sleIgmpMcastControl 8 }

		
--  IP address
-- 1.3.6.1.4.1.6296.9.8.15.3
		sleIgmpMcastNotification OBJECT IDENTIFIER ::= { sleIgmpMcast 3 }

		
--  1.3.6.1.4.1.6296.9.8.15.3.1
		sleIgmpStaticMcastCreated NOTIFICATION-TYPE
			OBJECTS { sleIgmpMcastControlReqest, sleIgmpMcastControlTimeStamp, sleIgmpMcastControlPortIndex, sleIgmpMcastControlReqResult }
			STATUS current
			DESCRIPTION 
				" "
			::= { sleIgmpMcastNotification 1 }

		
--  1.3.6.1.4.1.6296.9.8.15.3.2
		sleIgmpStaticMcastDestroyed NOTIFICATION-TYPE
			OBJECTS { sleIgmpMcastControlReqest, sleIgmpMcastControlReqResult, sleIgmpMcastControlPortIndex, sleIgmpMcastControlTimeStamp }
			STATUS current
			DESCRIPTION 
				" "
			::= { sleIgmpMcastNotification 2 }

		
		sleIgmpMcastCounterInfo OBJECT IDENTIFIER ::= { sleIgmpMcast 4 }

		
		sleIgmpMcastCounterInfoGroupCount OBJECT-TYPE
			SYNTAX Counter32
			MAX-ACCESS read-only
			STATUS current
			DESCRIPTION
				"Count of IGMP Group entry."
			::= { sleIgmpMcastCounterInfo 1 }

		
		sleIgmpMcastCounterInfoSnoopingCount OBJECT-TYPE
			SYNTAX Counter32
			MAX-ACCESS read-only
			STATUS current
			DESCRIPTION
				"Count of IGMP Snooping Group entry."
			::= { sleIgmpMcastCounterInfo 2 }

		
		sleMcastMrouteCounterInfo OBJECT IDENTIFIER ::= { sleIgmpMcast 5 }

		
		sleMcastMrouteJoinedCount OBJECT-TYPE
			SYNTAX Counter32
			MAX-ACCESS read-only
			STATUS current
			DESCRIPTION
				"The count of Mroute Joined channel"
			::= { sleMcastMrouteCounterInfo 1 }

		
--  1.3.6.1.4.1.6296.9.8.17
		sleStackDevice OBJECT IDENTIFIER ::= { sleBridge 17 }

		
--  1.3.6.1.4.1.6296.9.8.17.1
		sleStackDeviceTable OBJECT-TYPE
			SYNTAX SEQUENCE OF SleStackDeviceEntry
			MAX-ACCESS not-accessible
			STATUS current
			DESCRIPTION
				"Information table of stack master/slave devices."
			::= { sleStackDevice 1 }

		
--  1.3.6.1.4.1.6296.9.8.17.1.1
		sleStackDeviceEntry OBJECT-TYPE
			SYNTAX SleStackDeviceEntry
			MAX-ACCESS not-accessible
			STATUS current
			DESCRIPTION
				"Information table entry of stack master/slave devices.
				key: sleStackDeviceMacAddress"
			INDEX { sleStackDeviceMacAddress }
			::= { sleStackDeviceTable 1 }

		
		SleStackDeviceEntry ::=
			SEQUENCE { 
				sleStackDeviceMacAddress
					OCTET STRING,
				sleStackDeviceNodeId
					Integer32,
				sleStackDeviceDescriptor
					OCTET STRING,
				sleStackDeviceMode
					INTEGER,
				sleStackDeviceStatus
					INTEGER,
				sleStackDeviceType
					OCTET STRING,
				sleStackDeviceHostName
					OCTET STRING,
				sleStackDevicePortNum
					INTEGER
			 }

--  1.3.6.1.4.1.6296.9.8.17.1.1.1
		sleStackDeviceMacAddress OBJECT-TYPE
			SYNTAX OCTET STRING (SIZE (0..6))
			MAX-ACCESS read-only
			STATUS current
			DESCRIPTION
				"MAC address of stack device."
			::= { sleStackDeviceEntry 1 }

		
--  1.3.6.1.4.1.6296.9.8.17.1.1.2
		sleStackDeviceNodeId OBJECT-TYPE
			SYNTAX Integer32
			MAX-ACCESS read-only
			STATUS current
			DESCRIPTION
				"Index stack device nodes."
			::= { sleStackDeviceEntry 2 }

		
--  1.3.6.1.4.1.6296.9.8.17.1.1.3
		sleStackDeviceDescriptor OBJECT-TYPE
			SYNTAX OCTET STRING (SIZE (0..256))
			MAX-ACCESS read-only
			STATUS current
			DESCRIPTION
				"Description of stack device."
			::= { sleStackDeviceEntry 3 }

		
--  1.3.6.1.4.1.6296.9.8.17.1.1.4
		sleStackDeviceMode OBJECT-TYPE
			SYNTAX INTEGER
				{
				master(1),
				slave(2)
				}
			MAX-ACCESS read-only
			STATUS current
			DESCRIPTION
				"Stack status of device."
			::= { sleStackDeviceEntry 4 }

		
--  1.3.6.1.4.1.6296.9.8.17.1.1.6
		sleStackDeviceStatus OBJECT-TYPE
			SYNTAX INTEGER
				{
				inactive(0),
				active(1)
				}
			MAX-ACCESS read-only
			STATUS current
			DESCRIPTION
				"Stack status of stack device."
			::= { sleStackDeviceEntry 5 }

		
--  1.3.6.1.4.1.6296.9.8.17.1.1.7
		sleStackDeviceType OBJECT-TYPE
			SYNTAX OCTET STRING (SIZE (0..16))
			MAX-ACCESS read-only
			STATUS current
			DESCRIPTION
				"Device type of stack device."
			::= { sleStackDeviceEntry 6 }

		
--  1.3.6.1.4.1.6296.9.8.17.1.1.8
		sleStackDeviceHostName OBJECT-TYPE
			SYNTAX OCTET STRING (SIZE (0..32))
			MAX-ACCESS read-only
			STATUS current
			DESCRIPTION
				"Hostname of stack device."
			::= { sleStackDeviceEntry 7 }

		
--  1.3.6.1.4.1.6296.9.8.17.1.1.9
		sleStackDevicePortNum OBJECT-TYPE
			SYNTAX INTEGER (0..255)
			MAX-ACCESS read-only
			STATUS current
			DESCRIPTION
				"Number of stack device's ports."
			::= { sleStackDeviceEntry 8 }

		
--  1.3.6.1.4.1.6296.9.8.17.2
		sleStackDeviceControl OBJECT IDENTIFIER ::= { sleStackDevice 2 }

		
--  1.3.6.1.4.1.6296.9.8.17.2.1
		sleStackDeviceControlRequest OBJECT-TYPE
			SYNTAX INTEGER
				{
				createStackSlaveDevice(1),
				destoryStackSlaveDevice(2)
				}
			MAX-ACCESS read-write
			STATUS current
			DESCRIPTION
				" The request of a user command"
			::= { sleStackDeviceControl 1 }

		
--  1.3.6.1.4.1.6296.9.8.17.2.2
		sleStackDeviceControlStatus OBJECT-TYPE
			SYNTAX SleControlStatusType
			MAX-ACCESS read-only
			STATUS current
			DESCRIPTION
				" The status of user command"
			::= { sleStackDeviceControl 2 }

		
--  1.3.6.1.4.1.6296.9.8.17.2.3
		sleStackDeviceControlTimer OBJECT-TYPE
			SYNTAX Gauge32
			MAX-ACCESS read-write
			STATUS current
			DESCRIPTION
				" The maximum time for the manager for a long running user command"
			::= { sleStackDeviceControl 3 }

		
--  1.3.6.1.4.1.6296.9.8.17.2.5
		sleStackDeviceControlTImeStamp OBJECT-TYPE
			SYNTAX TimeTicks
			MAX-ACCESS read-only
			STATUS current
			DESCRIPTION
				" The time stamp of the last command(end of command)"
			::= { sleStackDeviceControl 4 }

		
--  1.3.6.1.4.1.6296.9.8.17.2.4
		sleStackDeviceControlReqResult OBJECT-TYPE
			SYNTAX SleControlRequestResultType
			MAX-ACCESS read-only
			STATUS current
			DESCRIPTION
				" The result of the last user command"
			::= { sleStackDeviceControl 5 }

		
--  1.3.6.1.4.1.6296.9.8.17.2.6
		sleStackDeviceControlMacAddress OBJECT-TYPE
			SYNTAX OCTET STRING (SIZE (0..6))
			MAX-ACCESS read-write
			STATUS current
			DESCRIPTION
				"MAC address of slave device."
			::= { sleStackDeviceControl 6 }

		
--  1.3.6.1.4.1.6296.9.8.17.2.7
		sleStackDeviceControlDescriptor OBJECT-TYPE
			SYNTAX OCTET STRING (SIZE (0..256))
			MAX-ACCESS read-write
			STATUS current
			DESCRIPTION
				"Description of stack slave device."
			::= { sleStackDeviceControl 7 }

		
--  1.3.6.1.4.1.6296.9.8.17.3
		sleStackDeviceNotification OBJECT IDENTIFIER ::= { sleStackDevice 3 }

		
--  1.3.6.1.4.1.6296.9.8.17.3.1
		sleStackDeviceCreated NOTIFICATION-TYPE
			OBJECTS { sleStackDeviceControlRequest, sleStackDeviceControlTImeStamp, sleStackDeviceControlReqResult, sleStackDeviceDescriptor }
			STATUS current
			DESCRIPTION 
				"Added stack slave device to master stack device."
			::= { sleStackDeviceNotification 1 }

		
--  1.3.6.1.4.1.6296.9.8.17.3.2
		sleStackDeviceDestoryed NOTIFICATION-TYPE
			OBJECTS { sleStackDeviceControlRequest, sleStackDeviceControlTImeStamp, sleStackDeviceControlMacAddress, sleStackDeviceControlReqResult }
			STATUS current
			DESCRIPTION 
				"Deleted stack slave device from master stack device."
			::= { sleStackDeviceNotification 2 }

		
		sleErpDomain OBJECT IDENTIFIER ::= { sleBridge 18 }

		
		sleErpDomainTable OBJECT-TYPE
			SYNTAX SEQUENCE OF SleErpDomainEntry
			MAX-ACCESS not-accessible
			STATUS current
			DESCRIPTION
				" erp domain table."
			::= { sleErpDomain 1 }

		
		sleErpDomainEntry OBJECT-TYPE
			SYNTAX SleErpDomainEntry
			MAX-ACCESS not-accessible
			STATUS current
			DESCRIPTION
				" key: sleErpDomainIndex"
			INDEX { sleErpDomainIndex }
			::= { sleErpDomainTable 1 }

		
		SleErpDomainEntry ::=
			SEQUENCE { 
				sleErpDomainIndex
					INTEGER,
				sleErpDomainName
					OCTET STRING,
				sleErpDomainPrimaryPort
					InterfaceIndex,
				sleErpDomainSecondaryPort
					InterfaceIndex,
				sleErpDomainBridgeRole
					INTEGER,
				sleErpDomainProtectionActivation
					INTEGER,
				sleErpDomainOperatorRequest
					INTEGER,
				sleErpDomainWaitToRestoreTime
					INTEGER,
				sleErpDomainTestPacketInterval
					INTEGER,
				sleErpDomainLearningDisabledTime
					INTEGER,
				sleErpDomainNodeStatus
					INTEGER,
				sleErpDomainRingStatus
					INTEGER,
				sleErpDomainLotp
					INTEGER,
				sleErpDomainULotp
					INTEGER,
				sleErpDomainMultipleRM
					INTEGER,
				sleErpDomainRMNodeReacheablility
					INTEGER,
				sleErpDomainHoldOffTime
					INTEGER,
				sleErpDomainRingPriority
					INTEGER
			 }

		sleErpDomainIndex OBJECT-TYPE
			SYNTAX INTEGER (1..4094)
			MAX-ACCESS read-only
			STATUS current
			DESCRIPTION
				"An index value that uniquely identifies an ERP domain."
			::= { sleErpDomainEntry 1 }

		
		sleErpDomainName OBJECT-TYPE
			SYNTAX OCTET STRING
			MAX-ACCESS read-only
			STATUS current
			DESCRIPTION
				"Domain name."
			::= { sleErpDomainEntry 2 }

		
		sleErpDomainPrimaryPort OBJECT-TYPE
			SYNTAX InterfaceIndex
			MAX-ACCESS read-write
			STATUS current
			DESCRIPTION
				"Interface index that represents the primary port of the domain."
			::= { sleErpDomainEntry 3 }

		
		sleErpDomainSecondaryPort OBJECT-TYPE
			SYNTAX InterfaceIndex
			MAX-ACCESS read-only
			STATUS current
			DESCRIPTION
				"Interface index that represents the secondary port of the domain."
			::= { sleErpDomainEntry 4 }

		
		sleErpDomainBridgeRole OBJECT-TYPE
			SYNTAX INTEGER
				{
				normalNode(0),
				rmNode(1)
				}
			MAX-ACCESS read-only
			STATUS current
			DESCRIPTION
				"Mode that the ERP domain may operate in."
			::= { sleErpDomainEntry 5 }

		
		sleErpDomainProtectionActivation OBJECT-TYPE
			SYNTAX INTEGER
				{
				deactivated(0),
				activated(1)
				}
			MAX-ACCESS read-only
			STATUS current
			DESCRIPTION
				"Protection activation."
			::= { sleErpDomainEntry 6 }

		
		sleErpDomainOperatorRequest OBJECT-TYPE
			SYNTAX INTEGER
				{
				clear(0),
				manualToSecondary(1)
				}
			MAX-ACCESS read-only
			STATUS current
			DESCRIPTION
				"Operator Request."
			::= { sleErpDomainEntry 7 }

		
		sleErpDomainWaitToRestoreTime OBJECT-TYPE
			SYNTAX INTEGER (1..720)
			MAX-ACCESS read-only
			STATUS current
			DESCRIPTION
				"Time in seconds taken to verify that ring integrity is restored."
			::= { sleErpDomainEntry 8 }

		
		sleErpDomainTestPacketInterval OBJECT-TYPE
			SYNTAX INTEGER (10..500)
			MAX-ACCESS read-only
			STATUS current
			DESCRIPTION
				"Time in mili seconds between consecutive transmissions of test packages."
			::= { sleErpDomainEntry 9 }

		
		sleErpDomainLearningDisabledTime OBJECT-TYPE
			SYNTAX INTEGER (0..500)
			MAX-ACCESS read-only
			STATUS current
			DESCRIPTION
				"Time in mili seconds during which learning is disabled after a FDB flash."
			::= { sleErpDomainEntry 10 }

		
		sleErpDomainNodeStatus OBJECT-TYPE
			SYNTAX INTEGER
				{
				rmidle(0),
				primaryProtecting(1),
				protecting(2),
				idle(3),
				failedS(4),
				failedP(5),
				preForward(6),
				isolated(7),
				deactivated(8),
				backoff(9)
				}
			MAX-ACCESS read-only
			STATUS current
			DESCRIPTION
				"Node status."
			::= { sleErpDomainEntry 11 }

		
		sleErpDomainRingStatus OBJECT-TYPE
			SYNTAX INTEGER
				{
				normal(0),
				protecting(1),
				unknown(2)
				}
			MAX-ACCESS read-only
			STATUS current
			DESCRIPTION
				"Actual protection state on the ring."
			::= { sleErpDomainEntry 12 }

		
		sleErpDomainLotp OBJECT-TYPE
			SYNTAX INTEGER
				{
				clear(0),
				raised(1)
				}
			MAX-ACCESS read-only
			STATUS current
			DESCRIPTION
				"Loss of Test Packet alarm status. Only meaningful in RM node."
			::= { sleErpDomainEntry 13 }

		
		sleErpDomainULotp OBJECT-TYPE
			SYNTAX INTEGER
				{
				clear(0),
				raised(1)
				}
			MAX-ACCESS read-only
			STATUS current
			DESCRIPTION
				"Unidirectional Detection of  Loss of Test Packet alarm status.
				Only meaningful in RM node."
			::= { sleErpDomainEntry 14 }

		
		sleErpDomainMultipleRM OBJECT-TYPE
			SYNTAX INTEGER
				{
				clear(0),
				raised(1)
				}
			MAX-ACCESS read-only
			STATUS current
			DESCRIPTION
				"Multiple Redundancy Manager alarm status. Only meaningful
				in RM node."
			::= { sleErpDomainEntry 15 }

		
		sleErpDomainRMNodeReacheablility OBJECT-TYPE
			SYNTAX INTEGER
				{
				clear(0),
				raised(1)
				}
			MAX-ACCESS read-only
			STATUS current
			DESCRIPTION
				"RM Node reacheability alarm status. Only meaningful in
				normal node."
			::= { sleErpDomainEntry 16 }

		
		sleErpDomainHoldOffTime OBJECT-TYPE
			SYNTAX INTEGER (0 | 1..20000)
			MAX-ACCESS read-only
			STATUS current
			DESCRIPTION
				"The hold off time."
			::= { sleErpDomainEntry 17 }

		
		sleErpDomainRingPriority OBJECT-TYPE
			SYNTAX INTEGER (0 | 1..255)
			MAX-ACCESS read-only
			STATUS current
			DESCRIPTION
				"The ring priority"
			::= { sleErpDomainEntry 18 }

		
		sleErpDomainControl OBJECT IDENTIFIER ::= { sleErpDomain 2 }

		
		sleErpDomainControlRequest OBJECT-TYPE
			SYNTAX INTEGER
				{
				createErpDomain(1),
				destroyErpDomain(2),
				setErpDomainProfile(3),
				setErpProtectionActivation(4),
				setErpHoldOffTime(5),
				setErpRingPriority(6),
				setErpTrap(7)
				}
			MAX-ACCESS read-write
			STATUS current
			DESCRIPTION
				"
				createErpDomain:
				sleErpDomainControlIndex
				sleErpDomainControlName
				sleErpDomainControlPrimaryPort
				sleErpDomainControlSecondaryPort
				sleErpDomainControlBridgeRole
				sleErpDomainControlProtectionActivation
				sleErpDomainControlOperatorRequest
				sleErpDomainControlWaitToRestoreTime
				sleErpDomainControlTestPacketInterval
				sleErpDomainControlLearningDisabledTime
				
				destroyErpDomain:
				sleErpDomainControlIndex
				 
				setErpDomainProfile:
				sleErpDomainControlIndex 
				sleErpDomainControlName
				sleErpDomainControlPrimaryPort
				sleErpDomainControlSecondaryPort
				sleErpDomainControlBridgeRole
				sleErpDomainControlOperatorRequest
				sleErpDomainControlWaitToRestoreTime
				sleErpDomainControlTestPacketInterval
				sleErpDomainControlLearningDisabledTime
				
				setErpProtectionActivation:
				sleErpDomainControlIndex 
				sleErpDomainControlProtectionActivation
				"
			::= { sleErpDomainControl 1 }

		
		sleErpDomainControlStatus OBJECT-TYPE
			SYNTAX SleControlStatusType
			MAX-ACCESS read-only
			STATUS current
			DESCRIPTION
				"The status of a user command. 
				"
			::= { sleErpDomainControl 2 }

		
		sleErpDomainControlTimer OBJECT-TYPE
			SYNTAX Gauge32
			MAX-ACCESS read-write
			STATUS current
			DESCRIPTION
				"The maximum wait time for the manager for a long running user command. 
				"
			::= { sleErpDomainControl 3 }

		
		sleErpDomainControlTImeStamp OBJECT-TYPE
			SYNTAX TimeTicks
			MAX-ACCESS read-only
			STATUS current
			DESCRIPTION
				"The time stamp of the last command (end of command)."
			::= { sleErpDomainControl 4 }

		
		sleErpDomainControlReqResult OBJECT-TYPE
			SYNTAX SleControlRequestResultType
			MAX-ACCESS read-only
			STATUS current
			DESCRIPTION
				"The result of the last user command."
			::= { sleErpDomainControl 5 }

		
		sleErpDomainControlIndex OBJECT-TYPE
			SYNTAX Integer32
			MAX-ACCESS read-write
			STATUS current
			DESCRIPTION
				" An index value that uniquely identifies an ERP domain."
			::= { sleErpDomainControl 6 }

		
		sleErpDomainControlName OBJECT-TYPE
			SYNTAX OCTET STRING
			MAX-ACCESS read-write
			STATUS current
			DESCRIPTION
				" Domain name."
			::= { sleErpDomainControl 7 }

		
		sleErpDomainControlPrimaryPort OBJECT-TYPE
			SYNTAX InterfaceIndex
			MAX-ACCESS read-write
			STATUS current
			DESCRIPTION
				" Interface index that represents the primary port of the domain."
			::= { sleErpDomainControl 8 }

		
		sleErpDomainControlSecondaryPort OBJECT-TYPE
			SYNTAX InterfaceIndex
			MAX-ACCESS read-write
			STATUS current
			DESCRIPTION
				" Interface index that represents the secondary port of the domain."
			::= { sleErpDomainControl 9 }

		
		sleErpDomainControlBridgeRole OBJECT-TYPE
			SYNTAX INTEGER
				{
				normalNode(0),
				rmNode(1)
				}
			MAX-ACCESS read-write
			STATUS current
			DESCRIPTION
				" Mode that the ERP domain may operate in."
			::= { sleErpDomainControl 10 }

		
		sleErpDomainControlProtectionActivation OBJECT-TYPE
			SYNTAX INTEGER
				{
				deactivated(0),
				activated(1)
				}
			MAX-ACCESS read-write
			STATUS current
			DESCRIPTION
				" Protection activation."
			::= { sleErpDomainControl 11 }

		
		sleErpDomainControlOperatorRequest OBJECT-TYPE
			SYNTAX INTEGER
				{
				clear(0),
				manualToSecondary(1)
				}
			MAX-ACCESS read-write
			STATUS current
			DESCRIPTION
				"Operator Request."
			::= { sleErpDomainControl 12 }

		
		sleErpDomainControlWaitToRestoreTime OBJECT-TYPE
			SYNTAX INTEGER (1..720)
			MAX-ACCESS read-write
			STATUS current
			DESCRIPTION
				" Time in seconds taken to verify that ring integrity is restored."
			::= { sleErpDomainControl 13 }

		
		sleErpDomainControlTestPacketInterval OBJECT-TYPE
			SYNTAX INTEGER (10..500)
			MAX-ACCESS read-write
			STATUS current
			DESCRIPTION
				" Time in mili seconds between consecutive transmissions of test packages."
			::= { sleErpDomainControl 14 }

		
		sleErpDomainControlLearningDisabledTime OBJECT-TYPE
			SYNTAX INTEGER (0..500)
			MAX-ACCESS read-write
			STATUS current
			DESCRIPTION
				" Time in mili seconds during which learning is disabled after a FDB flash."
			::= { sleErpDomainControl 15 }

		
		sleErpDomainControlHoldOffTime OBJECT-TYPE
			SYNTAX INTEGER (0 | 1..20000)
			MAX-ACCESS read-write
			STATUS current
			DESCRIPTION
				"The hold off time."
			::= { sleErpDomainControl 16 }

		
		sleErpDomainControlRingPriority OBJECT-TYPE
			SYNTAX INTEGER (0 | 1..255)
			MAX-ACCESS read-write
			STATUS current
			DESCRIPTION
				"The ring priority"
			::= { sleErpDomainControl 17 }

		
		sleErpDomainControlLotp OBJECT-TYPE
			SYNTAX INTEGER
				{
				clear(0),
				raised(1)
				}
			MAX-ACCESS read-write
			STATUS current
			DESCRIPTION
				"Loss of Test Packet alarm status. Only meaningful in RM node."
			::= { sleErpDomainControl 18 }

		
		sleErpDomainControlULotp OBJECT-TYPE
			SYNTAX INTEGER
				{
				clear(0),
				raised(1)
				}
			MAX-ACCESS read-write
			STATUS current
			DESCRIPTION
				"Unidirectional Detection of  Loss of Test Packet alarm status.
				Only meaningful in RM node."
			::= { sleErpDomainControl 19 }

		
		sleErpDomainControlMultipleRM OBJECT-TYPE
			SYNTAX INTEGER
				{
				clear(0),
				raised(1)
				}
			MAX-ACCESS read-write
			STATUS current
			DESCRIPTION
				"Multiple Redundancy Manager alarm status. Only meaningful
				in RM node.
				"
			::= { sleErpDomainControl 20 }

		
		sleErpDomainControlRMNodeReacheablility OBJECT-TYPE
			SYNTAX INTEGER
				{
				clear(0),
				raised(1)
				}
			MAX-ACCESS read-write
			STATUS current
			DESCRIPTION
				"Multiple Redundancy Manager alarm status. Only meaningful
				in RM node."
			::= { sleErpDomainControl 21 }

		
		sleErpDomainNotification OBJECT IDENTIFIER ::= { sleErpDomain 3 }

		
		sleErpDomainCreated NOTIFICATION-TYPE
			OBJECTS { sleErpDomainControlRequest, sleErpDomainControlReqResult, sleErpDomainControlTImeStamp, sleErpDomainName, sleErpDomainPrimaryPort, 
				sleErpDomainSecondaryPort, sleErpDomainBridgeRole, sleErpDomainProtectionActivation, sleErpDomainOperatorRequest, sleErpDomainWaitToRestoreTime, 
				sleErpDomainTestPacketInterval, sleErpDomainLearningDisabledTime }
			STATUS current
			DESCRIPTION 
				" "
			::= { sleErpDomainNotification 1 }

		
		sleErpDomainDestroyed NOTIFICATION-TYPE
			OBJECTS { sleErpDomainControlRequest, sleErpDomainControlReqResult, sleErpDomainControlIndex, sleErpDomainControlTImeStamp }
			STATUS current
			DESCRIPTION 
				" "
			::= { sleErpDomainNotification 2 }

		
		sleErpDomainProfileChanged NOTIFICATION-TYPE
			OBJECTS { sleErpDomainControlRequest, sleErpDomainControlReqResult, sleErpDomainControlTImeStamp, sleErpDomainName, sleErpDomainPrimaryPort, 
				sleErpDomainSecondaryPort, sleErpDomainBridgeRole, sleErpDomainOperatorRequest, sleErpDomainWaitToRestoreTime, sleErpDomainTestPacketInterval, 
				sleErpDomainLearningDisabledTime }
			STATUS current
			DESCRIPTION 
				" "
			::= { sleErpDomainNotification 3 }

		
		sleErpProtectionActivationChanged NOTIFICATION-TYPE
			OBJECTS { sleErpDomainControlRequest, sleErpDomainControlReqResult, sleErpDomainControlTImeStamp, sleErpDomainProtectionActivation }
			STATUS current
			DESCRIPTION 
				" "
			::= { sleErpDomainNotification 4 }

		
		sleErpHoldOffTimeChanged NOTIFICATION-TYPE
			OBJECTS { sleErpDomainControlRequest, sleErpDomainControlTImeStamp, sleErpDomainControlReqResult, sleErpDomainHoldOffTime }
			STATUS current
			DESCRIPTION 
				"Description."
			::= { sleErpDomainNotification 5 }

		
		sleErpRingPriorityChanged NOTIFICATION-TYPE
			OBJECTS { sleErpDomainControlRequest, sleErpDomainControlTImeStamp, sleErpDomainControlReqResult, sleErpDomainRingPriority }
			STATUS current
			DESCRIPTION 
				"Description."
			::= { sleErpDomainNotification 6 }

		
		sleErpTrapChanged NOTIFICATION-TYPE
			OBJECTS { sleErpDomainControlRequest, sleErpDomainControlTImeStamp, sleErpDomainControlReqResult, sleErpDomainLotp, sleErpDomainULotp, 
				sleErpDomainMultipleRM, sleErpDomainRMNodeReacheablility }
			STATUS current
			DESCRIPTION 
				"Description."
			::= { sleErpDomainNotification 7 }

		
--  1.3.6.1.4.1.6296.9.8.19
		sleLldpPort OBJECT IDENTIFIER ::= { sleBridge 19 }

		
--  1.3.6.1.4.1.6296.9.8.19.1
		sleLldpPortTable OBJECT-TYPE
			SYNTAX SEQUENCE OF SleLldpPortEntry
			MAX-ACCESS not-accessible
			STATUS current
			DESCRIPTION
				"LLDP port table."
			::= { sleLldpPort 1 }

		
--  1.3.6.1.4.1.6296.9.8.19.1.1
		sleLldpPortEntry OBJECT-TYPE
			SYNTAX SleLldpPortEntry
			MAX-ACCESS not-accessible
			STATUS current
			DESCRIPTION
				" key: sleLldpPortIndex"
			INDEX { sleLldpPortIndex }
			::= { sleLldpPortTable 1 }

		
		SleLldpPortEntry ::=
			SEQUENCE { 
				sleLldpPortIndex
					INTEGER,
				sleLldpPortActivity
					Boolean,
				sleLldpPortAdminStatus
					INTEGER,
				sleLldpPortNotificationEnable
					Boolean,
				sleLldpPortTLVsTxEnable
					BITS,
				sleLldpPortMgmtTxEnable
					Boolean,
				sleLldpPortMgmtAddress
					IpAddress
			 }

--  1.3.6.1.4.1.6296.9.8.19.1.1.1
		sleLldpPortIndex OBJECT-TYPE
			SYNTAX INTEGER (1..255)
			MAX-ACCESS read-only
			STATUS current
			DESCRIPTION
				" LLDP port index"
			::= { sleLldpPortEntry 1 }

		
		sleLldpPortActivity OBJECT-TYPE
			SYNTAX Boolean
			MAX-ACCESS read-only
			STATUS current
			DESCRIPTION
				"sleLldpPortActivity"
			::= { sleLldpPortEntry 2 }

		
--  1.3.6.1.4.1.6296.9.8.19.1.1.2
		sleLldpPortAdminStatus OBJECT-TYPE
			SYNTAX INTEGER
				{
				txOnly(1),
				rxOnly(2),
				txAndRx(3),
				disabled(4)
				}
			MAX-ACCESS read-write
			STATUS current
			DESCRIPTION
				"The administratively desired status of the local LLDP agent."
			::= { sleLldpPortEntry 3 }

		
--  It controls, on a per port basis,  whether or not notifications from the agent are enabled.
-- 1.3.6.1.4.1.6296.9.8.19.1.1.3
		sleLldpPortNotificationEnable OBJECT-TYPE
			SYNTAX Boolean
			MAX-ACCESS read-write
			STATUS current
			DESCRIPTION
				"It controls, on a per port basis,  whether or not notifications from the agent are enabled. "
			::= { sleLldpPortEntry 4 }

		
--  1.3.6.1.4.1.6296.9.8.19.1.1.4
		sleLldpPortTLVsTxEnable OBJECT-TYPE
			SYNTAX BITS
				{
				portDesc(0),
				sysName(1),
				sysDesc(2),
				sysCap(3)
				}
			MAX-ACCESS read-write
			STATUS current
			DESCRIPTION
				"Bitmap that includes the basic set of LLDP TLVs whose transmission is allowed on the local LLDP agent by the network management."
			::= { sleLldpPortEntry 5 }

		
		sleLldpPortMgmtTxEnable OBJECT-TYPE
			SYNTAX Boolean
			MAX-ACCESS read-only
			STATUS current
			DESCRIPTION
				"It indicates that the port is either enable or not to transfer management address."
			::= { sleLldpPortEntry 6 }

		
		sleLldpPortMgmtAddress OBJECT-TYPE
			SYNTAX IpAddress
			MAX-ACCESS read-only
			STATUS current
			DESCRIPTION
				"Management address to transfer on the port."
			::= { sleLldpPortEntry 7 }

		
--  1.3.6.1.4.1.6296.9.8.19.2
		sleLldpPortControl OBJECT IDENTIFIER ::= { sleLldpPort 2 }

		
--  1.3.6.1.4.1.6296.9.8.19.2.1
		sleLldpPortControlRequest OBJECT-TYPE
			SYNTAX INTEGER { setLldpPortProfile(1) }
			MAX-ACCESS read-write
			STATUS current
			DESCRIPTION
				" The request of a user command"
			::= { sleLldpPortControl 1 }

		
--  1.3.6.1.4.1.6296.9.8.19.2.2
		sleLldpPortControlStatus OBJECT-TYPE
			SYNTAX SleControlStatusType
			MAX-ACCESS read-only
			STATUS current
			DESCRIPTION
				" The status of user command"
			::= { sleLldpPortControl 2 }

		
--  1.3.6.1.4.1.6296.9.8.19.2.3
		sleLldpPortControlTimer OBJECT-TYPE
			SYNTAX Gauge32
			MAX-ACCESS read-write
			STATUS current
			DESCRIPTION
				" The maximum time for the manager for a long running user command"
			::= { sleLldpPortControl 3 }

		
--  1.3.6.1.4.1.6296.9.8.19.2.4
		sleLldpPortControlTimeStamp OBJECT-TYPE
			SYNTAX TimeTicks
			MAX-ACCESS read-only
			STATUS current
			DESCRIPTION
				" The time stamp of the last command(end of command)"
			::= { sleLldpPortControl 4 }

		
--  1.3.6.1.4.1.6296.9.8.19.2.5
		sleLldpPortControlReqResult OBJECT-TYPE
			SYNTAX SleControlRequestResultType
			MAX-ACCESS read-only
			STATUS current
			DESCRIPTION
				" The result of the last user command"
			::= { sleLldpPortControl 5 }

		
		sleLldpPortControlIndex OBJECT-TYPE
			SYNTAX INTEGER (1..255)
			MAX-ACCESS read-write
			STATUS current
			DESCRIPTION
				"LLDP port index"
			::= { sleLldpPortControl 6 }

		
		sleLldpPortControlActivity OBJECT-TYPE
			SYNTAX Boolean
			MAX-ACCESS read-write
			STATUS current
			DESCRIPTION
				"sleLldpPortControlActivity"
			::= { sleLldpPortControl 7 }

		
--  1.3.6.1.4.1.6296.9.8.19.2.6
		sleLldpPortControlAdminstatus OBJECT-TYPE
			SYNTAX INTEGER
				{
				txOnly(1),
				rxOnly(2),
				txAndRx(3),
				disabled(4)
				}
			MAX-ACCESS read-write
			STATUS current
			DESCRIPTION
				"The administratively desired status of the local LLDP agent."
			::= { sleLldpPortControl 8 }

		
--  1.3.6.1.4.1.6296.9.8.19.2.7
		sleLldpPortControlNotificationEnable OBJECT-TYPE
			SYNTAX Boolean
			MAX-ACCESS read-write
			STATUS current
			DESCRIPTION
				" It controls, on a per port basis, whether or not notifications from the agent are enabled."
			::= { sleLldpPortControl 9 }

		
--  1.3.6.1.4.1.6296.9.8.19.2.8
		sleLldpPortControlTLVsTxEnable OBJECT-TYPE
			SYNTAX BITS
				{
				portDesc(0),
				sysName(1),
				sysDesc(2),
				sysCap(3)
				}
			MAX-ACCESS read-write
			STATUS current
			DESCRIPTION
				" Bitmap that includes the basic set of LLDP TLVs whose transmission is allowed on the local LLDP agent by the network management."
			::= { sleLldpPortControl 10 }

		
		sleLldpPortControlMgmtTxEnable OBJECT-TYPE
			SYNTAX Boolean
			MAX-ACCESS read-write
			STATUS current
			DESCRIPTION
				"It indicates that the port is either enable or not to transfer management address."
			::= { sleLldpPortControl 11 }

		
		sleLldpPortControlMgmtAddress OBJECT-TYPE
			SYNTAX IpAddress
			MAX-ACCESS read-write
			STATUS current
			DESCRIPTION
				"Management address to transfer on the port."
			::= { sleLldpPortControl 12 }

		
--  1.3.6.1.4.1.6296.9.8.19.3
		sleLldpPortNotification OBJECT IDENTIFIER ::= { sleLldpPort 3 }

		
--  1.3.6.1.4.1.6296.9.8.19.3.1
		sleLldpPortProfileChanged NOTIFICATION-TYPE
			OBJECTS { sleLldpPortActivity, sleLldpPortAdminStatus, sleLldpPortNotificationEnable, sleLldpPortTLVsTxEnable, sleLldpPortMgmtTxEnable, 
				sleLldpPortMgmtAddress, sleLldpPortControlRequest, sleLldpPortControlTimeStamp, sleLldpPortControlReqResult }
			STATUS current
			DESCRIPTION 
				" "
			::= { sleLldpPortNotification 1 }

		
--  1.3.6.1.4.1.6296.9.8.20
		sleLldpRemote OBJECT IDENTIFIER ::= { sleBridge 20 }

		
--  1.3.6.1.4.1.6296.9.8.20.1
		sleLldpRemoteTable OBJECT-TYPE
			SYNTAX SEQUENCE OF SleLldpRemoteEntry
			MAX-ACCESS not-accessible
			STATUS current
			DESCRIPTION
				" LLDP remote table."
			::= { sleLldpRemote 1 }

		
--  1.3.6.1.4.1.6296.9.8.20.1.1
		sleLldpRemoteEntry OBJECT-TYPE
			SYNTAX SleLldpRemoteEntry
			MAX-ACCESS not-accessible
			STATUS current
			DESCRIPTION
				" key: sleLldpPortIndex, sleLldpRemIndex"
			INDEX { sleLldpPortIndex, sleLldpRemIndex }
			::= { sleLldpRemoteTable 1 }

		
		SleLldpRemoteEntry ::=
			SEQUENCE { 
				sleLldpRemIndex
					Integer32,
				sleLldpRemTimeMark
					TimeTicks,
				sleLldpRemChassisIdSubtype
					INTEGER,
				sleLldpRemChassisId
					OCTET STRING,
				sleLldpRemPortIdSubtype
					INTEGER,
				sleLldpRemPortId
					OCTET STRING,
				sleLldpRemPortDesc
					OCTET STRING,
				sleLldpRemSysName
					OCTET STRING,
				sleLldpRemSysDesc
					OCTET STRING,
				sleLldpRemSysCapSupported
					BITS,
				sleLldpRemSysCapEnabled
					BITS
			 }

--  1.3.6.1.4.1.6296.9.8.20.1.1.3
		sleLldpRemIndex OBJECT-TYPE
			SYNTAX Integer32 (1..2147483647)
			MAX-ACCESS read-write
			STATUS current
			DESCRIPTION
				"This object represents an arbitrary local integer value used by this agent to identify a particular connection instance, unique only for the indicated remote system."
			::= { sleLldpRemoteEntry 1 }

		
--  1.3.6.1.4.1.6296.9.8.20.1.1.1
		sleLldpRemTimeMark OBJECT-TYPE
			SYNTAX TimeTicks
			MAX-ACCESS read-only
			STATUS current
			DESCRIPTION
				"The sysUptime that this entry has been created or modified."
			::= { sleLldpRemoteEntry 2 }

		
--  1.3.6.1.4.1.6296.9.8.20.1.1.4
		sleLldpRemChassisIdSubtype OBJECT-TYPE
			SYNTAX INTEGER
				{
				chassisComponent(1),
				interfaceAlias(2),
				portComponent(3),
				macAddress(4),
				networkAddress(5),
				interfaceName(6),
				local(7)
				}
			MAX-ACCESS read-only
			STATUS current
			DESCRIPTION
				"The type of encoding used to identify the chassis associatedwith the remote system."
			::= { sleLldpRemoteEntry 3 }

		
--  1.3.6.1.4.1.6296.9.8.20.1.1.5
		sleLldpRemChassisId OBJECT-TYPE
			SYNTAX OCTET STRING (SIZE (1..255))
			MAX-ACCESS read-write
			STATUS current
			DESCRIPTION
				"The type of encoding used to identify the chassis associatedwith the remote system."
			::= { sleLldpRemoteEntry 4 }

		
--  1.3.6.1.4.1.6296.9.8.20.1.1.6
		sleLldpRemPortIdSubtype OBJECT-TYPE
			SYNTAX INTEGER
				{
				interfaceAlias(1),
				portComponent(2),
				macAddress(3),
				networkAddress(4),
				interfaceName(5),
				agentCircuitId(6),
				local(7)
				}
			MAX-ACCESS read-write
			STATUS current
			DESCRIPTION
				"The type of port identifier encoding used in the associated'lldpRemPortId' object."
			::= { sleLldpRemoteEntry 5 }

		
--  1.3.6.1.4.1.6296.9.8.20.1.1.7
		sleLldpRemPortId OBJECT-TYPE
			SYNTAX OCTET STRING (SIZE (1..255))
			MAX-ACCESS read-only
			STATUS current
			DESCRIPTION
				"The string value used to identify the port component associated with the remote system."
			::= { sleLldpRemoteEntry 6 }

		
--  1.3.6.1.4.1.6296.9.8.20.1.1.8
		sleLldpRemPortDesc OBJECT-TYPE
			SYNTAX OCTET STRING (SIZE (0..255))
			MAX-ACCESS read-only
			STATUS current
			DESCRIPTION
				"The string value used to identify the description of the given port associated with the remote system."
			::= { sleLldpRemoteEntry 7 }

		
--  1.3.6.1.4.1.6296.9.8.20.1.1.9
		sleLldpRemSysName OBJECT-TYPE
			SYNTAX OCTET STRING (SIZE (0..255))
			MAX-ACCESS read-only
			STATUS current
			DESCRIPTION
				"The string value used to identify the system name of the remote system."
			::= { sleLldpRemoteEntry 8 }

		
--  1.3.6.1.4.1.6296.9.8.20.1.1.10
		sleLldpRemSysDesc OBJECT-TYPE
			SYNTAX OCTET STRING (SIZE (0..255))
			MAX-ACCESS read-only
			STATUS current
			DESCRIPTION
				"The string value used to identify the system description of the remote system."
			::= { sleLldpRemoteEntry 9 }

		
--  1.3.6.1.4.1.6296.9.8.20.1.1.11
		sleLldpRemSysCapSupported OBJECT-TYPE
			SYNTAX BITS
				{
				other(0),
				repeater(1),
				bridge(2),
				wlanAccessPoint(3),
				router(4),
				telephone(5),
				docsisCableDevice(6),
				stationOnly(7)
				}
			MAX-ACCESS read-only
			STATUS current
			DESCRIPTION
				"The bitmap value used to identify which system capabilities are supported on the remote system."
			::= { sleLldpRemoteEntry 10 }

		
--  1.3.6.1.4.1.6296.9.8.20.1.1.12
		sleLldpRemSysCapEnabled OBJECT-TYPE
			SYNTAX BITS
				{
				other(0),
				repeater(1),
				bridge(2),
				wlanAccessPoint(3),
				router(4),
				telephone(5),
				docsisCableDevice(6),
				stationOnly(7)
				}
			MAX-ACCESS read-only
			STATUS current
			DESCRIPTION
				"The bitmap value used to identify which system capabilities are enabled on the remote system."
			::= { sleLldpRemoteEntry 11 }

		
--  1.3.6.1.4.1.6296.9.8.20.1
		sleLldpRemoteManAddrTable OBJECT-TYPE
			SYNTAX SEQUENCE OF SleLldpRemoteManAddrEntry
			MAX-ACCESS not-accessible
			STATUS current
			DESCRIPTION
				" LLDP remote table."
			::= { sleLldpRemote 2 }

		
--  1.3.6.1.4.1.6296.9.8.20.1.1
		sleLldpRemoteManAddrEntry OBJECT-TYPE
			SYNTAX SleLldpRemoteManAddrEntry
			MAX-ACCESS not-accessible
			STATUS current
			DESCRIPTION
				" key: sleLldpPortIndex, sleLldpRemIndex"
			INDEX { sleLldpPortIndex, sleLldpRemIndex, sleLldpRemManAddrSubType, sleLldpRemManAddr }
			::= { sleLldpRemoteManAddrTable 1 }

		
		SleLldpRemoteManAddrEntry ::=
			SEQUENCE { 
				sleLldpRemManAddrSubType
					AddressFamilyNumbers,
				sleLldpRemManAddr
					OCTET STRING,
				sleLldpRemManAddrIfSubType
					SleLldpManAddrIfSubType,
				sleLldpRemManAddrIfId
					INTEGER,
				sleLldpRemAddrOid
					OBJECT IDENTIFIER
			 }

--  1.3.6.1.4.1.6296.9.8.20.1.1.3
		sleLldpRemManAddrSubType OBJECT-TYPE
			SYNTAX AddressFamilyNumbers (0..65535)
			MAX-ACCESS read-only
			STATUS current
			DESCRIPTION
				"This object represents an arbitrary local integer value used by this agent to identify a particular connection instance, unique only for the indicated remote system."
			::= { sleLldpRemoteManAddrEntry 1 }

		
--  1.3.6.1.4.1.6296.9.8.20.1.1.1
		sleLldpRemManAddr OBJECT-TYPE
			SYNTAX OCTET STRING
			MAX-ACCESS read-only
			STATUS current
			DESCRIPTION
				"The sysUptime that this entry has been created or modified."
			::= { sleLldpRemoteManAddrEntry 2 }

		
--  1.3.6.1.4.1.6296.9.8.20.1.1.4
		sleLldpRemManAddrIfSubType OBJECT-TYPE
			SYNTAX SleLldpManAddrIfSubType
			MAX-ACCESS read-only
			STATUS current
			DESCRIPTION
				"The type of encoding used to identify the chassis associatedwith the remote system."
			::= { sleLldpRemoteManAddrEntry 3 }

		
--  1.3.6.1.4.1.6296.9.8.20.1.1.5
		sleLldpRemManAddrIfId OBJECT-TYPE
			SYNTAX INTEGER
			MAX-ACCESS read-only
			STATUS current
			DESCRIPTION
				"The type of encoding used to identify the chassis associatedwith the remote system."
			::= { sleLldpRemoteManAddrEntry 4 }

		
--  1.3.6.1.4.1.6296.9.8.20.1.1.6
		sleLldpRemAddrOid OBJECT-TYPE
			SYNTAX OBJECT IDENTIFIER
			MAX-ACCESS read-only
			STATUS current
			DESCRIPTION
				"The type of port identifier encoding used in the associated'lldpRemPortId' object."
			::= { sleLldpRemoteManAddrEntry 5 }

		
		sleLldpStatistics OBJECT IDENTIFIER ::= { sleBridge 21 }

		
		sleLldpStatisticsTable OBJECT-TYPE
			SYNTAX SEQUENCE OF SleLldpStatisticsEntry
			MAX-ACCESS not-accessible
			STATUS current
			DESCRIPTION
				"LLDP statistics table."
			::= { sleLldpStatistics 1 }

		
		sleLldpStatisticsEntry OBJECT-TYPE
			SYNTAX SleLldpStatisticsEntry
			MAX-ACCESS not-accessible
			STATUS current
			DESCRIPTION
				"key: sleLldpPortIndex"
			INDEX { sleLldpPortIndex }
			::= { sleLldpStatisticsTable 1 }

		
		SleLldpStatisticsEntry ::=
			SEQUENCE { 
				sleLldpStatsTxPortFramesTotal
					Integer32,
				sleLldpStatsRxPortFramesDiscardedTotal
					Counter32,
				sleLldpStatsRxPortFramesErrors
					Integer32,
				sleLldpStatsRxPortFramesTotal
					Counter32,
				sleLldpStatsRxPortTLVsDiscardedTotal
					Integer32,
				sleLldpStatsRxPortTLVsUnrecognizedTotal
					Integer32,
				sleLldpStatsRxPortAgeoutsTotal
					Counter32
			 }

		sleLldpStatsTxPortFramesTotal OBJECT-TYPE
			SYNTAX Integer32
			MAX-ACCESS read-only
			STATUS current
			DESCRIPTION
				"The number of LLDP frames transmitted by this LLDP agent on the indicated port."
			::= { sleLldpStatisticsEntry 1 }

		
		sleLldpStatsRxPortFramesDiscardedTotal OBJECT-TYPE
			SYNTAX Counter32
			MAX-ACCESS read-only
			STATUS current
			DESCRIPTION
				"The number of LLDP frames received by this LLDP agent on  the indicated port, and then discarded for any reason."
			::= { sleLldpStatisticsEntry 2 }

		
		sleLldpStatsRxPortFramesErrors OBJECT-TYPE
			SYNTAX Integer32
			MAX-ACCESS read-only
			STATUS current
			DESCRIPTION
				"The number of invalid LLDP frames received by this LLDPagent on the indicated port, while this LLDP agent is enabled."
			::= { sleLldpStatisticsEntry 3 }

		
		sleLldpStatsRxPortFramesTotal OBJECT-TYPE
			SYNTAX Counter32
			MAX-ACCESS read-only
			STATUS current
			DESCRIPTION
				"The number of valid LLDP frames received by this LLDP agent on the indicated port, while this LLDP agent is enabled."
			::= { sleLldpStatisticsEntry 4 }

		
		sleLldpStatsRxPortTLVsDiscardedTotal OBJECT-TYPE
			SYNTAX Integer32
			MAX-ACCESS read-only
			STATUS current
			DESCRIPTION
				"The number of LLDP TLVs discarded for any reason by this LLDP agent on the indicated port."
			::= { sleLldpStatisticsEntry 5 }

		
		sleLldpStatsRxPortTLVsUnrecognizedTotal OBJECT-TYPE
			SYNTAX Integer32
			MAX-ACCESS read-only
			STATUS current
			DESCRIPTION
				"The number of LLDP TLVs received on the given port that are not recognized by this LLDP agent on the indicated port."
			::= { sleLldpStatisticsEntry 6 }

		
		sleLldpStatsRxPortAgeoutsTotal OBJECT-TYPE
			SYNTAX Counter32
			MAX-ACCESS read-only
			STATUS current
			DESCRIPTION
				"The counter that represents the number of age-outs that occurred on a given port."
			::= { sleLldpStatisticsEntry 7 }

		
		sleLldpStatisticsControl OBJECT IDENTIFIER ::= { sleLldpStatistics 2 }

		
		sleLldpStatsControlRequest OBJECT-TYPE
			SYNTAX INTEGER { clearLldpStatistics(1) }
			MAX-ACCESS read-write
			STATUS current
			DESCRIPTION
				"The request of a user command"
			::= { sleLldpStatisticsControl 1 }

		
		sleLldpStatsControlStatus OBJECT-TYPE
			SYNTAX SleControlStatusType
			MAX-ACCESS read-only
			STATUS current
			DESCRIPTION
				"The status of user command"
			::= { sleLldpStatisticsControl 2 }

		
		sleLldpStatsControlTimer OBJECT-TYPE
			SYNTAX Gauge32
			MAX-ACCESS read-write
			STATUS current
			DESCRIPTION
				"The maximum time for the manager for a long running user command"
			::= { sleLldpStatisticsControl 3 }

		
		sleLldpStatsControlTimeStamp OBJECT-TYPE
			SYNTAX TimeTicks
			MAX-ACCESS read-only
			STATUS current
			DESCRIPTION
				"The time stamp of the last command(end of command)"
			::= { sleLldpStatisticsControl 4 }

		
		sleLldpStatsControlReqResult OBJECT-TYPE
			SYNTAX SleControlRequestResultType
			MAX-ACCESS read-only
			STATUS current
			DESCRIPTION
				"The result of the last user command"
			::= { sleLldpStatisticsControl 5 }

		
		sleLldpStatsControlPortIndex OBJECT-TYPE
			SYNTAX Unsigned32 (1..255)
			MAX-ACCESS read-write
			STATUS current
			DESCRIPTION
				"LLDP port index in sleLldpPortTable"
			::= { sleLldpStatisticsControl 6 }

		
		sleLldpStatisticsNotification OBJECT IDENTIFIER ::= { sleLldpStatistics 3 }

		
		sleLldpStatisticsCleared NOTIFICATION-TYPE
			OBJECTS { sleLldpStatsControlRequest, sleLldpStatsControlTimeStamp, sleLldpStatsControlPortIndex, sleLldpStatsControlReqResult }
			STATUS current
			DESCRIPTION 
				"Description."
			::= { sleLldpStatisticsNotification 1 }

		
		sleBridgePortSecurity OBJECT IDENTIFIER ::= { sleBridge 22 }

		
		sleBridgePSTable OBJECT-TYPE
			SYNTAX SEQUENCE OF SleBridgePSEntry
			MAX-ACCESS not-accessible
			STATUS current
			DESCRIPTION
				"bridge port security table."
			::= { sleBridgePortSecurity 1 }

		
		sleBridgePSEntry OBJECT-TYPE
			SYNTAX SleBridgePSEntry
			MAX-ACCESS not-accessible
			STATUS current
			DESCRIPTION
				"key: sleBridgePSIndex"
			INDEX { sleBridgePSIndex }
			::= { sleBridgePSTable 1 }

		
		SleBridgePSEntry ::=
			SEQUENCE { 
				sleBridgePSIndex
					InterfaceIndex,
				sleBridgePSStatus
					INTEGER,
				sleBridgePSMaxCount
					INTEGER,
				sleBridgePSCurrCount
					Unsigned32,
				sleBridgePSAgingType
					INTEGER,
				sleBridgePSAgingTimer
					INTEGER,
				sleBridgePSAgingStatic
					INTEGER,
				sleBridgePSViolation
					INTEGER
			 }

		sleBridgePSIndex OBJECT-TYPE
			SYNTAX InterfaceIndex
			MAX-ACCESS read-only
			STATUS current
			DESCRIPTION
				"The index of logical port"
			::= { sleBridgePSEntry 1 }

		
		sleBridgePSStatus OBJECT-TYPE
			SYNTAX INTEGER
				{
				enable(1),
				disable(2)
				}
			MAX-ACCESS read-only
			STATUS current
			DESCRIPTION
				"The status of port security"
			::= { sleBridgePSEntry 2 }

		
		sleBridgePSMaxCount OBJECT-TYPE
			SYNTAX INTEGER (-1 | 1..16384)
			MAX-ACCESS read-only
			STATUS current
			DESCRIPTION
				"The max secure addresses
				The value of -1 is not used
				"
			::= { sleBridgePSEntry 3 }

		
		sleBridgePSCurrCount OBJECT-TYPE
			SYNTAX Unsigned32
			MAX-ACCESS read-only
			STATUS current
			DESCRIPTION
				"The current count of port security"
			::= { sleBridgePSEntry 4 }

		
		sleBridgePSAgingType OBJECT-TYPE
			SYNTAX INTEGER
				{
				absolute(1),
				inactivity(2)
				}
			MAX-ACCESS read-only
			STATUS current
			DESCRIPTION
				"The aging type of port security"
			::= { sleBridgePSEntry 5 }

		
		sleBridgePSAgingTimer OBJECT-TYPE
			SYNTAX INTEGER (-1 | 0 | 1..2147483647)
			UNITS "second"
			MAX-ACCESS read-only
			STATUS current
			DESCRIPTION
				"The aging time of port security
				The value of -1 and 0 means that aging time fixed to static and it will be not aging out
				But The case of 5924N,
				The value of -1 means that aging time fixed to static and it will be not agint out
				The value of 0 means that aging out disable. "
			::= { sleBridgePSEntry 6 }

		
		sleBridgePSAgingStatic OBJECT-TYPE
			SYNTAX INTEGER
				{
				enable(1),
				disable(2)
				}
			MAX-ACCESS read-only
			STATUS current
			DESCRIPTION
				"The enable aging for configured secure addressess"
			::= { sleBridgePSEntry 7 }

		
		sleBridgePSViolation OBJECT-TYPE
			SYNTAX INTEGER
				{
				shutdown(1),
				protect(2),
				restrict(3)
				}
			MAX-ACCESS read-only
			STATUS current
			DESCRIPTION
				"The security violation mode of port security "
			::= { sleBridgePSEntry 8 }

		
		sleBridgePSControl OBJECT IDENTIFIER ::= { sleBridgePortSecurity 2 }

		
		sleBridgePSControlRequest OBJECT-TYPE
			SYNTAX INTEGER
				{
				setPSStatus(1),
				setPSMaxCount(2),
				setPSProfile(3)
				}
			MAX-ACCESS read-write
			STATUS current
			DESCRIPTION
				"The request of a user command"
			::= { sleBridgePSControl 1 }

		
		sleBridgePSControlStatus OBJECT-TYPE
			SYNTAX SleControlStatusType
			MAX-ACCESS read-only
			STATUS current
			DESCRIPTION
				"The status of user command"
			::= { sleBridgePSControl 2 }

		
		sleBridgePSControlTimer OBJECT-TYPE
			SYNTAX Gauge32
			MAX-ACCESS read-write
			STATUS current
			DESCRIPTION
				"The maximum time for the manager for a long running user command"
			::= { sleBridgePSControl 3 }

		
		sleBridgePSControlTimeStamp OBJECT-TYPE
			SYNTAX TimeTicks
			MAX-ACCESS read-only
			STATUS current
			DESCRIPTION
				"The time stamp of the last command(end of command)"
			::= { sleBridgePSControl 4 }

		
		sleBridgePSControlReqResult OBJECT-TYPE
			SYNTAX SleControlRequestResultType
			MAX-ACCESS read-only
			STATUS current
			DESCRIPTION
				"The result of the last user command"
			::= { sleBridgePSControl 5 }

		
		sleBridgePSControlIndex OBJECT-TYPE
			SYNTAX InterfaceIndex
			MAX-ACCESS read-write
			STATUS current
			DESCRIPTION
				"The index of logical port"
			::= { sleBridgePSControl 6 }

		
		sleBridgePSControlPSStatus OBJECT-TYPE
			SYNTAX INTEGER
				{
				enable(1),
				disable(2)
				}
			MAX-ACCESS read-write
			STATUS current
			DESCRIPTION
				"The status of port security"
			::= { sleBridgePSControl 7 }

		
		sleBridgePSControlMaxCount OBJECT-TYPE
			SYNTAX INTEGER (-1 | 1..16384)
			MAX-ACCESS read-write
			STATUS current
			DESCRIPTION
				"The max secure addresses
				The value of -1 is not used
				"
			::= { sleBridgePSControl 8 }

		
		sleBridgePSControlAgingType OBJECT-TYPE
			SYNTAX INTEGER
				{
				absolute(1),
				inactivity(2)
				}
			MAX-ACCESS read-write
			STATUS current
			DESCRIPTION
				"The aging type of port security"
			::= { sleBridgePSControl 9 }

		
		sleBridgePSControlAgingTimer OBJECT-TYPE
			SYNTAX INTEGER (-1 | 0 | 1..2147483647)
			UNITS "second"
			MAX-ACCESS read-write
			STATUS current
			DESCRIPTION
				"The aging time of port security
				The value -1 and 0 means that aging time fixed to static and it will be not aging out"
			::= { sleBridgePSControl 10 }

		
		sleBridgePSControlAgingStatic OBJECT-TYPE
			SYNTAX INTEGER
				{
				enable(1),
				disable(2)
				}
			MAX-ACCESS read-write
			STATUS current
			DESCRIPTION
				"The enable aging for configured secure addressess"
			::= { sleBridgePSControl 11 }

		
		sleBridgePScontrolViolation OBJECT-TYPE
			SYNTAX INTEGER
				{
				shutdown(1),
				protect(2),
				restrict(3)
				}
			MAX-ACCESS read-write
			STATUS current
			DESCRIPTION
				"The security violation mode of port security "
			::= { sleBridgePSControl 12 }

		
		sleBridgePSNotification OBJECT IDENTIFIER ::= { sleBridgePortSecurity 3 }

		
		sleBridgePSStatusChanged NOTIFICATION-TYPE
			OBJECTS { sleBridgePSControlRequest, sleBridgePSControlTimeStamp, sleBridgePSControlReqResult, sleBridgePSControlIndex, sleBridgePSControlPSStatus
				 }
			STATUS current
			DESCRIPTION 
				"Description."
			::= { sleBridgePSNotification 1 }

		
		sleBridgePSMaxCountChanged NOTIFICATION-TYPE
			OBJECTS { sleBridgePSControlRequest, sleBridgePSControlTimeStamp, sleBridgePSControlReqResult, sleBridgePSControlIndex, sleBridgePSControlMaxCount
				 }
			STATUS current
			DESCRIPTION 
				"Description."
			::= { sleBridgePSNotification 2 }

		
		sleBridgePSProfileChanged NOTIFICATION-TYPE
			OBJECTS { sleBridgePSControlRequest, sleBridgePSControlTimeStamp, sleBridgePSControlReqResult, sleBridgePSControlIndex, sleBridgePSControlAgingType, 
				sleBridgePSControlAgingTimer, sleBridgePSControlAgingStatic, sleBridgePScontrolViolation }
			STATUS current
			DESCRIPTION 
				"Description."
			::= { sleBridgePSNotification 3 }

		
		sleBridgePortSecurityFdb OBJECT IDENTIFIER ::= { sleBridge 23 }

		
		sleBridgePSFdbTable OBJECT-TYPE
			SYNTAX SEQUENCE OF SleBridgePSFdbEntry
			MAX-ACCESS not-accessible
			STATUS current
			DESCRIPTION
				"bridge port security FDB table."
			::= { sleBridgePortSecurityFdb 1 }

		
		sleBridgePSFdbEntry OBJECT-TYPE
			SYNTAX SleBridgePSFdbEntry
			MAX-ACCESS not-accessible
			STATUS current
			DESCRIPTION
				"key: sleBridgePSFdbPort, sleBridgePSFdbVid, sleBridgePSFdbMacAddress"
			INDEX { sleBridgePSFdbPort, sleBridgePSFdbVid, sleBridgePSFdbMacAddress }
			::= { sleBridgePSFdbTable 1 }

		
		SleBridgePSFdbEntry ::=
			SEQUENCE { 
				sleBridgePSFdbPort
					INTEGER,
				sleBridgePSFdbVid
					INTEGER,
				sleBridgePSFdbMacAddress
					OCTET STRING,
				sleBridgePSFdbMode
					INTEGER,
				sleBridgePSFdbElapsedTime
					Unsigned32
			 }

		sleBridgePSFdbPort OBJECT-TYPE
			SYNTAX INTEGER (1..512)
			MAX-ACCESS read-only
			STATUS current
			DESCRIPTION
				"FDB mode configuration.
				1: dynamic
				2: static
				"
			::= { sleBridgePSFdbEntry 1 }

		
		sleBridgePSFdbVid OBJECT-TYPE
			SYNTAX INTEGER (1..4094)
			MAX-ACCESS read-only
			STATUS current
			DESCRIPTION
				"FDB vlan index"
			::= { sleBridgePSFdbEntry 2 }

		
		sleBridgePSFdbMacAddress OBJECT-TYPE
			SYNTAX OCTET STRING (SIZE (0..6))
			MAX-ACCESS read-only
			STATUS current
			DESCRIPTION
				"FDB MAC address"
			::= { sleBridgePSFdbEntry 3 }

		
		sleBridgePSFdbMode OBJECT-TYPE
			SYNTAX INTEGER
				{
				dynamic(1),
				static(2)
				}
			MAX-ACCESS read-only
			STATUS current
			DESCRIPTION
				"FDB mode configuration.
				1: dynamic
				2: static
				"
			::= { sleBridgePSFdbEntry 4 }

		
		sleBridgePSFdbElapsedTime OBJECT-TYPE
			SYNTAX Unsigned32
			MAX-ACCESS read-only
			STATUS current
			DESCRIPTION
				"FDB elapsed time"
			::= { sleBridgePSFdbEntry 5 }

		
		sleBridgePSFdbControl OBJECT IDENTIFIER ::= { sleBridgePortSecurityFdb 2 }

		
		sleBridgePSFdbControlRequest OBJECT-TYPE
			SYNTAX INTEGER
				{
				createPSFedEntry(1),
				destroyPSFdbEntry(2),
				clearPSFdbEntry(3)
				}
			MAX-ACCESS read-write
			STATUS current
			DESCRIPTION
				"The request of a user command"
			::= { sleBridgePSFdbControl 1 }

		
		sleBridgePSFdbControlStatus OBJECT-TYPE
			SYNTAX SleControlStatusType
			MAX-ACCESS read-only
			STATUS current
			DESCRIPTION
				"The status of user command"
			::= { sleBridgePSFdbControl 2 }

		
		sleBridgePSFdbControlTimer OBJECT-TYPE
			SYNTAX Gauge32
			MAX-ACCESS read-write
			STATUS current
			DESCRIPTION
				"The maximum time for the manager for a long running user command"
			::= { sleBridgePSFdbControl 3 }

		
		sleBridgePSFdbControlTimeStamp OBJECT-TYPE
			SYNTAX TimeTicks
			MAX-ACCESS read-only
			STATUS current
			DESCRIPTION
				"The time stamp of the last command(end of command)"
			::= { sleBridgePSFdbControl 4 }

		
		sleBridgePSFdbControlReqResult OBJECT-TYPE
			SYNTAX SleControlRequestResultType
			MAX-ACCESS read-only
			STATUS current
			DESCRIPTION
				"The result of the last user command"
			::= { sleBridgePSFdbControl 5 }

		
		sleBridgePSFdbControlPort OBJECT-TYPE
			SYNTAX INTEGER (1..512)
			MAX-ACCESS read-write
			STATUS current
			DESCRIPTION
				"FDB port"
			::= { sleBridgePSFdbControl 6 }

		
		sleBridgePSFdbControlVid OBJECT-TYPE
			SYNTAX INTEGER (1..4094)
			MAX-ACCESS read-write
			STATUS current
			DESCRIPTION
				"FDB vlan index"
			::= { sleBridgePSFdbControl 7 }

		
		sleBridgePSFdbControlMacAddress OBJECT-TYPE
			SYNTAX OCTET STRING (SIZE (0..6))
			MAX-ACCESS read-write
			STATUS current
			DESCRIPTION
				"FDB MAC address"
			::= { sleBridgePSFdbControl 8 }

		
		sleBridgePSFdbNotification OBJECT IDENTIFIER ::= { sleBridgePortSecurityFdb 3 }

		
		sleBridgePSFdbEntryCreated NOTIFICATION-TYPE
			OBJECTS { sleBridgePSFdbControlRequest, sleBridgePSFdbControlTimeStamp, sleBridgePSFdbControlReqResult, sleBridgePSFdbControlPort, sleBridgePSFdbControlVid, 
				sleBridgePSFdbControlMacAddress }
			STATUS current
			DESCRIPTION 
				"Description."
			::= { sleBridgePSFdbNotification 1 }

		
		sleBridgePSFdbEntryDestroyed NOTIFICATION-TYPE
			OBJECTS { sleBridgePSFdbControlRequest, sleBridgePSFdbControlTimeStamp, sleBridgePSFdbControlReqResult, sleBridgePSFdbControlPort, sleBridgePSFdbControlVid, 
				sleBridgePSFdbControlMacAddress }
			STATUS current
			DESCRIPTION 
				"Description."
			::= { sleBridgePSFdbNotification 2 }

		
		sleBridgePSFdbEntryCleared NOTIFICATION-TYPE
			OBJECTS { sleBridgePSFdbControlRequest, sleBridgePSFdbControlTimeStamp, sleBridgePSFdbControlReqResult, sleBridgePSFdbControlPort, sleBridgePSFdbControlVid, 
				sleBridgePSFdbControlMacAddress }
			STATUS current
			DESCRIPTION 
				"Description."
			::= { sleBridgePSFdbNotification 3 }

		
		sleBridgeFloodGuard OBJECT IDENTIFIER ::= { sleBridge 24 }

		
		sleBridgeFGBase OBJECT IDENTIFIER ::= { sleBridgeFloodGuard 1 }

		
		sleBridgeFGBaseInfo OBJECT IDENTIFIER ::= { sleBridgeFGBase 1 }

		
		sleBridgeFGBaseCfgdEnabled OBJECT-TYPE
			SYNTAX INTEGER
				{
				enable(1),
				disable(2)
				}
			MAX-ACCESS read-only
			STATUS current
			DESCRIPTION
				"The CFG enabled
				1: enable
				2: disable
				"
			::= { sleBridgeFGBaseInfo 1 }

		
		sleBridgeFGBaseMfgdEnabled OBJECT-TYPE
			SYNTAX INTEGER
				{
				enable(1),
				disable(2)
				}
			MAX-ACCESS read-only
			STATUS current
			DESCRIPTION
				"The MFG enabled
				1: enable
				2: disable"
			::= { sleBridgeFGBaseInfo 2 }

		
		sleBridgeFGBaseSfgdEnabled OBJECT-TYPE
			SYNTAX INTEGER
				{
				enable(1),
				disable(2)
				}
			MAX-ACCESS read-only
			STATUS current
			DESCRIPTION
				"The SFG enabled
				1: enable
				2: disable"
			::= { sleBridgeFGBaseInfo 3 }

		
		sleBridgeFGBaseControl OBJECT IDENTIFIER ::= { sleBridgeFGBase 2 }

		
		sleBridgeFGBaseControlRequest OBJECT-TYPE
			SYNTAX INTEGER
				{
				setCfgdEnable(1),
				setSfgdEnable(2)
				}
			MAX-ACCESS read-write
			STATUS current
			DESCRIPTION
				"The request of a user command"
			::= { sleBridgeFGBaseControl 1 }

		
		sleBridgeFGBaseControlStatus OBJECT-TYPE
			SYNTAX SleControlStatusType
			MAX-ACCESS read-only
			STATUS current
			DESCRIPTION
				"The status of user command"
			::= { sleBridgeFGBaseControl 2 }

		
		sleBridgeFGBaseControlTimer OBJECT-TYPE
			SYNTAX Gauge32
			MAX-ACCESS read-write
			STATUS current
			DESCRIPTION
				"The maximum time for the manager for a long running user command"
			::= { sleBridgeFGBaseControl 3 }

		
		sleBridgeFGBaseControlTimeStamp OBJECT-TYPE
			SYNTAX TimeTicks
			MAX-ACCESS read-only
			STATUS current
			DESCRIPTION
				"The time stamp of the last command(end of command)"
			::= { sleBridgeFGBaseControl 4 }

		
		sleBridgeFGBaseControlReqResult OBJECT-TYPE
			SYNTAX SleControlRequestResultType
			MAX-ACCESS read-only
			STATUS current
			DESCRIPTION
				"The result of the last user command"
			::= { sleBridgeFGBaseControl 5 }

		
		sleBridgeFGBaseControlCfgdEnable OBJECT-TYPE
			SYNTAX INTEGER
				{
				enable(1),
				disable(2)
				}
			MAX-ACCESS read-write
			STATUS current
			DESCRIPTION
				"The CFG enabled
				1: enable
				2: disable"
			::= { sleBridgeFGBaseControl 6 }

		
		sleBridgeFGBaseControlSfgdEnable OBJECT-TYPE
			SYNTAX INTEGER
				{
				enable(1),
				disable(2)
				}
			MAX-ACCESS read-write
			STATUS current
			DESCRIPTION
				"The SFG enabled
				1: enable
				2: disable	"
			::= { sleBridgeFGBaseControl 7 }

		
		sleBridgeFGBaseNotification OBJECT IDENTIFIER ::= { sleBridgeFGBase 3 }

		
		sleBridgeFGBaseCfgdStatusChanged NOTIFICATION-TYPE
			OBJECTS { sleBridgeFGBaseControlRequest, sleBridgeFGBaseControlTimeStamp, sleBridgeFGBaseControlReqResult, sleBridgeFGBaseControlCfgdEnable }
			STATUS current
			DESCRIPTION 
				"Description."
			::= { sleBridgeFGBaseNotification 1 }

		
		sleBridgeFGBaseSfgdStatusChanged NOTIFICATION-TYPE
			OBJECTS { sleBridgeFGBaseControlRequest, sleBridgeFGBaseControlTimeStamp, sleBridgeFGBaseControlReqResult, sleBridgeFGBaseControlSfgdEnable }
			STATUS current
			DESCRIPTION 
				"Description."
			::= { sleBridgeFGBaseNotification 2 }

		
		sleBridgeFGPort OBJECT IDENTIFIER ::= { sleBridgeFloodGuard 2 }

		
		sleBridgeFGPortTable OBJECT-TYPE
			SYNTAX SEQUENCE OF SleBridgeFGPortEntry
			MAX-ACCESS not-accessible
			STATUS current
			DESCRIPTION
				"Description."
			::= { sleBridgeFGPort 1 }

		
		sleBridgeFGPortEntry OBJECT-TYPE
			SYNTAX SleBridgeFGPortEntry
			MAX-ACCESS not-accessible
			STATUS current
			DESCRIPTION
				"Description."
			INDEX { sleBridgePortIndex, sleBridgeFGPortType }
			::= { sleBridgeFGPortTable 1 }

		
		SleBridgeFGPortEntry ::=
			SEQUENCE { 
				sleBridgeFGPortType
					INTEGER,
				sleBridgeFGPortFrameType
					INTEGER,
				sleBridgeFGPortFrame
					INTEGER,
				sleBridgeFGPortBlocked
					INTEGER,
				sleBridgeFGPortTimer
					INTEGER
			 }

		sleBridgeFGPortType OBJECT-TYPE
			SYNTAX INTEGER
				{
				systemFloodGuard(1),
				cpuFloodGuard(2),
				macFloodGuard(3)
				}
			MAX-ACCESS read-only
			STATUS current
			DESCRIPTION
				"Flood guard port type
				1 : systemFloodGuard
				2 : cpuFloodGuard
				3 : macFloodGuard"
			::= { sleBridgeFGPortEntry 1 }

		
		sleBridgeFGPortFrameType OBJECT-TYPE
			SYNTAX INTEGER
				{
				none(0),
				multicast(1),
				broadcast(2),
				both(3)
				}
			MAX-ACCESS read-only
			STATUS current
			DESCRIPTION
				"Flood guard frame type
				0 : none
				1 : multicast
				2 : broadcast
				3 : both"
			::= { sleBridgeFGPortEntry 2 }

		
		sleBridgeFGPortFrame OBJECT-TYPE
			SYNTAX INTEGER (-1 | 1..2147483647)
			MAX-ACCESS read-only
			STATUS current
			DESCRIPTION
				"Flood guard frame"
			::= { sleBridgeFGPortEntry 3 }

		
		sleBridgeFGPortBlocked OBJECT-TYPE
			SYNTAX INTEGER
				{
				block(1),
				unblock(2)
				}
			MAX-ACCESS read-only
			STATUS current
			DESCRIPTION
				"Flood guard block status
				1 : block
				2 : unblock"
			::= { sleBridgeFGPortEntry 4 }

		
		sleBridgeFGPortTimer OBJECT-TYPE
			SYNTAX INTEGER (-1 | 10..3600)
			MAX-ACCESS read-only
			STATUS current
			DESCRIPTION
				"Flood guard timer"
			::= { sleBridgeFGPortEntry 5 }

		
		sleBridgeFGPortControl OBJECT IDENTIFIER ::= { sleBridgeFGPort 2 }

		
		sleBridgeFGPortControlRequest OBJECT-TYPE
			SYNTAX INTEGER
				{
				setFgPortProfile(1),
				setFgPortUnblock(2)
				}
			MAX-ACCESS read-write
			STATUS current
			DESCRIPTION
				"The request of a user command"
			::= { sleBridgeFGPortControl 1 }

		
		sleBridgeFGPortControlStatus OBJECT-TYPE
			SYNTAX SleControlStatusType
			MAX-ACCESS read-only
			STATUS current
			DESCRIPTION
				"The status of user command"
			::= { sleBridgeFGPortControl 2 }

		
		sleBridgeFGPortControlTimer OBJECT-TYPE
			SYNTAX Gauge32
			MAX-ACCESS read-only
			STATUS current
			DESCRIPTION
				"The maximum time for the manager for a long running user command"
			::= { sleBridgeFGPortControl 3 }

		
		sleBridgeFGPortControlTimeStamp OBJECT-TYPE
			SYNTAX TimeTicks
			MAX-ACCESS read-only
			STATUS current
			DESCRIPTION
				"The time stamp of the last command(end of command)"
			::= { sleBridgeFGPortControl 4 }

		
		sleBridgeFGPortControlReqResult OBJECT-TYPE
			SYNTAX SleControlRequestResultType
			MAX-ACCESS read-only
			STATUS current
			DESCRIPTION
				"The result of the last user command"
			::= { sleBridgeFGPortControl 5 }

		
		sleBridgeFGPortControlIndex OBJECT-TYPE
			SYNTAX Integer32
			MAX-ACCESS read-write
			STATUS current
			DESCRIPTION
				"Port index"
			::= { sleBridgeFGPortControl 6 }

		
		sleBridgeFGPortControlType OBJECT-TYPE
			SYNTAX INTEGER
				{
				systemfloodguard(1),
				cpufloodguard(2),
				macfloodguard(3)
				}
			MAX-ACCESS read-write
			STATUS current
			DESCRIPTION
				"Flood guard port type
				1 : systemFloodGuard
				2 : cpuFloodGuard
				3 : macFloodGuard"
			::= { sleBridgeFGPortControl 7 }

		
		sleBridgeFGPortControlFrameType OBJECT-TYPE
			SYNTAX INTEGER
				{
				none(0),
				multicast(1),
				broadcast(2),
				both(3)
				}
			MAX-ACCESS read-write
			STATUS current
			DESCRIPTION
				"Flood guard frame type
				0 : none
				1 : multicast
				2 : broadcast
				3 : both
				"
			::= { sleBridgeFGPortControl 8 }

		
		sleBridgeFGPortControlFrame OBJECT-TYPE
			SYNTAX INTEGER (-1 | 1..2147483647)
			MAX-ACCESS read-write
			STATUS current
			DESCRIPTION
				"Flood guard frame"
			::= { sleBridgeFGPortControl 9 }

		
		sleBridgeFGPortControlSetTimer OBJECT-TYPE
			SYNTAX INTEGER (-1 | 10..3600)
			MAX-ACCESS read-write
			STATUS current
			DESCRIPTION
				"Flood guard timer"
			::= { sleBridgeFGPortControl 10 }

		
		sleBridgeFGPortControlBlock OBJECT-TYPE
			SYNTAX INTEGER
				{
				block(1),
				unblock(2)
				}
			MAX-ACCESS read-write
			STATUS current
			DESCRIPTION
				"Flood guard block status
				1 : block
				2 : unblock"
			::= { sleBridgeFGPortControl 11 }

		
		sleBridgeFGPortNotification OBJECT IDENTIFIER ::= { sleBridgeFGPort 3 }

		
		sleBridgeFGPortProfileChanged NOTIFICATION-TYPE
			OBJECTS { sleBridgeFGPortControlReqResult, sleBridgeFGPortControlTimeStamp, sleBridgeFGPortControlRequest, sleBridgeFGPortControlIndex, sleBridgeFGPortControlType, 
				sleBridgeFGPortControlFrameType, sleBridgeFGPortControlFrame, sleBridgeFGPortControlSetTimer, sleBridgeFGPortControlBlock }
			STATUS current
			DESCRIPTION 
				"Description."
			::= { sleBridgeFGPortNotification 1 }

		
		sleBridgeFGPortUnblockChanged NOTIFICATION-TYPE
			OBJECTS { sleBridgeFGPortControlRequest, sleBridgeFGPortControlTimeStamp, sleBridgeFGPortControlReqResult, sleBridgeFGPortControlIndex, sleBridgeFGPortControlType
				 }
			STATUS current
			DESCRIPTION 
				"Description."
			::= { sleBridgeFGPortNotification 2 }

		
		sleBridgeVlanTranslation OBJECT IDENTIFIER ::= { sleBridge 25 }

		
		sleBridgeVTTable OBJECT-TYPE
			SYNTAX SEQUENCE OF SleBridgeVTEntry
			MAX-ACCESS not-accessible
			STATUS current
			DESCRIPTION
				"bridge vlan translation table."
			::= { sleBridgeVlanTranslation 1 }

		
		sleBridgeVTEntry OBJECT-TYPE
			SYNTAX SleBridgeVTEntry
			MAX-ACCESS not-accessible
			STATUS current
			DESCRIPTION
				"key: sleBridgeVTServiceId, sleBridgeVTSubscriberId"
			INDEX { sleBridgeVTServiceId, sleBridgeVTSubscriberId }
			::= { sleBridgeVTTable 1 }

		
		SleBridgeVTEntry ::=
			SEQUENCE { 
				sleBridgeVTServiceId
					INTEGER,
				sleBridgeVTSubscriberId
					INTEGER
			 }

		sleBridgeVTServiceId OBJECT-TYPE
			SYNTAX INTEGER (1..4094)
			MAX-ACCESS read-only
			STATUS current
			DESCRIPTION
				"Service Vlan Id"
			::= { sleBridgeVTEntry 1 }

		
		sleBridgeVTSubscriberId OBJECT-TYPE
			SYNTAX INTEGER (1..4094)
			MAX-ACCESS read-only
			STATUS current
			DESCRIPTION
				"Subscriber Vlan Id"
			::= { sleBridgeVTEntry 2 }

		
		sleBridgeVTRuleTable OBJECT-TYPE
			SYNTAX SEQUENCE OF SleBridgeVTRuleEntry
			MAX-ACCESS not-accessible
			STATUS current
			DESCRIPTION
				"bridge vlan translation rule table."
			::= { sleBridgeVlanTranslation 2 }

		
		sleBridgeVTRuleEntry OBJECT-TYPE
			SYNTAX SleBridgeVTRuleEntry
			MAX-ACCESS not-accessible
			STATUS current
			DESCRIPTION
				"key: sleBridgeVTRuleMac, sleBridgeVTRuleVid"
			INDEX { sleBridgeVTRuleMac, sleBridgeVTRuleVid }
			::= { sleBridgeVTRuleTable 1 }

		
		SleBridgeVTRuleEntry ::=
			SEQUENCE { 
				sleBridgeVTRuleMac
					MacAddress,
				sleBridgeVTRuleVid
					INTEGER,
				sleBridgeVTRuleRDirVid
					INTEGER,
				sleBridgeVTRuleRDirPort
					Integer32,
				sleBridgeVTRuleStatus
					INTEGER
			 }

		sleBridgeVTRuleMac OBJECT-TYPE
			SYNTAX MacAddress
			MAX-ACCESS read-only
			STATUS current
			DESCRIPTION
				"sleBridgeVTRuleMac, sleBridgeVTRuleVid"
			::= { sleBridgeVTRuleEntry 1 }

		
		sleBridgeVTRuleVid OBJECT-TYPE
			SYNTAX INTEGER (1..4094)
			MAX-ACCESS read-only
			STATUS current
			DESCRIPTION
				"Original packet Vid"
			::= { sleBridgeVTRuleEntry 2 }

		
		sleBridgeVTRuleRDirVid OBJECT-TYPE
			SYNTAX INTEGER (1..4094)
			MAX-ACCESS read-only
			STATUS current
			DESCRIPTION
				"Output port"
			::= { sleBridgeVTRuleEntry 3 }

		
		sleBridgeVTRuleRDirPort OBJECT-TYPE
			SYNTAX Integer32
			MAX-ACCESS read-only
			STATUS current
			DESCRIPTION
				"Output Vid"
			::= { sleBridgeVTRuleEntry 4 }

		
		sleBridgeVTRuleStatus OBJECT-TYPE
			SYNTAX INTEGER
				{
				static(1),
				dynamic(2)
				}
			MAX-ACCESS read-only
			STATUS current
			DESCRIPTION
				"Vlan Translation rule status"
			::= { sleBridgeVTRuleEntry 5 }

		
		sleBridgeVTControl OBJECT IDENTIFIER ::= { sleBridgeVlanTranslation 3 }

		
		sleBridgeVTControlRequest OBJECT-TYPE
			SYNTAX INTEGER
				{
				setVT(1),
				clearVT(2)
				}
			MAX-ACCESS read-write
			STATUS current
			DESCRIPTION
				"The request of a user command."
			::= { sleBridgeVTControl 1 }

		
		sleBridgeVTControlStatus OBJECT-TYPE
			SYNTAX SleControlStatusType
			MAX-ACCESS read-only
			STATUS current
			DESCRIPTION
				"The status of a user command."
			::= { sleBridgeVTControl 2 }

		
		sleBridgeVTControlTimer OBJECT-TYPE
			SYNTAX Gauge32
			MAX-ACCESS read-write
			STATUS current
			DESCRIPTION
				"The maximum wait time for the manager for a long running user command."
			::= { sleBridgeVTControl 3 }

		
		sleBridgeVTControlTimeStamp OBJECT-TYPE
			SYNTAX TimeTicks
			MAX-ACCESS read-only
			STATUS current
			DESCRIPTION
				"The time stamp of the last command (end of command)."
			::= { sleBridgeVTControl 4 }

		
		sleBridgeVTControlReqResult OBJECT-TYPE
			SYNTAX SleControlRequestResultType
			MAX-ACCESS read-only
			STATUS current
			DESCRIPTION
				"The result of the last user command."
			::= { sleBridgeVTControl 5 }

		
		sleBridgeVTControlServerId OBJECT-TYPE
			SYNTAX INTEGER (1..4094)
			MAX-ACCESS read-write
			STATUS current
			DESCRIPTION
				"Network Interface Index."
			::= { sleBridgeVTControl 6 }

		
		sleBridgeVTControlClientId OBJECT-TYPE
			SYNTAX INTEGER (1..4094)
			MAX-ACCESS read-write
			STATUS current
			DESCRIPTION
				"Network Interface Index."
			::= { sleBridgeVTControl 7 }

		
		sleBridgeVTNotification OBJECT IDENTIFIER ::= { sleBridgeVlanTranslation 4 }

		
		sleBridgeVTSet NOTIFICATION-TYPE
			OBJECTS { sleBridgeVTControlRequest, sleBridgeVTControlTimeStamp, sleBridgeVTControlServerId, sleBridgeVTControlClientId, sleBridgeVTControlReqResult
				 }
			STATUS current
			DESCRIPTION 
				"Description."
			::= { sleBridgeVTNotification 1 }

		
		sleBridgeVTClear NOTIFICATION-TYPE
			OBJECTS { sleBridgeVTControlRequest, sleBridgeVTControlTimeStamp, sleBridgeVTControlServerId, sleBridgeVTControlClientId, sleBridgeVTControlReqResult
				 }
			STATUS current
			DESCRIPTION 
				"Description."
			::= { sleBridgeVTNotification 2 }

		
		sleBridgeInBoundVTTable OBJECT-TYPE
			SYNTAX SEQUENCE OF SleBridgeInBoundVTEntry
			MAX-ACCESS not-accessible
			STATUS current
			DESCRIPTION
				"bridge inbound vlan translation table."
			::= { sleBridgeVlanTranslation 5 }

		
		sleBridgeInBoundVTEntry OBJECT-TYPE
			SYNTAX SleBridgeInBoundVTEntry
			MAX-ACCESS not-accessible
			STATUS current
			DESCRIPTION
				"key: sleBridgeInBoundVTPortIndex, sleBridgeInBoundVTVlanIndex"
			INDEX { sleBridgeInBoundVTPortIndex, sleBridgeInBoundVTVlanIndex }
			::= { sleBridgeInBoundVTTable 1 }

		
		SleBridgeInBoundVTEntry ::=
			SEQUENCE { 
				sleBridgeInBoundVTPortIndex
					INTEGER,
				sleBridgeInBoundVTVlanIndex
					Integer32,
				sleBridgeInBoundVTNewVid
					Integer32,
				sleBridgeInBoundVTOperStatus
					INTEGER
			 }

		sleBridgeInBoundVTPortIndex OBJECT-TYPE
			SYNTAX INTEGER (0..512)
			MAX-ACCESS read-only
			STATUS current
			DESCRIPTION
				"Port Index."
			::= { sleBridgeInBoundVTEntry 1 }

		
		sleBridgeInBoundVTVlanIndex OBJECT-TYPE
			SYNTAX Integer32 (0..65535)
			MAX-ACCESS read-only
			STATUS current
			DESCRIPTION
				"Vlan Index."
			::= { sleBridgeInBoundVTEntry 2 }

		
		sleBridgeInBoundVTNewVid OBJECT-TYPE
			SYNTAX Integer32
			MAX-ACCESS read-only
			STATUS current
			DESCRIPTION
				"New VID."
			::= { sleBridgeInBoundVTEntry 3 }

		
		sleBridgeInBoundVTOperStatus OBJECT-TYPE
			SYNTAX INTEGER
				{
				on(1),
				off(2)
				}
			MAX-ACCESS read-only
			STATUS current
			DESCRIPTION
				"The operational status of InBound Vlan Translation."
			::= { sleBridgeInBoundVTEntry 4 }

		
		sleBridgeInBoundVTControl OBJECT IDENTIFIER ::= { sleBridgeVlanTranslation 6 }

		
		sleBridgeInBoundVTControlRequest OBJECT-TYPE
			SYNTAX INTEGER
				{
				setInBoundVT(1),
				clearInBoundVT(2)
				}
			MAX-ACCESS read-write
			STATUS current
			DESCRIPTION
				"The request of a user command."
			::= { sleBridgeInBoundVTControl 1 }

		
		sleBridgeInBoundVTControlStatus OBJECT-TYPE
			SYNTAX SleControlStatusType
			MAX-ACCESS read-only
			STATUS current
			DESCRIPTION
				"The status of a user command."
			::= { sleBridgeInBoundVTControl 2 }

		
		sleBridgeInBoundVTControlTimer OBJECT-TYPE
			SYNTAX Gauge32
			MAX-ACCESS read-write
			STATUS current
			DESCRIPTION
				"The maximum wait time for the manager for a long running user command."
			::= { sleBridgeInBoundVTControl 3 }

		
		sleBridgeInBoundVTControlTimeStamp OBJECT-TYPE
			SYNTAX TimeTicks
			MAX-ACCESS read-only
			STATUS current
			DESCRIPTION
				"The time stamp of the last command (end of command)."
			::= { sleBridgeInBoundVTControl 4 }

		
		sleBridgeInBoundVTControlReqResult OBJECT-TYPE
			SYNTAX SleControlRequestResultType
			MAX-ACCESS read-only
			STATUS current
			DESCRIPTION
				"The result of the last user command."
			::= { sleBridgeInBoundVTControl 5 }

		
		sleBridgeInBoundVTControlPortIndex OBJECT-TYPE
			SYNTAX Integer32
			MAX-ACCESS read-write
			STATUS current
			DESCRIPTION
				"Port Index."
			::= { sleBridgeInBoundVTControl 6 }

		
		sleBridgeInBoundVTControlVlanIndex OBJECT-TYPE
			SYNTAX Integer32
			MAX-ACCESS read-write
			STATUS current
			DESCRIPTION
				"Vlan Index."
			::= { sleBridgeInBoundVTControl 7 }

		
		sleBridgeInBoundVTControlNewVid OBJECT-TYPE
			SYNTAX Integer32
			MAX-ACCESS read-write
			STATUS current
			DESCRIPTION
				"New VID."
			::= { sleBridgeInBoundVTControl 8 }

		
		sleBridgeInBoundVTNotification OBJECT IDENTIFIER ::= { sleBridgeVlanTranslation 7 }

		
		sleBridgeInBoundVTSet NOTIFICATION-TYPE
			OBJECTS { sleBridgeInBoundVTControlRequest, sleBridgeInBoundVTControlTimeStamp, sleBridgeInBoundVTControlReqResult, sleBridgeInBoundVTControlPortIndex, sleBridgeInBoundVTControlVlanIndex, 
				sleBridgeInBoundVTControlNewVid }
			STATUS current
			DESCRIPTION 
				"Description."
			::= { sleBridgeInBoundVTNotification 1 }

		
		sleBridgeInBoundVTClear NOTIFICATION-TYPE
			OBJECTS { sleBridgeInBoundVTControlRequest, sleBridgeInBoundVTControlTimeStamp, sleBridgeInBoundVTControlReqResult, sleBridgeInBoundVTControlPortIndex, sleBridgeInBoundVTControlVlanIndex
				 }
			STATUS current
			DESCRIPTION 
				"Description."
			::= { sleBridgeInBoundVTNotification 2 }

		
		sleBridgeOutBoundVTTable OBJECT-TYPE
			SYNTAX SEQUENCE OF SleBridgeOutBoundVTEntry
			MAX-ACCESS not-accessible
			STATUS current
			DESCRIPTION
				"bridge outbound vlan translation table."
			::= { sleBridgeVlanTranslation 8 }

		
		sleBridgeOutBoundVTEntry OBJECT-TYPE
			SYNTAX SleBridgeOutBoundVTEntry
			MAX-ACCESS not-accessible
			STATUS current
			DESCRIPTION
				"key: sleBridgeOutBoundVTPortIndex, sleBridgeOutBoundVTVlanIndex"
			INDEX { sleBridgeOutBoundVTPortIndex, sleBridgeOutBoundVTVlanIndex }
			::= { sleBridgeOutBoundVTTable 1 }

		
		SleBridgeOutBoundVTEntry ::=
			SEQUENCE { 
				sleBridgeOutBoundVTPortIndex
					INTEGER,
				sleBridgeOutBoundVTVlanIndex
					Integer32,
				sleBridgeOutBoundVTNewVid
					Integer32,
				sleBridgeOutBoundVTOperStatus
					INTEGER
			 }

		sleBridgeOutBoundVTPortIndex OBJECT-TYPE
			SYNTAX INTEGER (0..512)
			MAX-ACCESS read-only
			STATUS current
			DESCRIPTION
				"Port Index."
			::= { sleBridgeOutBoundVTEntry 1 }

		
		sleBridgeOutBoundVTVlanIndex OBJECT-TYPE
			SYNTAX Integer32 (0..65535)
			MAX-ACCESS read-only
			STATUS current
			DESCRIPTION
				"Vlan Index."
			::= { sleBridgeOutBoundVTEntry 2 }

		
		sleBridgeOutBoundVTNewVid OBJECT-TYPE
			SYNTAX Integer32
			MAX-ACCESS read-only
			STATUS current
			DESCRIPTION
				"New VID."
			::= { sleBridgeOutBoundVTEntry 3 }

		
		sleBridgeOutBoundVTOperStatus OBJECT-TYPE
			SYNTAX INTEGER
				{
				on(1),
				off(2)
				}
			MAX-ACCESS read-only
			STATUS current
			DESCRIPTION
				"The operational status of InBound Vlan Translation."
			::= { sleBridgeOutBoundVTEntry 4 }

		
		sleBridgeOutBoundVTControl OBJECT IDENTIFIER ::= { sleBridgeVlanTranslation 9 }

		
		sleBridgeOutBoundVTControlRequest OBJECT-TYPE
			SYNTAX INTEGER
				{
				setOutBoundVT(1),
				clearOutBoundVT(2)
				}
			MAX-ACCESS read-write
			STATUS current
			DESCRIPTION
				"The request of a user command."
			::= { sleBridgeOutBoundVTControl 1 }

		
		sleBridgeOutBoundVTControlStatus OBJECT-TYPE
			SYNTAX SleControlStatusType
			MAX-ACCESS read-only
			STATUS current
			DESCRIPTION
				"The status of a user command."
			::= { sleBridgeOutBoundVTControl 2 }

		
		sleBridgeOutBoundVTControlTimer OBJECT-TYPE
			SYNTAX Gauge32
			MAX-ACCESS read-write
			STATUS current
			DESCRIPTION
				"The maximum wait time for the manager for a long running user command."
			::= { sleBridgeOutBoundVTControl 3 }

		
		sleBridgeOutBoundVTControlTimeStamp OBJECT-TYPE
			SYNTAX TimeTicks
			MAX-ACCESS read-only
			STATUS current
			DESCRIPTION
				"The time stamp of the last command (end of command)."
			::= { sleBridgeOutBoundVTControl 4 }

		
		sleBridgeOutBoundVTControlReqResult OBJECT-TYPE
			SYNTAX SleControlRequestResultType
			MAX-ACCESS read-only
			STATUS current
			DESCRIPTION
				"The result of the last user command."
			::= { sleBridgeOutBoundVTControl 5 }

		
		sleBridgeOutBoundVTControlPortIndex OBJECT-TYPE
			SYNTAX Integer32
			MAX-ACCESS read-write
			STATUS current
			DESCRIPTION
				"Port Index."
			::= { sleBridgeOutBoundVTControl 6 }

		
		sleBridgeOutBoundVTControlVlanIndex OBJECT-TYPE
			SYNTAX Integer32
			MAX-ACCESS read-write
			STATUS current
			DESCRIPTION
				"Vlan Index."
			::= { sleBridgeOutBoundVTControl 7 }

		
		sleBridgeOutBoundVTControlNewVid OBJECT-TYPE
			SYNTAX Integer32
			MAX-ACCESS read-write
			STATUS current
			DESCRIPTION
				"New VID."
			::= { sleBridgeOutBoundVTControl 8 }

		
		sleBridgeOutBoundVTNotification OBJECT IDENTIFIER ::= { sleBridgeVlanTranslation 10 }

		
		sleBridgeOutBoundVTSet NOTIFICATION-TYPE
			OBJECTS { sleBridgeOutBoundVTControlRequest, sleBridgeOutBoundVTControlTimeStamp, sleBridgeOutBoundVTControlReqResult, sleBridgeOutBoundVTControlPortIndex, sleBridgeOutBoundVTControlVlanIndex, 
				sleBridgeOutBoundVTControlNewVid }
			STATUS current
			DESCRIPTION 
				"Description."
			::= { sleBridgeOutBoundVTNotification 1 }

		
		sleBridgeOutBoundVTClear NOTIFICATION-TYPE
			OBJECTS { sleBridgeOutBoundVTControlRequest, sleBridgeOutBoundVTControlTimeStamp, sleBridgeOutBoundVTControlReqResult, sleBridgeOutBoundVTControlPortIndex, sleBridgeOutBoundVTControlVlanIndex
				 }
			STATUS current
			DESCRIPTION 
				"Description."
			::= { sleBridgeOutBoundVTNotification 2 }

		
		sleBridgeGarp OBJECT IDENTIFIER ::= { sleBridge 26 }

		
		sleBridgeGarpBase OBJECT IDENTIFIER ::= { sleBridgeGarp 1 }

		
		sleBridgeGarpBaseInfo OBJECT IDENTIFIER ::= { sleBridgeGarpBase 1 }

		
		sleBridgeGvrpStatus OBJECT-TYPE
			SYNTAX INTEGER
				{
				enable(1),
				disable(2)
				}
			MAX-ACCESS read-only
			STATUS current
			DESCRIPTION
				"Global GVRP status"
			::= { sleBridgeGarpBaseInfo 1 }

		
		sleBridgeGmrpStatus OBJECT-TYPE
			SYNTAX INTEGER
				{
				enable(1),
				disable(2)
				}
			MAX-ACCESS read-only
			STATUS current
			DESCRIPTION
				"Global GMRP status"
			::= { sleBridgeGarpBaseInfo 2 }

		
		sleBridgeGarpTimerJoin OBJECT-TYPE
			SYNTAX Integer32
			MAX-ACCESS read-only
			STATUS current
			DESCRIPTION
				"Global Join Timer"
			::= { sleBridgeGarpBaseInfo 3 }

		
		sleBridgeGarpTimerLeave OBJECT-TYPE
			SYNTAX Integer32
			MAX-ACCESS read-only
			STATUS current
			DESCRIPTION
				"Global Leave Timer"
			::= { sleBridgeGarpBaseInfo 4 }

		
		sleBridgeGarpTimerLeaveAll OBJECT-TYPE
			SYNTAX Integer32
			MAX-ACCESS read-only
			STATUS current
			DESCRIPTION
				"Global LeaveAll Timer"
			::= { sleBridgeGarpBaseInfo 5 }

		
		sleBridgeGarpBaseControl OBJECT IDENTIFIER ::= { sleBridgeGarpBase 2 }

		
		sleBridgeGarpBaseControlRequest OBJECT-TYPE
			SYNTAX INTEGER
				{
				setGarpStatus(1),
				setGarpTimer(2)
				}
			MAX-ACCESS read-write
			STATUS current
			DESCRIPTION
				"The request of a user command"
			::= { sleBridgeGarpBaseControl 1 }

		
		sleBridgeGarpBaseControlStatus OBJECT-TYPE
			SYNTAX SleControlStatusType
			MAX-ACCESS read-only
			STATUS current
			DESCRIPTION
				"The status of user command"
			::= { sleBridgeGarpBaseControl 2 }

		
		sleBridgeGarpBaseControlTimer OBJECT-TYPE
			SYNTAX Gauge32
			MAX-ACCESS read-write
			STATUS current
			DESCRIPTION
				"The maximum time for the manager for a long running user command"
			::= { sleBridgeGarpBaseControl 3 }

		
		sleBridgeGarpBaseControlTimeStamp OBJECT-TYPE
			SYNTAX TimeTicks
			MAX-ACCESS read-only
			STATUS current
			DESCRIPTION
				"The time stamp of the last command(end of command)"
			::= { sleBridgeGarpBaseControl 4 }

		
		sleBridgeGarpBaseControlReqResult OBJECT-TYPE
			SYNTAX SleControlRequestResultType
			MAX-ACCESS read-only
			STATUS current
			DESCRIPTION
				"The result of the last user command"
			::= { sleBridgeGarpBaseControl 5 }

		
		sleBridgeGarpBaseControlGvrpStatus OBJECT-TYPE
			SYNTAX INTEGER
				{
				enable(1),
				disable(2)
				}
			MAX-ACCESS read-write
			STATUS current
			DESCRIPTION
				"Global GVRP status"
			::= { sleBridgeGarpBaseControl 6 }

		
		sleBridgeGarpBaseControlGmrpStatus OBJECT-TYPE
			SYNTAX INTEGER
				{
				enable(1),
				disable(2)
				}
			MAX-ACCESS read-write
			STATUS current
			DESCRIPTION
				"Global GMRP status"
			::= { sleBridgeGarpBaseControl 7 }

		
		sleBridgeGarpBaseControlTimerJoin OBJECT-TYPE
			SYNTAX Integer32
			MAX-ACCESS read-write
			STATUS current
			DESCRIPTION
				"Global Join Timer"
			::= { sleBridgeGarpBaseControl 8 }

		
		sleBridgeGarpBaseControlTimerLeave OBJECT-TYPE
			SYNTAX Integer32
			MAX-ACCESS read-write
			STATUS current
			DESCRIPTION
				"Global Leave Timer"
			::= { sleBridgeGarpBaseControl 9 }

		
		sleBridgeGarpBaseControlTimerLeaveAll OBJECT-TYPE
			SYNTAX Integer32
			MAX-ACCESS read-write
			STATUS current
			DESCRIPTION
				"Global LeaveAll Timer"
			::= { sleBridgeGarpBaseControl 10 }

		
		sleBridgeGarpBaseNotification OBJECT IDENTIFIER ::= { sleBridgeGarpBase 3 }

		
		sleBridgeGarpStatusChanged NOTIFICATION-TYPE
			OBJECTS { sleBridgeGarpBaseControlRequest, sleBridgeGarpBaseControlTimeStamp, sleBridgeGarpBaseControlReqResult, sleBridgeGarpBaseControlGvrpStatus, sleBridgeGarpBaseControlGmrpStatus
				 }
			STATUS current
			DESCRIPTION 
				"Description."
			::= { sleBridgeGarpBaseNotification 1 }

		
		sleBridgeGarpTimerChanged NOTIFICATION-TYPE
			OBJECTS { sleBridgeGarpBaseControlRequest, sleBridgeGarpBaseControlTimeStamp, sleBridgeGarpBaseControlReqResult, sleBridgeGarpBaseControlTimerJoin, sleBridgeGarpBaseControlTimerLeave, 
				sleBridgeGarpBaseControlTimerLeaveAll }
			STATUS current
			DESCRIPTION 
				"Description."
			::= { sleBridgeGarpBaseNotification 2 }

		
		sleBridgeGarpApplication OBJECT IDENTIFIER ::= { sleBridgeGarp 2 }

		
		sleBridgeGarpAppPortTable OBJECT-TYPE
			SYNTAX SEQUENCE OF SleBridgeGarpAppPortEntry
			MAX-ACCESS not-accessible
			STATUS current
			DESCRIPTION
				"bridge GARP application port table."
			::= { sleBridgeGarpApplication 1 }

		
		sleBridgeGarpAppPortEntry OBJECT-TYPE
			SYNTAX SleBridgeGarpAppPortEntry
			MAX-ACCESS not-accessible
			STATUS current
			DESCRIPTION
				"key: sleBridgeGarpAppPortIndex, sleBridgeGarpAppPortType"
			INDEX { sleBridgeGarpAppPortIndex, sleBridgeGarpAppPortType }
			::= { sleBridgeGarpAppPortTable 1 }

		
		SleBridgeGarpAppPortEntry ::=
			SEQUENCE { 
				sleBridgeGarpAppPortIndex
					INTEGER,
				sleBridgeGarpAppPortType
					INTEGER,
				sleBridgeGarpAppPortStatus
					INTEGER,
				sleBridgeGarpAppPortFailedRegistrations
					Integer32,
				sleBridgeGarpAppPortLastPduOrigin
					OCTET STRING,
				sleBridgeGarpAppPortRegistration
					INTEGER,
				sleBridgeGarpAppPortApplicant
					INTEGER,
				sleBridgeGarpAppPortFwdAll
					INTEGER,
				sleBridgeGarpAppPortTimerJoin
					Integer32,
				sleBridgeGarpAppPortTimerLeave
					Integer32,
				sleBridgeGarpAppPortTimerLeaveAll
					Integer32
			 }

		sleBridgeGarpAppPortIndex OBJECT-TYPE
			SYNTAX INTEGER (1..65535)
			MAX-ACCESS read-only
			STATUS current
			DESCRIPTION
				"Port index.  Same as ifindex."
			::= { sleBridgeGarpAppPortEntry 1 }

		
		sleBridgeGarpAppPortType OBJECT-TYPE
			SYNTAX INTEGER
				{
				gvrp(1),
				gmrp(2)
				}
			MAX-ACCESS read-only
			STATUS current
			DESCRIPTION
				"GARP Application Type.
				Supports GVRP, GMRP 
				"
			::= { sleBridgeGarpAppPortEntry 2 }

		
		sleBridgeGarpAppPortStatus OBJECT-TYPE
			SYNTAX INTEGER
				{
				enable(1),
				disable(2)
				}
			MAX-ACCESS read-only
			STATUS current
			DESCRIPTION
				"GARP Application port status
				1 : enable
				2 : disable"
			::= { sleBridgeGarpAppPortEntry 3 }

		
		sleBridgeGarpAppPortFailedRegistrations OBJECT-TYPE
			SYNTAX Integer32
			MAX-ACCESS read-only
			STATUS current
			DESCRIPTION
				"The current value of the Failed Registrations counter maintained for a GARP Attribute type."
			::= { sleBridgeGarpAppPortEntry 4 }

		
		sleBridgeGarpAppPortLastPduOrigin OBJECT-TYPE
			SYNTAX OCTET STRING (SIZE (1..6))
			MAX-ACCESS read-only
			STATUS current
			DESCRIPTION
				"MAC Address of the last pdu that caused a state change for a given GARP Attribute."
			::= { sleBridgeGarpAppPortEntry 5 }

		
		sleBridgeGarpAppPortRegistration OBJECT-TYPE
			SYNTAX INTEGER
				{
				nomal(1),
				fixed(2),
				forbidden(3)
				}
			MAX-ACCESS read-only
			STATUS current
			DESCRIPTION
				"GARP registration mode."
			::= { sleBridgeGarpAppPortEntry 6 }

		
		sleBridgeGarpAppPortApplicant OBJECT-TYPE
			SYNTAX INTEGER
				{
				participant(1),
				nonParticipant(2)
				}
			MAX-ACCESS read-only
			STATUS current
			DESCRIPTION
				"Applicant type
				1: Transmissible PDU
				2: Untransmissible PDU
				"
			::= { sleBridgeGarpAppPortEntry 7 }

		
		sleBridgeGarpAppPortFwdAll OBJECT-TYPE
			SYNTAX INTEGER
				{
				enable(1),
				disable(2)
				}
			MAX-ACCESS read-only
			STATUS current
			DESCRIPTION
				"GMRP forward all registered-groups."
			::= { sleBridgeGarpAppPortEntry 8 }

		
		sleBridgeGarpAppPortTimerJoin OBJECT-TYPE
			SYNTAX Integer32
			MAX-ACCESS read-only
			STATUS current
			DESCRIPTION
				"GARP Application port timer join"
			::= { sleBridgeGarpAppPortEntry 9 }

		
		sleBridgeGarpAppPortTimerLeave OBJECT-TYPE
			SYNTAX Integer32
			MAX-ACCESS read-only
			STATUS current
			DESCRIPTION
				"GARP Application port timer leave"
			::= { sleBridgeGarpAppPortEntry 10 }

		
		sleBridgeGarpAppPortTimerLeaveAll OBJECT-TYPE
			SYNTAX Integer32
			MAX-ACCESS read-only
			STATUS current
			DESCRIPTION
				"GARP Application port timer leave all"
			::= { sleBridgeGarpAppPortEntry 11 }

		
		sleBridgeGarpAppPortControl OBJECT IDENTIFIER ::= { sleBridgeGarpApplication 2 }

		
		sleBridgeGarpAppPortControlRequest OBJECT-TYPE
			SYNTAX INTEGER
				{
				setGarpAppStatus(1),
				setGarpAppProfile(2)
				}
			MAX-ACCESS read-write
			STATUS current
			DESCRIPTION
				"The request of a user command"
			::= { sleBridgeGarpAppPortControl 1 }

		
		sleBridgeGarpAppPortControlStatus OBJECT-TYPE
			SYNTAX SleControlStatusType
			MAX-ACCESS read-only
			STATUS current
			DESCRIPTION
				"The status of user command"
			::= { sleBridgeGarpAppPortControl 2 }

		
		sleBridgeGarpAppPortControlTimer OBJECT-TYPE
			SYNTAX Gauge32
			MAX-ACCESS read-write
			STATUS current
			DESCRIPTION
				"The maximum time for the manager for a long running user command"
			::= { sleBridgeGarpAppPortControl 3 }

		
		sleBridgeGarpAppPortControlTimeStamp OBJECT-TYPE
			SYNTAX TimeTicks
			MAX-ACCESS read-only
			STATUS current
			DESCRIPTION
				"The time stamp of the last command(end of command)"
			::= { sleBridgeGarpAppPortControl 4 }

		
		sleBridgeGarpAppPortControlReqResult OBJECT-TYPE
			SYNTAX SleControlRequestResultType
			MAX-ACCESS read-only
			STATUS current
			DESCRIPTION
				"The result of the last user command"
			::= { sleBridgeGarpAppPortControl 5 }

		
		sleBridgeGarpAppPortControlIndex OBJECT-TYPE
			SYNTAX INTEGER (1..65535)
			MAX-ACCESS read-write
			STATUS current
			DESCRIPTION
				"Port index.  Same as ifindex."
			::= { sleBridgeGarpAppPortControl 6 }

		
		sleBridgeGarpAppPortControlType OBJECT-TYPE
			SYNTAX INTEGER
				{
				gvrp(1),
				gmrp(2)
				}
			MAX-ACCESS read-write
			STATUS current
			DESCRIPTION
				"GARP Application Type.
				Supports GVRP, GMRP"
			::= { sleBridgeGarpAppPortControl 7 }

		
		sleBridgeGarpAppPortControlPortStatus OBJECT-TYPE
			SYNTAX INTEGER
				{
				enable(1),
				disable(2)
				}
			MAX-ACCESS read-write
			STATUS current
			DESCRIPTION
				"GARP Application port status
				1 : enable
				2 : disable
				"
			::= { sleBridgeGarpAppPortControl 8 }

		
		sleBridgeGarpAppPortControlRegistration OBJECT-TYPE
			SYNTAX INTEGER
				{
				nomal(1),
				fixed(2),
				forbidden(3)
				}
			MAX-ACCESS read-write
			STATUS current
			DESCRIPTION
				"The current value of the Failed Registrations counter maintained for a GARP Attribute type."
			::= { sleBridgeGarpAppPortControl 9 }

		
		sleBridgeGarpAppPortControlApplicant OBJECT-TYPE
			SYNTAX INTEGER
				{
				participant(1),
				nonPorticipant(2)
				}
			MAX-ACCESS read-write
			STATUS current
			DESCRIPTION
				"Applicant type
				1: Transmissible PDU
				2: Untransmissible PDU"
			::= { sleBridgeGarpAppPortControl 10 }

		
		sleBridgeGarpAppPortControlFwdAll OBJECT-TYPE
			SYNTAX INTEGER
				{
				enable(1),
				disable(2)
				}
			MAX-ACCESS read-write
			STATUS current
			DESCRIPTION
				"Applicant type
				1: Transmissible PDU
				2: Untransmissible PDU
				"
			::= { sleBridgeGarpAppPortControl 11 }

		
		sleBridgeGarpAppPortControlTimerJoin OBJECT-TYPE
			SYNTAX Integer32
			MAX-ACCESS read-write
			STATUS current
			DESCRIPTION
				"GARP Application port timer join"
			::= { sleBridgeGarpAppPortControl 12 }

		
		sleBridgeGarpAppPortControlTimerLeave OBJECT-TYPE
			SYNTAX Integer32
			MAX-ACCESS read-write
			STATUS current
			DESCRIPTION
				"GARP Application port timer leave"
			::= { sleBridgeGarpAppPortControl 13 }

		
		sleBridgeGarpAppPortControlTimerLeaveAll OBJECT-TYPE
			SYNTAX Integer32
			MAX-ACCESS read-write
			STATUS current
			DESCRIPTION
				"GARP Application port timer leave all"
			::= { sleBridgeGarpAppPortControl 14 }

		
		sleBridgeGarpAppPortNotification OBJECT IDENTIFIER ::= { sleBridgeGarpApplication 3 }

		
		sleBridgeGarpAppPortStatusChanged NOTIFICATION-TYPE
			OBJECTS { sleBridgeGarpAppPortControlRequest, sleBridgeGarpAppPortControlTimeStamp, sleBridgeGarpAppPortControlReqResult, sleBridgeGarpAppPortControlIndex, sleBridgeGarpAppPortControlType, 
				sleBridgeGarpAppPortControlPortStatus }
			STATUS current
			DESCRIPTION 
				"Description."
			::= { sleBridgeGarpAppPortNotification 1 }

		
		sleBridgeGarpAppPortProfileChanged NOTIFICATION-TYPE
			OBJECTS { sleBridgeGarpAppPortControlRequest, sleBridgeGarpAppPortControlTimeStamp, sleBridgeGarpAppPortControlReqResult, sleBridgeGarpAppPortControlIndex, sleBridgeGarpAppPortControlType, 
				sleBridgeGarpAppPortControlRegistration, sleBridgeGarpAppPortControlApplicant, sleBridgeGarpAppPortControlFwdAll, sleBridgeGarpAppPortControlTimerJoin, sleBridgeGarpAppPortControlTimerLeave, 
				sleBridgeGarpAppPortControlTimerLeaveAll }
			STATUS current
			DESCRIPTION 
				"Description."
			::= { sleBridgeGarpAppPortNotification 2 }

		
		sleBridgeGarpStats OBJECT IDENTIFIER ::= { sleBridgeGarp 3 }

		
		sleBridgeGarpStatsTable OBJECT-TYPE
			SYNTAX SEQUENCE OF SleBridgeGarpStatsEntry
			MAX-ACCESS not-accessible
			STATUS current
			DESCRIPTION
				"bridge GARP stats table"
			::= { sleBridgeGarpStats 1 }

		
		sleBridgeGarpStatsEntry OBJECT-TYPE
			SYNTAX SleBridgeGarpStatsEntry
			MAX-ACCESS not-accessible
			STATUS current
			DESCRIPTION
				"key: sleBridgeGarpAppPortIndex, sleBridgeGarpAppPortType"
			INDEX { sleBridgeGarpAppPortIndex, sleBridgeGarpAppPortType }
			::= { sleBridgeGarpStatsTable 1 }

		
		SleBridgeGarpStatsEntry ::=
			SEQUENCE { 
				sleBridgeGarpStatsJoinEmptyReceived
					Integer32,
				sleBridgeGarpStatsJoinInReceived
					Integer32,
				sleBridgeGarpStatsEmptyReceived
					Integer32,
				sleBridgeGarpStatsLeaveInReceived
					Integer32,
				sleBridgeGarpStatsLeaveEmptyReceived
					Integer32,
				sleBridgeGarpStatsLeaveAllReceived
					Integer32,
				sleBridgeGarpStatsJoinEmptyTransmitted
					Integer32,
				sleBridgeGarpStatsJoinInTransmitted
					Integer32,
				sleBridgeGarpStatsEmptyTransmitted
					Integer32,
				sleBridgeGarpStatsLeaveInTransmitted
					Integer32,
				sleBridgeGarpStatsLeaveEmptyTransmitted
					Integer32,
				sleBridgeGarpStatsLeaveAllTransmitted
					Integer32
			 }

		sleBridgeGarpStatsJoinEmptyReceived OBJECT-TYPE
			SYNTAX Integer32
			MAX-ACCESS read-only
			STATUS current
			DESCRIPTION
				"GARP stats received:
				join empty"
			::= { sleBridgeGarpStatsEntry 1 }

		
		sleBridgeGarpStatsJoinInReceived OBJECT-TYPE
			SYNTAX Integer32
			MAX-ACCESS read-only
			STATUS current
			DESCRIPTION
				"GARP stats received:
				Joun in
				"
			::= { sleBridgeGarpStatsEntry 2 }

		
		sleBridgeGarpStatsEmptyReceived OBJECT-TYPE
			SYNTAX Integer32
			MAX-ACCESS read-only
			STATUS current
			DESCRIPTION
				"GARP stats received:
				empty "
			::= { sleBridgeGarpStatsEntry 3 }

		
		sleBridgeGarpStatsLeaveInReceived OBJECT-TYPE
			SYNTAX Integer32
			MAX-ACCESS read-only
			STATUS current
			DESCRIPTION
				"GARP stats received:
				Leave in"
			::= { sleBridgeGarpStatsEntry 4 }

		
		sleBridgeGarpStatsLeaveEmptyReceived OBJECT-TYPE
			SYNTAX Integer32
			MAX-ACCESS read-only
			STATUS current
			DESCRIPTION
				"GARP stats received:
				Leave empty"
			::= { sleBridgeGarpStatsEntry 5 }

		
		sleBridgeGarpStatsLeaveAllReceived OBJECT-TYPE
			SYNTAX Integer32
			MAX-ACCESS read-only
			STATUS current
			DESCRIPTION
				"GARP stats received:
				Leave all"
			::= { sleBridgeGarpStatsEntry 6 }

		
		sleBridgeGarpStatsJoinEmptyTransmitted OBJECT-TYPE
			SYNTAX Integer32
			MAX-ACCESS read-only
			STATUS current
			DESCRIPTION
				"GARP stats transmitted:
				Join empty"
			::= { sleBridgeGarpStatsEntry 7 }

		
		sleBridgeGarpStatsJoinInTransmitted OBJECT-TYPE
			SYNTAX Integer32
			MAX-ACCESS read-only
			STATUS current
			DESCRIPTION
				"GARP stats transmitted:
				Join in"
			::= { sleBridgeGarpStatsEntry 8 }

		
		sleBridgeGarpStatsEmptyTransmitted OBJECT-TYPE
			SYNTAX Integer32
			MAX-ACCESS read-only
			STATUS current
			DESCRIPTION
				"GARP stats transmitted:
				Empty
				"
			::= { sleBridgeGarpStatsEntry 9 }

		
		sleBridgeGarpStatsLeaveInTransmitted OBJECT-TYPE
			SYNTAX Integer32
			MAX-ACCESS read-only
			STATUS current
			DESCRIPTION
				"GARP stats transmitted:
				Leave in"
			::= { sleBridgeGarpStatsEntry 10 }

		
		sleBridgeGarpStatsLeaveEmptyTransmitted OBJECT-TYPE
			SYNTAX Integer32
			MAX-ACCESS read-only
			STATUS current
			DESCRIPTION
				"GARP stats transmitted;
				Leave empty"
			::= { sleBridgeGarpStatsEntry 11 }

		
		sleBridgeGarpStatsLeaveAllTransmitted OBJECT-TYPE
			SYNTAX Integer32
			MAX-ACCESS read-only
			STATUS current
			DESCRIPTION
				"GARP stats transmitted:
				Leave all"
			::= { sleBridgeGarpStatsEntry 12 }

		
		sleBridgeGarpStatsControl OBJECT IDENTIFIER ::= { sleBridgeGarpStats 2 }

		
		sleBridgeGarpStatsControlRequest OBJECT-TYPE
			SYNTAX INTEGER { clearGarpPktStatistics(1) }
			MAX-ACCESS read-write
			STATUS current
			DESCRIPTION
				"The request of a user command"
			::= { sleBridgeGarpStatsControl 1 }

		
		sleBridgeGarpStatstControlStatus OBJECT-TYPE
			SYNTAX SleControlStatusType
			MAX-ACCESS read-only
			STATUS current
			DESCRIPTION
				"The status of user command"
			::= { sleBridgeGarpStatsControl 2 }

		
		sleBridgeGarpStatsControlTimer OBJECT-TYPE
			SYNTAX Gauge32
			MAX-ACCESS read-write
			STATUS current
			DESCRIPTION
				"The maximum time for the manager for a long running user command"
			::= { sleBridgeGarpStatsControl 3 }

		
		sleBridgeGarpStatsControlTimeStamp OBJECT-TYPE
			SYNTAX TimeTicks
			MAX-ACCESS read-only
			STATUS current
			DESCRIPTION
				"The time stamp of the last command(end of command)"
			::= { sleBridgeGarpStatsControl 4 }

		
		sleBridgeGarpStatsControlReqResult OBJECT-TYPE
			SYNTAX SleControlRequestResultType
			MAX-ACCESS read-only
			STATUS current
			DESCRIPTION
				"The result of the last user command"
			::= { sleBridgeGarpStatsControl 5 }

		
		sleBridgeGarpStatsControlIndex OBJECT-TYPE
			SYNTAX INTEGER (1..65535)
			MAX-ACCESS read-write
			STATUS current
			DESCRIPTION
				"Port index"
			::= { sleBridgeGarpStatsControl 6 }

		
		sleBridgeGarpStatsControlType OBJECT-TYPE
			SYNTAX INTEGER
				{
				gvrp(1),
				gmrp(2)
				}
			MAX-ACCESS read-write
			STATUS current
			DESCRIPTION
				"Port type
				"
			::= { sleBridgeGarpStatsControl 7 }

		
		sleBridgeGarpStatsNotification OBJECT IDENTIFIER ::= { sleBridgeGarpStats 3 }

		
		sleBridgeGarpStatisticsCleared NOTIFICATION-TYPE
			OBJECTS { sleBridgeGarpStatsControlRequest, sleBridgeGarpStatsControlTimeStamp, sleBridgeGarpStatsControlReqResult, sleBridgeGarpStatsControlIndex, sleBridgeGarpStatsControlType
				 }
			STATUS current
			DESCRIPTION 
				"Description."
			::= { sleBridgeGarpStatsNotification 1 }

		
		sleBridgeGmrpStatic OBJECT IDENTIFIER ::= { sleBridgeGarp 4 }

		
		sleBridgeGmrpStaticTable OBJECT-TYPE
			SYNTAX SEQUENCE OF SleBridgeGmrpStaticEntry
			MAX-ACCESS not-accessible
			STATUS current
			DESCRIPTION
				"bridge GMRP static table"
			::= { sleBridgeGmrpStatic 1 }

		
		sleBridgeGmrpStaticEntry OBJECT-TYPE
			SYNTAX SleBridgeGmrpStaticEntry
			MAX-ACCESS not-accessible
			STATUS current
			DESCRIPTION
				"key: sleBridgeGmrpStaticVid, sleBridgeGmrpStaticPort, sleBridgeGmrpStaticGmac"
			INDEX { sleBridgeGmrpStaticVid, sleBridgeGmrpStaticPort, sleBridgeGmrpStaticGmac }
			::= { sleBridgeGmrpStaticTable 1 }

		
		SleBridgeGmrpStaticEntry ::=
			SEQUENCE { 
				sleBridgeGmrpStaticVid
					INTEGER,
				sleBridgeGmrpStaticPort
					INTEGER,
				sleBridgeGmrpStaticGmac
					OCTET STRING
			 }

		sleBridgeGmrpStaticVid OBJECT-TYPE
			SYNTAX INTEGER (1..65535)
			MAX-ACCESS read-only
			STATUS current
			DESCRIPTION
				"VLAN Id"
			::= { sleBridgeGmrpStaticEntry 1 }

		
		sleBridgeGmrpStaticPort OBJECT-TYPE
			SYNTAX INTEGER (1..65535)
			MAX-ACCESS read-only
			STATUS current
			DESCRIPTION
				"Port index"
			::= { sleBridgeGmrpStaticEntry 2 }

		
		sleBridgeGmrpStaticGmac OBJECT-TYPE
			SYNTAX OCTET STRING (SIZE (0..6))
			MAX-ACCESS read-only
			STATUS current
			DESCRIPTION
				"Group Mac Address"
			::= { sleBridgeGmrpStaticEntry 3 }

		
		sleBridgeGmrpStaticControl OBJECT IDENTIFIER ::= { sleBridgeGmrpStatic 2 }

		
		sleBridgeGmrpStaticControlRequest OBJECT-TYPE
			SYNTAX INTEGER
				{
				addGmrpStatic(1),
				delGmrpStatic(2)
				}
			MAX-ACCESS read-write
			STATUS current
			DESCRIPTION
				"The request of a user command"
			::= { sleBridgeGmrpStaticControl 1 }

		
		sleBridgeGmrpStaticControlStatus OBJECT-TYPE
			SYNTAX SleControlStatusType
			MAX-ACCESS read-only
			STATUS current
			DESCRIPTION
				"The status of user command"
			::= { sleBridgeGmrpStaticControl 2 }

		
		sleBridgeGmrpStaticControlTimer OBJECT-TYPE
			SYNTAX Gauge32
			MAX-ACCESS read-write
			STATUS current
			DESCRIPTION
				"The maximum time for the manager for a long running user command"
			::= { sleBridgeGmrpStaticControl 3 }

		
		sleBridgeGmrpStaticControlTimeStamp OBJECT-TYPE
			SYNTAX TimeTicks
			MAX-ACCESS read-only
			STATUS current
			DESCRIPTION
				"The time stamp of the last command(end of command)"
			::= { sleBridgeGmrpStaticControl 4 }

		
		sleBridgeGmrpStaticControlReqResult OBJECT-TYPE
			SYNTAX SleControlRequestResultType
			MAX-ACCESS read-only
			STATUS current
			DESCRIPTION
				"The result of the last user command"
			::= { sleBridgeGmrpStaticControl 5 }

		
		sleBridgeGmrpStaticControlVid OBJECT-TYPE
			SYNTAX INTEGER (1..65535)
			MAX-ACCESS read-write
			STATUS current
			DESCRIPTION
				"VLAN Id"
			::= { sleBridgeGmrpStaticControl 6 }

		
		sleBridgeGmrpStaticControlPort OBJECT-TYPE
			SYNTAX INTEGER (1..65535)
			MAX-ACCESS read-write
			STATUS current
			DESCRIPTION
				"Port index"
			::= { sleBridgeGmrpStaticControl 7 }

		
		sleBridgeGmrpStaticControlGmac OBJECT-TYPE
			SYNTAX OCTET STRING (SIZE (0..6))
			MAX-ACCESS read-write
			STATUS current
			DESCRIPTION
				"Group Mac Address"
			::= { sleBridgeGmrpStaticControl 8 }

		
		sleBridgeGmrpStaticNotification OBJECT IDENTIFIER ::= { sleBridgeGmrpStatic 3 }

		
		sleBridgeGmrpStaticAdded NOTIFICATION-TYPE
			OBJECTS { sleBridgeGmrpStaticControlRequest, sleBridgeGmrpStaticControlTimeStamp, sleBridgeGmrpStaticControlReqResult, sleBridgeGmrpStaticControlVid, sleBridgeGmrpStaticControlPort, 
				sleBridgeGmrpStaticControlGmac }
			STATUS current
			DESCRIPTION 
				"Description."
			::= { sleBridgeGmrpStaticNotification 1 }

		
		sleBridgeGmrpStaticDeleted NOTIFICATION-TYPE
			OBJECTS { sleBridgeGmrpStaticControlRequest, sleBridgeGmrpStaticControlTimeStamp, sleBridgeGmrpStaticControlReqResult, sleBridgeGmrpStaticControlVid, sleBridgeGmrpStaticControlPort, 
				sleBridgeGmrpStaticControlGmac }
			STATUS current
			DESCRIPTION 
				"Description."
			::= { sleBridgeGmrpStaticNotification 2 }

		
		sleVlanTag OBJECT IDENTIFIER ::= { sleBridge 27 }

		
		sleVlanInboundTag OBJECT IDENTIFIER ::= { sleVlanTag 1 }

		
		sleVlanInboundTagTable OBJECT-TYPE
			SYNTAX SEQUENCE OF SleVlanInboundTagEntry
			MAX-ACCESS not-accessible
			STATUS current
			DESCRIPTION
				"vlan inbound tag table."
			::= { sleVlanInboundTag 1 }

		
		sleVlanInboundTagEntry OBJECT-TYPE
			SYNTAX SleVlanInboundTagEntry
			MAX-ACCESS not-accessible
			STATUS current
			DESCRIPTION
				"key: sleVlanInboundTagPortIndex, sleVlanInboundTagVlanIndex"
			INDEX { sleVlanInboundTagPortIndex, sleVlanInboundTagVlanIndex, sleVlanInboundTagVlanPriority }
			::= { sleVlanInboundTagTable 1 }

		
		SleVlanInboundTagEntry ::=
			SEQUENCE { 
				sleVlanInboundTagPortIndex
					INTEGER,
				sleVlanInboundTagVlanIndex
					INTEGER,
				sleVlanInboundTagOuterVid
					INTEGER,
				sleVlanInboundTagOperStatus
					INTEGER,
				sleVlanInboundTagVlanPriority
					INTEGER,
				sleVlanInboundTagOuterVlanPriority
					INTEGER
			 }

		sleVlanInboundTagPortIndex OBJECT-TYPE
			SYNTAX INTEGER (1..65535)
			MAX-ACCESS read-only
			STATUS current
			DESCRIPTION
				"Bridge Port Index"
			::= { sleVlanInboundTagEntry 1 }

		
		sleVlanInboundTagVlanIndex OBJECT-TYPE
			SYNTAX INTEGER (1..4094)
			MAX-ACCESS read-only
			STATUS current
			DESCRIPTION
				"Vlan Index of inner-tag"
			::= { sleVlanInboundTagEntry 2 }

		
		sleVlanInboundTagOuterVid OBJECT-TYPE
			SYNTAX INTEGER (1..4094)
			MAX-ACCESS read-only
			STATUS current
			DESCRIPTION
				"The Outer Vlan-ID to tag for incoming packet with vlan index"
			::= { sleVlanInboundTagEntry 3 }

		
		sleVlanInboundTagOperStatus OBJECT-TYPE
			SYNTAX INTEGER
				{
				on(1),
				off(2)
				}
			MAX-ACCESS read-only
			STATUS current
			DESCRIPTION
				"The Operational Status of Outer Vlan-ID to tag for incoming packet with vlan index."
			::= { sleVlanInboundTagEntry 4 }

		
		sleVlanInboundTagVlanPriority OBJECT-TYPE
			SYNTAX INTEGER
				{
				cos0(0),
				cos1(1),
				cos2(2),
				cos3(3),
				cos4(4),
				cos5(5),
				cos6(6),
				cos7(7),
				cosAny(8)
				}
			MAX-ACCESS read-only
			STATUS current
			DESCRIPTION
				"Vlan Priority of inner-tag"
			::= { sleVlanInboundTagEntry 5 }

		
		sleVlanInboundTagOuterVlanPriority OBJECT-TYPE
			SYNTAX INTEGER
				{
				cos0(0),
				cos1(1),
				cos2(2),
				cos3(3),
				cos4(4),
				cos5(5),
				cos6(6),
				cos7(7)
				}
			MAX-ACCESS read-only
			STATUS current
			DESCRIPTION
				"The Outer Vlan-Pri to tag for incoming packet with vlan index"
			::= { sleVlanInboundTagEntry 6 }

		
		sleVlanInboundTagControl OBJECT IDENTIFIER ::= { sleVlanInboundTag 2 }

		
		sleVlanInboundTagControlRequest OBJECT-TYPE
			SYNTAX INTEGER
				{
				setInboundVid(1),
				clearInboundVid(2)
				}
			MAX-ACCESS read-write
			STATUS current
			DESCRIPTION
				"The request of a user command"
			::= { sleVlanInboundTagControl 1 }

		
		sleVlanInboundTagControlStatus OBJECT-TYPE
			SYNTAX SleControlStatusType
			MAX-ACCESS read-only
			STATUS current
			DESCRIPTION
				"The status of user command"
			::= { sleVlanInboundTagControl 2 }

		
		sleVlanInboundTagControlTimer OBJECT-TYPE
			SYNTAX Gauge32
			MAX-ACCESS read-write
			STATUS current
			DESCRIPTION
				"The maximum time for the manager for a long running user command"
			::= { sleVlanInboundTagControl 3 }

		
		sleVlanInboundTagControlTimeStamp OBJECT-TYPE
			SYNTAX TimeTicks
			MAX-ACCESS read-only
			STATUS current
			DESCRIPTION
				"The time stamp of the last command(end of command)"
			::= { sleVlanInboundTagControl 4 }

		
		sleVlanInboundTagControlReqResult OBJECT-TYPE
			SYNTAX SleControlRequestResultType
			MAX-ACCESS read-only
			STATUS current
			DESCRIPTION
				"The result of the last user command"
			::= { sleVlanInboundTagControl 5 }

		
		sleVlanInboundTagControlPortIndex OBJECT-TYPE
			SYNTAX INTEGER (1..65535)
			MAX-ACCESS read-write
			STATUS current
			DESCRIPTION
				"sleVlanInboundTagPortIndex"
			::= { sleVlanInboundTagControl 6 }

		
		sleVlanInboundTagControlVlanIndex OBJECT-TYPE
			SYNTAX INTEGER (1..4094)
			MAX-ACCESS read-write
			STATUS current
			DESCRIPTION
				"sleVlanInboundTagVlanIndex"
			::= { sleVlanInboundTagControl 7 }

		
		sleVlanInboundTagControlOuterVid OBJECT-TYPE
			SYNTAX INTEGER (0..4094)
			MAX-ACCESS read-write
			STATUS current
			DESCRIPTION
				"The Vlan-ID for outer-tag
				0 : clear
				"
			::= { sleVlanInboundTagControl 8 }

		
		sleVlanInboundTagControlVlanPriority OBJECT-TYPE
			SYNTAX INTEGER
				{
				cos0(0),
				cos1(1),
				cos2(2),
				cos3(3),
				cos4(4),
				cos5(5),
				cos6(6),
				cos7(7),
				cosAny(8)
				}
			MAX-ACCESS read-write
			STATUS current
			DESCRIPTION
				"Vlan Priority of inner-tag"
			::= { sleVlanInboundTagControl 9 }

		
		sleVlanInboundTagControlOuterVlanPriority OBJECT-TYPE
			SYNTAX INTEGER
				{
				cos0(0),
				cos1(1),
				cos2(2),
				cos3(3),
				cos4(4),
				cos5(5),
				cos6(6),
				cos7(7)
				}
			MAX-ACCESS read-write
			STATUS current
			DESCRIPTION
				"The Outer Vlan-Pri to tag for incoming packet with vlan index"
			::= { sleVlanInboundTagControl 10 }

		
		sleVlanInboundTagNotification OBJECT IDENTIFIER ::= { sleVlanInboundTag 3 }

		
		sleVlanInboundTagChanged NOTIFICATION-TYPE
			OBJECTS { sleVlanInboundTagControlRequest, sleVlanInboundTagControlReqResult, sleVlanInboundTagControlTimeStamp, sleVlanInboundTagControlPortIndex, sleVlanInboundTagControlVlanIndex, 
				sleVlanInboundTagControlOuterVid, sleVlanInboundTagControlVlanPriority, sleVlanInboundTagControlOuterVlanPriority }
			STATUS current
			DESCRIPTION 
				"setInboundVid"
			::= { sleVlanInboundTagNotification 1 }

		
		sleVlanInboundTagCleared NOTIFICATION-TYPE
			OBJECTS { sleVlanInboundTagControlRequest, sleVlanInboundTagControlTimeStamp, sleVlanInboundTagControlReqResult, sleVlanInboundTagControlPortIndex, sleVlanInboundTagControlVlanIndex, 
				sleVlanInboundTagControlVlanPriority }
			STATUS current
			DESCRIPTION 
				"Description."
			::= { sleVlanInboundTagNotification 2 }

		
		sleVlanOutboundTag OBJECT IDENTIFIER ::= { sleVlanTag 2 }

		
		sleVlanOutboundTagTable OBJECT-TYPE
			SYNTAX SEQUENCE OF SleVlanOutboundTagEntry
			MAX-ACCESS not-accessible
			STATUS current
			DESCRIPTION
				"vlan outbound tag table."
			::= { sleVlanOutboundTag 1 }

		
		sleVlanOutboundTagEntry OBJECT-TYPE
			SYNTAX SleVlanOutboundTagEntry
			MAX-ACCESS not-accessible
			STATUS current
			DESCRIPTION
				"key: sleVlanOutboundTagPortIndex, sleVlanOutboundTagVlanIndex"
			INDEX { sleVlanOutboundTagPortIndex, sleVlanOutboundTagVlanIndex }
			::= { sleVlanOutboundTagTable 1 }

		
		SleVlanOutboundTagEntry ::=
			SEQUENCE { 
				sleVlanOutboundTagPortIndex
					INTEGER,
				sleVlanOutboundTagVlanIndex
					INTEGER,
				sleVlanOutboundTagOperStatus
					INTEGER
			 }

		sleVlanOutboundTagPortIndex OBJECT-TYPE
			SYNTAX INTEGER (1..65535)
			MAX-ACCESS read-only
			STATUS current
			DESCRIPTION
				"Bridge Port Index for egress port"
			::= { sleVlanOutboundTagEntry 1 }

		
		sleVlanOutboundTagVlanIndex OBJECT-TYPE
			SYNTAX INTEGER (1..4094)
			MAX-ACCESS read-only
			STATUS current
			DESCRIPTION
				"Vlan index of outer-tag"
			::= { sleVlanOutboundTagEntry 2 }

		
		sleVlanOutboundTagOperStatus OBJECT-TYPE
			SYNTAX INTEGER
				{
				on(1),
				off(2)
				}
			MAX-ACCESS read-only
			STATUS current
			DESCRIPTION
				"The Operational Status of Outer Vlan-ID to tag for outgoing packet with vlan index."
			::= { sleVlanOutboundTagEntry 3 }

		
		sleVlanOutboundTagControl OBJECT IDENTIFIER ::= { sleVlanOutboundTag 2 }

		
		sleVlanOutboundTagControlRequest OBJECT-TYPE
			SYNTAX INTEGER
				{
				setOutboundtag(1),
				clearOutboundtag(2)
				}
			MAX-ACCESS read-write
			STATUS current
			DESCRIPTION
				"The request of a user command"
			::= { sleVlanOutboundTagControl 1 }

		
		sleVlanOutboundTagControlStatus OBJECT-TYPE
			SYNTAX SleControlStatusType
			MAX-ACCESS read-only
			STATUS current
			DESCRIPTION
				"The status of user command"
			::= { sleVlanOutboundTagControl 2 }

		
		sleVlanOutboundTagControlTimer OBJECT-TYPE
			SYNTAX Gauge32
			MAX-ACCESS read-write
			STATUS current
			DESCRIPTION
				"The maximum time for the manager for a long running user command"
			::= { sleVlanOutboundTagControl 3 }

		
		sleVlanOutboundTagControlTimeStamp OBJECT-TYPE
			SYNTAX TimeTicks
			MAX-ACCESS read-only
			STATUS current
			DESCRIPTION
				"The time stamp of the last command(end of command)"
			::= { sleVlanOutboundTagControl 4 }

		
		sleVlanOutboundTagControlReqResult OBJECT-TYPE
			SYNTAX SleControlRequestResultType
			MAX-ACCESS read-only
			STATUS current
			DESCRIPTION
				"The result of the last user command"
			::= { sleVlanOutboundTagControl 5 }

		
		sleVlanOutboundTagControlPortIndex OBJECT-TYPE
			SYNTAX INTEGER (1..65535)
			MAX-ACCESS read-write
			STATUS current
			DESCRIPTION
				"sleVlanOutboundTagPortIndex"
			::= { sleVlanOutboundTagControl 6 }

		
		sleVlanOutboundTagControlOuterVid OBJECT-TYPE
			SYNTAX INTEGER (1..4094)
			MAX-ACCESS read-write
			STATUS current
			DESCRIPTION
				"The outer-tag vid of packet to go out on the egress port"
			::= { sleVlanOutboundTagControl 7 }

		
		sleVlanOutboundTagNotification OBJECT IDENTIFIER ::= { sleVlanOutboundTag 3 }

		
		sleVlanOutboundTagSet NOTIFICATION-TYPE
			OBJECTS { sleVlanOutboundTagControlRequest, sleVlanOutboundTagControlReqResult, sleVlanOutboundTagControlTimeStamp, sleVlanOutboundTagControlPortIndex, sleVlanOutboundTagControlOuterVid
				 }
			STATUS current
			DESCRIPTION 
				"setOutboundtag"
			::= { sleVlanOutboundTagNotification 1 }

		
		sleVlanOutboundTagClear NOTIFICATION-TYPE
			OBJECTS { sleVlanOutboundTagControlRequest, sleVlanOutboundTagControlReqResult, sleVlanOutboundTagControlTimeStamp, sleVlanOutboundTagControlPortIndex, sleVlanOutboundTagControlOuterVid
				 }
			STATUS current
			DESCRIPTION 
				"clearOutboundtag"
			::= { sleVlanOutboundTagNotification 2 }

		
		sleVlanRangeInboundTag OBJECT IDENTIFIER ::= { sleVlanTag 3 }

		
		sleVlanRangeInboundTagTable OBJECT-TYPE
			SYNTAX SEQUENCE OF SleVlanRangeInboundTagEntry
			MAX-ACCESS not-accessible
			STATUS current
			DESCRIPTION
				"vlan range inbound tag table."
			::= { sleVlanRangeInboundTag 1 }

		
		sleVlanRangeInboundTagEntry OBJECT-TYPE
			SYNTAX SleVlanRangeInboundTagEntry
			MAX-ACCESS not-accessible
			STATUS current
			DESCRIPTION
				"key: sleVlanRangeInboundTagPortIndex, sleVlanRangeInboundTagMinVlanIndex, sleVlanRangeInboundTagMaxVlanIndex"
			INDEX { sleVlanRangeInboundTagPortIndex, sleVlanRangeInboundTagMinVlanIndex, sleVlanRangeInboundTagMaxVlanIndex }
			::= { sleVlanRangeInboundTagTable 1 }

		
		SleVlanRangeInboundTagEntry ::=
			SEQUENCE { 
				sleVlanRangeInboundTagPortIndex
					Integer32,
				sleVlanRangeInboundTagMinVlanIndex
					Integer32,
				sleVlanRangeInboundTagMaxVlanIndex
					Integer32,
				sleVlanRangeInboundTagOuterVid
					Integer32,
				sleVlanRangeInboundTagOperStatus
					INTEGER
			 }

		sleVlanRangeInboundTagPortIndex OBJECT-TYPE
			SYNTAX Integer32 (1..512)
			MAX-ACCESS read-only
			STATUS current
			DESCRIPTION
				"Bridge Port Index."
			::= { sleVlanRangeInboundTagEntry 1 }

		
		sleVlanRangeInboundTagMinVlanIndex OBJECT-TYPE
			SYNTAX Integer32 (1..65535)
			MAX-ACCESS read-only
			STATUS current
			DESCRIPTION
				"Min Vlan Index of inner-tag."
			::= { sleVlanRangeInboundTagEntry 2 }

		
		sleVlanRangeInboundTagMaxVlanIndex OBJECT-TYPE
			SYNTAX Integer32 (1..65535)
			MAX-ACCESS read-only
			STATUS current
			DESCRIPTION
				"Max Vlan Index of inner-tag."
			::= { sleVlanRangeInboundTagEntry 3 }

		
		sleVlanRangeInboundTagOuterVid OBJECT-TYPE
			SYNTAX Integer32 (1..65535)
			MAX-ACCESS read-only
			STATUS current
			DESCRIPTION
				"The Outer Vlan-ID to tag for incoming packet with vlan index."
			::= { sleVlanRangeInboundTagEntry 4 }

		
		sleVlanRangeInboundTagOperStatus OBJECT-TYPE
			SYNTAX INTEGER
				{
				on(1),
				off(2)
				}
			MAX-ACCESS read-only
			STATUS current
			DESCRIPTION
				"The Operational Status of Outer Vlan-ID to tag for incoming packet with vlan index."
			::= { sleVlanRangeInboundTagEntry 5 }

		
		sleVlanRangeInboundTagControl OBJECT IDENTIFIER ::= { sleVlanRangeInboundTag 2 }

		
		sleVlanRangeInboundTagControlRequest OBJECT-TYPE
			SYNTAX INTEGER
				{
				setRangeInboundVid(1),
				clearRangeInboundVid(2)
				}
			MAX-ACCESS read-write
			STATUS current
			DESCRIPTION
				"The request of a user command."
			::= { sleVlanRangeInboundTagControl 1 }

		
		sleVlanRangeInboundTagControlStatus OBJECT-TYPE
			SYNTAX SleControlStatusType
			MAX-ACCESS read-only
			STATUS current
			DESCRIPTION
				"The status of a user command."
			::= { sleVlanRangeInboundTagControl 2 }

		
		sleVlanRangeInboundTagControlTimer OBJECT-TYPE
			SYNTAX Gauge32
			MAX-ACCESS read-write
			STATUS current
			DESCRIPTION
				"The maximum wait time for the manager for a long running user command."
			::= { sleVlanRangeInboundTagControl 3 }

		
		sleVlanRangeInboundTagControlTimeStamp OBJECT-TYPE
			SYNTAX TimeTicks
			MAX-ACCESS read-only
			STATUS current
			DESCRIPTION
				"The time stamp of the last command (end of command)."
			::= { sleVlanRangeInboundTagControl 4 }

		
		sleVlanRangeInboundTagControlReqResult OBJECT-TYPE
			SYNTAX SleControlRequestResultType
			MAX-ACCESS read-only
			STATUS current
			DESCRIPTION
				"The result of the last user command."
			::= { sleVlanRangeInboundTagControl 5 }

		
		sleVlanRangeInboundTagControlPortIndex OBJECT-TYPE
			SYNTAX Integer32 (1..512)
			MAX-ACCESS read-write
			STATUS current
			DESCRIPTION
				"Bridge Port Index."
			::= { sleVlanRangeInboundTagControl 6 }

		
		sleVlanRangeInboundTagControlMinVlanIndex OBJECT-TYPE
			SYNTAX Integer32 (1..65535)
			MAX-ACCESS read-write
			STATUS current
			DESCRIPTION
				"Min vlan Index of inner-tag."
			::= { sleVlanRangeInboundTagControl 7 }

		
		sleVlanRangeInboundTagControlMaxVlanIndex OBJECT-TYPE
			SYNTAX Integer32 (1..65535)
			MAX-ACCESS read-write
			STATUS current
			DESCRIPTION
				"Max vlan Index of inner-tag."
			::= { sleVlanRangeInboundTagControl 8 }

		
		sleVlanRangeInboundTagControlOuterVid OBJECT-TYPE
			SYNTAX Integer32 (1..65535)
			MAX-ACCESS read-write
			STATUS current
			DESCRIPTION
				"The Outer Vlan-ID to tag for incoming packet with vlan index."
			::= { sleVlanRangeInboundTagControl 9 }

		
		sleVlanRangeInboundTagNotification OBJECT IDENTIFIER ::= { sleVlanRangeInboundTag 3 }

		
		sleVlanRangeInboundTagChanged NOTIFICATION-TYPE
			OBJECTS { sleVlanRangeInboundTagControlRequest, sleVlanRangeInboundTagControlTimeStamp, sleVlanRangeInboundTagControlReqResult, sleVlanRangeInboundTagControlPortIndex, sleVlanRangeInboundTagControlMinVlanIndex, 
				sleVlanRangeInboundTagControlMaxVlanIndex, sleVlanRangeInboundTagControlOuterVid }
			STATUS current
			DESCRIPTION 
				"Description."
			::= { sleVlanRangeInboundTagNotification 1 }

		
		sleVlanRangeInboundTagCleared NOTIFICATION-TYPE
			OBJECTS { sleVlanRangeInboundTagControlRequest, sleVlanRangeInboundTagControlTimeStamp, sleVlanRangeInboundTagControlReqResult, sleVlanRangeInboundTagControlPortIndex, sleVlanRangeInboundTagControlMinVlanIndex, 
				sleVlanRangeInboundTagControlMaxVlanIndex }
			STATUS current
			DESCRIPTION 
				"Description."
			::= { sleVlanRangeInboundTagNotification 2 }

		
		sleVlanProtoId OBJECT IDENTIFIER ::= { sleVlanTag 4 }

		
		sleVlanProtoIdTable OBJECT-TYPE
			SYNTAX SEQUENCE OF SleVlanProtoIdEntry
			MAX-ACCESS not-accessible
			STATUS current
			DESCRIPTION
				"vlan proto id table"
			::= { sleVlanProtoId 1 }

		
		sleVlanProtoIdEntry OBJECT-TYPE
			SYNTAX SleVlanProtoIdEntry
			MAX-ACCESS not-accessible
			STATUS current
			DESCRIPTION
				"key: sleVlanProtoIdVid"
			INDEX { sleVlanProtoIdVid }
			::= { sleVlanProtoIdTable 1 }

		
		SleVlanProtoIdEntry ::=
			SEQUENCE { 
				sleVlanProtoIdVid
					Integer32,
				sleVlanProtoIdOuterProtoId
					INTEGER
			 }

		sleVlanProtoIdVid OBJECT-TYPE
			SYNTAX Integer32 (0..65535)
			MAX-ACCESS read-only
			STATUS current
			DESCRIPTION
				"The Vlan ID."
			::= { sleVlanProtoIdEntry 1 }

		
		sleVlanProtoIdOuterProtoId OBJECT-TYPE
			SYNTAX INTEGER
				{
				dtag8100(33024),
				dtag9100(37120)
				}
			MAX-ACCESS read-only
			STATUS current
			DESCRIPTION
				"programmable outer Double Tag Protocol Identifier."
			::= { sleVlanProtoIdEntry 2 }

		
		sleVlanProtoIdControl OBJECT IDENTIFIER ::= { sleVlanProtoId 2 }

		
		sleVlanProtoIdControlRequest OBJECT-TYPE
			SYNTAX INTEGER { setVlanProtoIdOuterTpid(1) }
			MAX-ACCESS read-write
			STATUS current
			DESCRIPTION
				"The request of a user command"
			::= { sleVlanProtoIdControl 1 }

		
		sleVlanProtoIdControlStatus OBJECT-TYPE
			SYNTAX SleControlStatusType
			MAX-ACCESS read-only
			STATUS current
			DESCRIPTION
				"The status of user command"
			::= { sleVlanProtoIdControl 2 }

		
		sleVlanProtoIdControlTimer OBJECT-TYPE
			SYNTAX Gauge32
			MAX-ACCESS read-write
			STATUS current
			DESCRIPTION
				"The maximum time for the manager for a long running user command"
			::= { sleVlanProtoIdControl 3 }

		
		sleVlanProtoIdControlTimeStamp OBJECT-TYPE
			SYNTAX TimeTicks
			MAX-ACCESS read-only
			STATUS current
			DESCRIPTION
				"The time stamp of the last command(end of command)"
			::= { sleVlanProtoIdControl 4 }

		
		sleVlanProtoIdControlReqResult OBJECT-TYPE
			SYNTAX SleControlRequestResultType
			MAX-ACCESS read-only
			STATUS current
			DESCRIPTION
				"The result of the last user command"
			::= { sleVlanProtoIdControl 5 }

		
		sleVlanProtoIdControlVid OBJECT-TYPE
			SYNTAX Integer32
			MAX-ACCESS read-write
			STATUS current
			DESCRIPTION
				"The Vlan Index."
			::= { sleVlanProtoIdControl 6 }

		
		sleVlanProtoIdControlOuterProtoId OBJECT-TYPE
			SYNTAX Integer32
			MAX-ACCESS read-write
			STATUS current
			DESCRIPTION
				"The programmable outer Double Tag Protocol Identifier"
			::= { sleVlanProtoIdControl 7 }

		
		sleVlanProtoIdNotification OBJECT IDENTIFIER ::= { sleVlanProtoId 3 }

		
		sleVlanProtoIdOuterProtoIdChanged NOTIFICATION-TYPE
			OBJECTS { sleVlanProtoIdControlRequest, sleVlanProtoIdControlTimeStamp, sleVlanProtoIdControlReqResult, sleVlanProtoIdControlVid, sleVlanProtoIdControlOuterProtoId
				 }
			STATUS current
			DESCRIPTION 
				"Description."
			::= { sleVlanProtoIdNotification 1 }

		
		sleVlanMapping OBJECT IDENTIFIER ::= { sleBridge 28 }

		
		sleVlanMappingTable OBJECT-TYPE
			SYNTAX SEQUENCE OF SleVlanMappingEntry
			MAX-ACCESS not-accessible
			STATUS current
			DESCRIPTION
				"vlan mapping table"
			::= { sleVlanMapping 1 }

		
		sleVlanMappingEntry OBJECT-TYPE
			SYNTAX SleVlanMappingEntry
			MAX-ACCESS not-accessible
			STATUS current
			DESCRIPTION
				"key: sleVlanMappingIndex"
			INDEX { sleVlanMappingIndex }
			::= { sleVlanMappingTable 1 }

		
		SleVlanMappingEntry ::=
			SEQUENCE { 
				sleVlanMappingIndex
					INTEGER,
				sleVlanMappingPortId
					INTEGER,
				sleVlanMappingOriVlanId
					INTEGER,
				sleVlanMappingTransVlanId
					INTEGER,
				sleVlanMappingMode
					INTEGER,
				sleVlanMappingMatchCos
					Integer32,
				sleVlanMappingMatchDscp
					Integer32,
				sleVlanMappingMatchEthType
					INTEGER,
				sleVlanMappingMatchIPPrecedence
					Integer32,
				sleVlanMappingMatchTos
					Integer32,
				sleVlanMappingRateLimit
					INTEGER,
				sleVlanMappingCos
					Integer32,
				sleVlanMappingDscp
					Integer32
			 }

		sleVlanMappingIndex OBJECT-TYPE
			SYNTAX INTEGER (1..65535)
			MAX-ACCESS read-only
			STATUS current
			DESCRIPTION
				"The Vlan index"
			::= { sleVlanMappingEntry 1 }

		
		sleVlanMappingPortId OBJECT-TYPE
			SYNTAX INTEGER (1..65535)
			MAX-ACCESS read-only
			STATUS current
			DESCRIPTION
				"The port index."
			::= { sleVlanMappingEntry 2 }

		
		sleVlanMappingOriVlanId OBJECT-TYPE
			SYNTAX INTEGER (1..4094)
			MAX-ACCESS read-only
			STATUS current
			DESCRIPTION
				"The original vlan index."
			::= { sleVlanMappingEntry 3 }

		
		sleVlanMappingTransVlanId OBJECT-TYPE
			SYNTAX INTEGER (1..4094)
			MAX-ACCESS read-only
			STATUS current
			DESCRIPTION
				"The translation vlan index"
			::= { sleVlanMappingEntry 4 }

		
		sleVlanMappingMode OBJECT-TYPE
			SYNTAX INTEGER
				{
				default(0),
				cos(1),
				dscp(2),
				matchCos(3),
				matchDscp(4),
				matchEthType(5),
				matchIpPrecedence(6),
				matchTos(7),
				rateLimit(8)
				}
			MAX-ACCESS read-only
			STATUS current
			DESCRIPTION
				"The vlan mapping mode configuration"
			::= { sleVlanMappingEntry 5 }

		
		sleVlanMappingMatchCos OBJECT-TYPE
			SYNTAX Integer32 (-1 | 0..7)
			MAX-ACCESS read-only
			STATUS current
			DESCRIPTION
				"The match CoS value"
			::= { sleVlanMappingEntry 6 }

		
		sleVlanMappingMatchDscp OBJECT-TYPE
			SYNTAX Integer32 (-1 | 0..63)
			MAX-ACCESS read-only
			STATUS current
			DESCRIPTION
				"The match DSCP value"
			::= { sleVlanMappingEntry 7 }

		
		sleVlanMappingMatchEthType OBJECT-TYPE
			SYNTAX INTEGER (-1 | 1..65535)
			MAX-ACCESS read-only
			STATUS current
			DESCRIPTION
				"The match Ethernet type value"
			::= { sleVlanMappingEntry 8 }

		
		sleVlanMappingMatchIPPrecedence OBJECT-TYPE
			SYNTAX Integer32 (-1 | 0..7)
			MAX-ACCESS read-only
			STATUS current
			DESCRIPTION
				"The Match IP precedence value"
			::= { sleVlanMappingEntry 9 }

		
		sleVlanMappingMatchTos OBJECT-TYPE
			SYNTAX Integer32 (-1 | 0..255)
			MAX-ACCESS read-only
			STATUS current
			DESCRIPTION
				"The match ToS value"
			::= { sleVlanMappingEntry 10 }

		
		sleVlanMappingRateLimit OBJECT-TYPE
			SYNTAX INTEGER (-1 | 1..65535)
			MAX-ACCESS read-only
			STATUS current
			DESCRIPTION
				"The rate limit value"
			::= { sleVlanMappingEntry 11 }

		
		sleVlanMappingCos OBJECT-TYPE
			SYNTAX Integer32 (-1 | 0..7)
			MAX-ACCESS read-only
			STATUS current
			DESCRIPTION
				"The CoS value"
			::= { sleVlanMappingEntry 12 }

		
		sleVlanMappingDscp OBJECT-TYPE
			SYNTAX Integer32 (-1 | 0..63)
			MAX-ACCESS read-only
			STATUS current
			DESCRIPTION
				"The DSCP value"
			::= { sleVlanMappingEntry 13 }

		
		sleVlanMappingControl OBJECT IDENTIFIER ::= { sleVlanMapping 2 }

		
		sleVlanMappingControlRequest OBJECT-TYPE
			SYNTAX INTEGER
				{
				addVlanMapping(1),
				delVlanMapping(2)
				}
			MAX-ACCESS read-write
			STATUS current
			DESCRIPTION
				"The request of a user command"
			::= { sleVlanMappingControl 1 }

		
		sleVlanMappingControlStatus OBJECT-TYPE
			SYNTAX SleControlStatusType
			MAX-ACCESS read-write
			STATUS current
			DESCRIPTION
				"The status of user command"
			::= { sleVlanMappingControl 2 }

		
		sleVlanMappingControlTimer OBJECT-TYPE
			SYNTAX Gauge32
			MAX-ACCESS read-write
			STATUS current
			DESCRIPTION
				"The maximum time for the manager for a long running user command"
			::= { sleVlanMappingControl 3 }

		
		sleVlanMappingControlTimeStamp OBJECT-TYPE
			SYNTAX TimeTicks
			MAX-ACCESS read-write
			STATUS current
			DESCRIPTION
				"The time stamp of the last command(end of command)"
			::= { sleVlanMappingControl 4 }

		
		sleVlanMappingControlReqResult OBJECT-TYPE
			SYNTAX SleControlRequestResultType
			MAX-ACCESS read-write
			STATUS current
			DESCRIPTION
				"The result of the last user command"
			::= { sleVlanMappingControl 5 }

		
		sleVlanMappingControlIndex OBJECT-TYPE
			SYNTAX INTEGER (1..65535)
			MAX-ACCESS read-write
			STATUS current
			DESCRIPTION
				"The Vlan index"
			::= { sleVlanMappingControl 6 }

		
		sleVlanMappingControlPortId OBJECT-TYPE
			SYNTAX INTEGER (1..65535)
			MAX-ACCESS read-write
			STATUS current
			DESCRIPTION
				"The port index."
			::= { sleVlanMappingControl 7 }

		
		sleVlanMappingControlOriVlanId OBJECT-TYPE
			SYNTAX INTEGER (1..4094)
			MAX-ACCESS read-write
			STATUS current
			DESCRIPTION
				"The original vlan index."
			::= { sleVlanMappingControl 8 }

		
		sleVlanMappingControlTransVlanID OBJECT-TYPE
			SYNTAX INTEGER (1..4094)
			MAX-ACCESS read-write
			STATUS current
			DESCRIPTION
				"The translation vlan index"
			::= { sleVlanMappingControl 9 }

		
		sleVlanMappingControlMode OBJECT-TYPE
			SYNTAX INTEGER
				{
				default(0),
				cos(1),
				dscp(2),
				matchCos(3),
				matchDscp(4),
				matchEthType(5),
				matchIpPrecedence(6),
				matchTos(7),
				rateLimit(8)
				}
			MAX-ACCESS read-write
			STATUS current
			DESCRIPTION
				"The vlan mapping mode configuration"
			::= { sleVlanMappingControl 10 }

		
		sleVlanMappingControlMatchCos OBJECT-TYPE
			SYNTAX Integer32 (-1 | 0..7)
			MAX-ACCESS read-write
			STATUS current
			DESCRIPTION
				"The match CoS value"
			::= { sleVlanMappingControl 11 }

		
		sleVlanMappingControlMatchDscp OBJECT-TYPE
			SYNTAX Integer32 (-1 | 0..63)
			MAX-ACCESS read-write
			STATUS current
			DESCRIPTION
				"The match DSCP value"
			::= { sleVlanMappingControl 12 }

		
		sleVlanMappingControlMatchEthType OBJECT-TYPE
			SYNTAX INTEGER (-1 | 1..65535)
			MAX-ACCESS read-write
			STATUS current
			DESCRIPTION
				"The match Ethernet type value"
			::= { sleVlanMappingControl 13 }

		
		sleVlanMappingControlMatchIPPrecedence OBJECT-TYPE
			SYNTAX Integer32 (-1 | 0..7)
			MAX-ACCESS read-write
			STATUS current
			DESCRIPTION
				"The Match IP precedence value"
			::= { sleVlanMappingControl 14 }

		
		sleVlanMappingControlMatchTos OBJECT-TYPE
			SYNTAX Integer32 (-1 | 0..255)
			MAX-ACCESS read-write
			STATUS current
			DESCRIPTION
				"The match ToS value"
			::= { sleVlanMappingControl 15 }

		
		sleVlanMappingControlRateLimit OBJECT-TYPE
			SYNTAX INTEGER (-1 | 1..65535)
			MAX-ACCESS read-write
			STATUS current
			DESCRIPTION
				"The rate limit value"
			::= { sleVlanMappingControl 16 }

		
		sleVlanMappingControlCos OBJECT-TYPE
			SYNTAX Integer32 (-1 | 0..7)
			MAX-ACCESS read-write
			STATUS current
			DESCRIPTION
				"The CoS value"
			::= { sleVlanMappingControl 17 }

		
		sleVlanMappingControlDscp OBJECT-TYPE
			SYNTAX Integer32 (-1 | 0..255)
			MAX-ACCESS read-write
			STATUS current
			DESCRIPTION
				"The DSCP value"
			::= { sleVlanMappingControl 18 }

		
		sleVlanMappingNotification OBJECT IDENTIFIER ::= { sleVlanMapping 3 }

		
		sleVlanMappingCreated NOTIFICATION-TYPE
			OBJECTS { sleVlanMappingControlRequest, sleVlanMappingControlTimeStamp, sleVlanMappingControlReqResult, sleVlanMappingControlPortId, sleVlanMappingControlOriVlanId, 
				sleVlanMappingControlTransVlanID, sleVlanMappingControlMode, sleVlanMappingControlMatchCos, sleVlanMappingControlMatchDscp, sleVlanMappingControlMatchEthType, 
				sleVlanMappingControlMatchIPPrecedence, sleVlanMappingControlMatchTos, sleVlanMappingControlRateLimit, sleVlanMappingControlCos, sleVlanMappingControlDscp
				 }
			STATUS current
			DESCRIPTION 
				"Description."
			::= { sleVlanMappingNotification 1 }

		
		sleVlanMappingDeleted NOTIFICATION-TYPE
			OBJECTS { sleVlanMappingControlRequest, sleVlanMappingControlTimeStamp, sleVlanMappingControlIndex, sleVlanMappingControlReqResult }
			STATUS current
			DESCRIPTION 
				"Description."
			::= { sleVlanMappingNotification 2 }

		
		slePowerInline OBJECT IDENTIFIER ::= { sleBridge 29 }

		
		slePowerInlineTable OBJECT-TYPE
			SYNTAX SEQUENCE OF SlePowerInlineEntry
			MAX-ACCESS not-accessible
			STATUS current
			DESCRIPTION
				"The poe snmp main table"
			::= { slePowerInline 1 }

		
		slePowerInlineEntry OBJECT-TYPE
			SYNTAX SlePowerInlineEntry
			MAX-ACCESS not-accessible
			STATUS current
			DESCRIPTION
				"The poe snmp entry table"
			INDEX { slePowerInlinePortIndex }
			::= { slePowerInlineTable 1 }

		
		SlePowerInlineEntry ::=
			SEQUENCE { 
				slePowerInlinePortIndex
					INTEGER,
				slePowerInlineAdminStatus
					INTEGER,
				slePowerInlinePortStatus
					INTEGER,
				slePowerInlineDetectionStatus
					INTEGER,
				slePowerInlinePortClass
					INTEGER,
				slePowerInlinePortMaxPow
					INTEGER,
				slePowerInlinePortLegacy
					INTEGER,
				slePowerInlinePortPriority
					INTEGER,
				slePowerInlinePortPower
					OCTET STRING,
				slePowerInlinePortCurrent
					OCTET STRING,
				slePowerInlinePortVoltage
					OCTET STRING,
				slePowerInlinePortTemperture
					OCTET STRING
			 }

		slePowerInlinePortIndex OBJECT-TYPE
			SYNTAX INTEGER (1..65535)
			MAX-ACCESS read-only
			STATUS current
			DESCRIPTION
				"The number of poe port."
			::= { slePowerInlineEntry 1 }

		
		slePowerInlineAdminStatus OBJECT-TYPE
			SYNTAX INTEGER
				{
				auto(1),
				static(2),
				null(3)
				}
			MAX-ACCESS read-only
			STATUS current
			DESCRIPTION
				"The poe port Admin status"
			::= { slePowerInlineEntry 2 }

		
		slePowerInlinePortStatus OBJECT-TYPE
			SYNTAX INTEGER
				{
				enable(1),
				disable(2)
				}
			MAX-ACCESS read-only
			STATUS current
			DESCRIPTION
				"The poe port operate status"
			::= { slePowerInlineEntry 3 }

		
		slePowerInlineDetectionStatus OBJECT-TYPE
			SYNTAX INTEGER
				{
				disable(1),
				searching(2),
				delivingPower(3),
				test(4),
				fault(5),
				overloadFault(6),
				requestPower(7)
				}
			MAX-ACCESS read-only
			STATUS current
			DESCRIPTION
				"The poe port detection status"
			::= { slePowerInlineEntry 4 }

		
		slePowerInlinePortClass OBJECT-TYPE
			SYNTAX INTEGER
				{
				class0(1),
				class1(2),
				class2(3),
				class3(4)
				}
			MAX-ACCESS read-only
			STATUS current
			DESCRIPTION
				"The poe port class type."
			::= { slePowerInlineEntry 5 }

		
		slePowerInlinePortMaxPow OBJECT-TYPE
			SYNTAX INTEGER (3000..30000)
			MAX-ACCESS read-only
			STATUS current
			DESCRIPTION
				"The max power value."
			::= { slePowerInlineEntry 6 }

		
		slePowerInlinePortLegacy OBJECT-TYPE
			SYNTAX INTEGER
				{
				enable(1),
				disable(2)
				}
			MAX-ACCESS read-only
			STATUS current
			DESCRIPTION
				"The poe port legacy mode."
			::= { slePowerInlineEntry 7 }

		
		slePowerInlinePortPriority OBJECT-TYPE
			SYNTAX INTEGER
				{
				low(1),
				medium(2),
				high(3)
				}
			MAX-ACCESS read-only
			STATUS current
			DESCRIPTION
				"The poe port priority level."
			::= { slePowerInlineEntry 8 }

		
		slePowerInlinePortPower OBJECT-TYPE
			SYNTAX OCTET STRING (SIZE (1..8))
			MAX-ACCESS read-only
			STATUS current
			DESCRIPTION
				"The poe port detected power."
			::= { slePowerInlineEntry 9 }

		
		slePowerInlinePortCurrent OBJECT-TYPE
			SYNTAX OCTET STRING (SIZE (1..8))
			MAX-ACCESS read-only
			STATUS current
			DESCRIPTION
				"The poe port detected current."
			::= { slePowerInlineEntry 10 }

		
		slePowerInlinePortVoltage OBJECT-TYPE
			SYNTAX OCTET STRING (SIZE (1..8))
			MAX-ACCESS read-only
			STATUS current
			DESCRIPTION
				"The poe port detected voltage."
			::= { slePowerInlineEntry 11 }

		
		slePowerInlinePortTemperture OBJECT-TYPE
			SYNTAX OCTET STRING (SIZE (1..8))
			MAX-ACCESS read-only
			STATUS current
			DESCRIPTION
				"The poe port detected temperture."
			::= { slePowerInlineEntry 12 }

		
		slePowerInlineControl OBJECT IDENTIFIER ::= { slePowerInline 2 }
-- The poe snmp control table
		
		slePowerInlineControlRequest OBJECT-TYPE
			SYNTAX INTEGER
				{
				setPowerInlineEnable(1),
				setPowerInlineDisable(2),
				setPowerInlineReset(3),
				setPowerInlineLegacy(4),
				setPowerInlinePriority(5),
				setPowerInlineClass(6),
				setPowerInlinePower(7)
				}
			MAX-ACCESS read-write
			STATUS current
			DESCRIPTION
				"The poe control request type"
			::= { slePowerInlineControl 1 }

		
		slePowerInlineControlStatus OBJECT-TYPE
			SYNTAX SleControlStatusType
			MAX-ACCESS read-only
			STATUS current
			DESCRIPTION
				"The poe control status type"
			::= { slePowerInlineControl 2 }

		
		slePowerInlineControlTimer OBJECT-TYPE
			SYNTAX Gauge32
			MAX-ACCESS read-write
			STATUS current
			DESCRIPTION
				"The poe control flag"
			::= { slePowerInlineControl 3 }

		
		slePowerInlineControlTimeStamp OBJECT-TYPE
			SYNTAX TimeTicks
			MAX-ACCESS read-only
			STATUS current
			DESCRIPTION
				"The poe control timestamp"
			::= { slePowerInlineControl 4 }

		
		slePowerInlineControlReqResult OBJECT-TYPE
			SYNTAX SleControlRequestResultType
			MAX-ACCESS read-only
			STATUS current
			DESCRIPTION
				"Result of the last command."
			::= { slePowerInlineControl 5 }

		
		slePowerInlineControlPortIndex OBJECT-TYPE
			SYNTAX INTEGER (1..65535)
			MAX-ACCESS read-write
			STATUS current
			DESCRIPTION
				"The Index of poe port."
			::= { slePowerInlineControl 6 }

		
		slePowerInlineControlAdminStatus OBJECT-TYPE
			SYNTAX INTEGER
				{
				auto(1),
				static(2),
				null(3)
				}
			MAX-ACCESS read-write
			STATUS current
			DESCRIPTION
				"The poe port admin status"
			::= { slePowerInlineControl 7 }

		
		slePowerInlineControlPortStatus OBJECT-TYPE
			SYNTAX INTEGER
				{
				enable(1),
				disable(2)
				}
			MAX-ACCESS read-write
			STATUS current
			DESCRIPTION
				"The poe port operate status."
			::= { slePowerInlineControl 8 }

		
		slePowerInlineControlPortClass OBJECT-TYPE
			SYNTAX INTEGER
				{
				class0(1),
				class1(2),
				class2(3),
				class3(4)
				}
			MAX-ACCESS read-write
			STATUS current
			DESCRIPTION
				"The poe port class type."
			::= { slePowerInlineControl 9 }

		
		slePowerInlineControlPortMaxPower OBJECT-TYPE
			SYNTAX INTEGER (3000..30000)
			MAX-ACCESS read-write
			STATUS current
			DESCRIPTION
				"The max power value."
			::= { slePowerInlineControl 10 }

		
		slePowerInlineControlPortLegacy OBJECT-TYPE
			SYNTAX INTEGER
				{
				enable(1),
				disable(2)
				}
			MAX-ACCESS read-write
			STATUS current
			DESCRIPTION
				"The poe port legacy mode."
			::= { slePowerInlineControl 11 }

		
		slePowerInlineControlPriority OBJECT-TYPE
			SYNTAX INTEGER
				{
				low(1),
				medium(2),
				high(3)
				}
			MAX-ACCESS read-write
			STATUS current
			DESCRIPTION
				"The poe port priority level."
			::= { slePowerInlineControl 12 }

		
		slePowerInlineNotification OBJECT IDENTIFIER ::= { slePowerInline 3 }
-- The poe snmp notify table
		
		slePowerInlineEnableChanged NOTIFICATION-TYPE
			OBJECTS { slePowerInlineControlRequest, slePowerInlineControlTimeStamp, slePowerInlineControlReqResult, slePowerInlineControlPortIndex, slePowerInlineControlPortStatus, 
				slePowerInlineControlPortClass, slePowerInlineControlPortMaxPower, slePowerInlineControlPortLegacy, slePowerInlineControlPriority }
			STATUS current
			DESCRIPTION 
				"setPowerInlineEnable"
			::= { slePowerInlineNotification 1 }

		
		slePowerInlineDisableChanged NOTIFICATION-TYPE
			OBJECTS { slePowerInlineControlRequest, slePowerInlineControlTimeStamp, slePowerInlineControlReqResult, slePowerInlineControlPortIndex, slePowerInlineControlPortStatus
				 }
			STATUS current
			DESCRIPTION 
				"setPowerInlineDisable"
			::= { slePowerInlineNotification 2 }

		
		slePowerInlineResetChanged NOTIFICATION-TYPE
			OBJECTS { slePowerInlineControlRequest, slePowerInlineControlTimeStamp, slePowerInlineControlReqResult, slePowerInlineControlPortIndex, slePowerInlineControlPortStatus, 
				slePowerInlineControlPortClass, slePowerInlineControlPortMaxPower, slePowerInlineControlPortLegacy, slePowerInlineControlPriority }
			STATUS current
			DESCRIPTION 
				"setPowerInlineReset"
			::= { slePowerInlineNotification 3 }

		
		slePowerInlineLegacyChanged NOTIFICATION-TYPE
			OBJECTS { slePowerInlineControlRequest, slePowerInlineControlTimeStamp, slePowerInlineControlReqResult, slePowerInlineControlPortIndex, slePowerInlineControlPortStatus, 
				slePowerInlineControlPortLegacy }
			STATUS current
			DESCRIPTION 
				"setPowerInlineLegacy"
			::= { slePowerInlineNotification 4 }

		
		slePowerInlinePriorityChanged NOTIFICATION-TYPE
			OBJECTS { slePowerInlineControlRequest, slePowerInlineControlTimeStamp, slePowerInlineControlReqResult, slePowerInlineControlPortIndex, slePowerInlineControlPortStatus, 
				slePowerInlineControlPriority }
			STATUS current
			DESCRIPTION 
				"setPowerInlinePriority"
			::= { slePowerInlineNotification 5 }

		
		slePowerInlineClassChanged NOTIFICATION-TYPE
			OBJECTS { slePowerInlineControlRequest, slePowerInlineControlTimeStamp, slePowerInlineControlReqResult, slePowerInlineControlPortIndex, slePowerInlineControlPortStatus, 
				slePowerInlineControlPortClass }
			STATUS current
			DESCRIPTION 
				"setPowerInlineClass"
			::= { slePowerInlineNotification 6 }

		
		slePowerInlinePowerChanged NOTIFICATION-TYPE
			OBJECTS { slePowerInlineControlRequest, slePowerInlineControlTimeStamp, slePowerInlineControlReqResult, slePowerInlineControlPortIndex, slePowerInlineControlPortStatus, 
				slePowerInlineControlPortClass, slePowerInlineControlPortMaxPower, slePowerInlineControlPortLegacy }
			STATUS current
			DESCRIPTION 
				"setPowerInlinePower"
			::= { slePowerInlineNotification 7 }

		
--  1.3.6.1.4.1.6296.9.8.14
		sleMfdb OBJECT IDENTIFIER ::= { sleBridge 30 }

		
--  1.3.6.1.4.1.6296.9.8.14.1
		sleMfdbTable OBJECT-TYPE
			SYNTAX SEQUENCE OF SleMfdbEntry
			MAX-ACCESS not-accessible
			STATUS current
			DESCRIPTION
				"The table of MFDB entries."
			::= { sleMfdb 1 }

		
--  1.3.6.1.4.1.6296.9.8.14.1.1
		sleMfdbEntry OBJECT-TYPE
			SYNTAX SleMfdbEntry
			MAX-ACCESS not-accessible
			STATUS current
			DESCRIPTION
				"Information about a specific MAC address that
				should be forwarding or dropping.
				key: sleMfdbMacAddress"
			INDEX { sleMfdbMacAddress, sleMfdbVlanIndex }
			::= { sleMfdbTable 1 }

		
		SleMfdbEntry ::=
			SEQUENCE { 
				sleMfdbMacAddress
					OCTET STRING,
				sleMfdbEntryPermission
					INTEGER,
				sleMfdbVlanIndex
					INTEGER,
				sleMfdbPorts
					OCTET STRING
			 }

--  1.3.6.1.4.1.6296.9.8.14.1.1.1
		sleMfdbMacAddress OBJECT-TYPE
			SYNTAX OCTET STRING (SIZE (0..6))
			MAX-ACCESS read-only
			STATUS current
			DESCRIPTION
				"A unicast MAC address for which the device has
				forwarding or filtering information."
			::= { sleMfdbEntry 1 }

		
--  1.3.6.1.4.1.6296.9.8.14.1.1.2
		sleMfdbEntryPermission OBJECT-TYPE
			SYNTAX INTEGER
				{
				deny(0),
				permit(1)
				}
			MAX-ACCESS read-only
			STATUS current
			DESCRIPTION
				"The permission of sleMFdbMacAddress.
				The meanings of the values are: 
				    deny(0)   - the value of the corresponding instance
				                of sleMfdbMacAddress will be dropped.
				    permit(1) - the value of the corresponding instance
				                of sleMfdbMacAddress will be flooded.
				"
			::= { sleMfdbEntry 2 }

		
		sleMfdbVlanIndex OBJECT-TYPE
			SYNTAX INTEGER (0 | 1..4094)
			MAX-ACCESS read-only
			STATUS current
			DESCRIPTION
				"vlan index
				"
			::= { sleMfdbEntry 3 }

		
		sleMfdbPorts OBJECT-TYPE
			SYNTAX OCTET STRING (SIZE (0..32))
			MAX-ACCESS read-write
			STATUS current
			DESCRIPTION
				"Port Map"
			::= { sleMfdbEntry 4 }

		
--  1.3.6.1.4.1.6296.9.8.14.2
		sleMfdbControl OBJECT IDENTIFIER ::= { sleMfdb 2 }

		
--  1.3.6.1.4.1.6296.9.8.14.2.1
		sleMfdbControlRequest OBJECT-TYPE
			SYNTAX INTEGER
				{
				createMfdbEntry(1),
				destoryMfdbEntry(2),
				setMfdbEntryPermission(3),
				clearMfdbEntryTable(4)
				}
			MAX-ACCESS read-write
			STATUS current
			DESCRIPTION
				" The request of a user command"
			::= { sleMfdbControl 1 }

		
--  1.3.6.1.4.1.6296.9.8.14.2.2
		sleMfdbControlStatus OBJECT-TYPE
			SYNTAX SleControlStatusType
			MAX-ACCESS read-only
			STATUS current
			DESCRIPTION
				" The status of user command"
			::= { sleMfdbControl 2 }

		
--  1.3.6.1.4.1.6296.9.8.14.2.3
		sleMfdbControlTimer OBJECT-TYPE
			SYNTAX Gauge32
			MAX-ACCESS read-write
			STATUS current
			DESCRIPTION
				" The maximum time for the manager for a long running user command"
			::= { sleMfdbControl 3 }

		
--  1.3.6.1.4.1.6296.9.8.14.2.5
		sleMfdbControlTimeStamp OBJECT-TYPE
			SYNTAX TimeTicks
			MAX-ACCESS read-only
			STATUS current
			DESCRIPTION
				" The time stamp of the last command(end of command)"
			::= { sleMfdbControl 4 }

		
--  1.3.6.1.4.1.6296.9.8.14.2.4
		sleMfdbControlReqResult OBJECT-TYPE
			SYNTAX SleControlRequestResultType
			MAX-ACCESS read-only
			STATUS current
			DESCRIPTION
				" The result of the last user command"
			::= { sleMfdbControl 5 }

		
--  1.3.6.1.4.1.6296.9.8.14.2.6
		sleMfdbControlMacAddress OBJECT-TYPE
			SYNTAX OCTET STRING (SIZE (0..6))
			MAX-ACCESS read-write
			STATUS current
			DESCRIPTION
				"A unicast MAC address for which the device has
				forwarding or filtering information.
				  If MAC address is NULL apply mac-filter list 
				  from file '/etc/mfdb.conf'."
			::= { sleMfdbControl 6 }

		
--  1.3.6.1.4.1.6296.9.8.14.2.7
		sleMfdbControlEntryPermission OBJECT-TYPE
			SYNTAX INTEGER
				{
				deny(0),
				permit(1)
				}
			MAX-ACCESS read-write
			STATUS current
			DESCRIPTION
				"The permission of sleMFdbControlMacAddress."
			::= { sleMfdbControl 7 }

		
		sleMfdbControlVlanIndex OBJECT-TYPE
			SYNTAX INTEGER (0 | 1..4094)
			MAX-ACCESS read-write
			STATUS current
			DESCRIPTION
				"vlan index
				The value of 0 is all vlan"
			::= { sleMfdbControl 8 }

		
		sleMfdbControlPorts OBJECT-TYPE
			SYNTAX OCTET STRING (SIZE (0..32))
			MAX-ACCESS read-write
			STATUS current
			DESCRIPTION
				"Port Map 
				The value of 0x00 is all port
				"
			::= { sleMfdbControl 9 }

		
--  1.3.6.1.4.1.6296.9.8.14.3
		sleMfdbNotification OBJECT IDENTIFIER ::= { sleMfdb 3 }

		
--  1.3.6.1.4.1.6296.9.8.14.3.1
		sleMfdbEntryCreated NOTIFICATION-TYPE
			OBJECTS { sleMfdbControlRequest, sleMfdbControlReqResult, sleMfdbControlTimeStamp, sleMfdbControlMacAddress, sleMfdbControlVlanIndex
				 }
			STATUS current
			DESCRIPTION 
				"Create new MFDB entry."
			::= { sleMfdbNotification 1 }

		
--  1.3.6.1.4.1.6296.9.8.14.3.2
		sleMfdbEntryDestoryed NOTIFICATION-TYPE
			OBJECTS { sleMfdbControlRequest, sleMfdbControlReqResult, sleMfdbControlTimeStamp, sleMfdbControlMacAddress, sleMfdbControlVlanIndex
				 }
			STATUS current
			DESCRIPTION 
				"Destroyed MFDB entry."
			::= { sleMfdbNotification 2 }

		
--  1.3.6.1.4.1.6296.9.8.14.3.3
		sleMfdbEntryPermissionChanged NOTIFICATION-TYPE
			OBJECTS { sleMfdbControlRequest, sleMfdbControlReqResult, sleMfdbControlTimeStamp, sleMfdbControlEntryPermission }
			STATUS current
			DESCRIPTION 
				"Changed permission of MFDB entry."
			::= { sleMfdbNotification 3 }

		
		sleMfdbEntryTableCleared NOTIFICATION-TYPE
			OBJECTS { sleMfdbControlRequest, sleMfdbControlReqResult, sleMfdbControlTimeStamp }
			STATUS current
			DESCRIPTION 
				"Description."
			::= { sleMfdbNotification 4 }

		
		sleBridgeGroup OBJECT-GROUP
			OBJECTS { sleBridgeMacAddress, sleBridgePortNum, sleBridgeLagMaxId, sleBridgeLacpActivity, sleBridgeLacpPriority, 
				sleBridgeVlanSupportMode, sleBridgeVlanMaxNum, sleBridgeDoubleTagProtoId, sleBridgeMirrorMode, sleBridgeMirrorMonitorPortId, 
				sleBridgeMirroredIngressPorts, sleBridgeMirroredEgressPorts, sleBridgeMaxLearnPerUnit, sleBridgeFdbAgeingTime, sleBridgeFdbMaxEntries, 
				sleBridgeFdbCurrentEntries, sleBridgeStackMode, sleBridgeStackDeviceName, sleBridgeStackNodeId, sleBridgeLldpMessageTxInterval, 
				sleBridgeLldpTxHoldMultiplier, sleBridgeLldpReinitDelay, sleBridgeLldpTxDelay, sleBridgeLldpNotificationInterval, sleBridgeLldpStatsRemTablesLastChangeTime, 
				sleBridgeLldpStatsRemTablesInserts, sleBridgeLldpStatsRemTablesDeletes, sleBridgeLldpStatsRemTablesDrops, sleBridgeLldpStatsRemTablesAgeouts, sleBridgeLldpLocalChassisIdSubtype, 
				sleBridgeLldpLocalChassisId, sleBridgeLldpLocalSysName, sleBridgeLldpLocalSysDes, sleBridgeLldpLocalSysCapSupported, sleBridgeLldpLocalSysCapEnabled, 
				sleBridgeStpActivity, sleBridgeStpSelfLoop, sleBridgePvlanOnePromPortEnable, sleBridgeTcpSyncookie, sleBridgeTcpIgnoreRstUnknown, 
				sleBridgeControlRequest, sleBridgeControlStatus, sleBridgeControlTimer, sleBridgeControlTimeStamp, sleBridgeControlReqResult, 
				sleBridgeControlLacpActivity, sleBridgeControlLacpPriority, sleBridgeControlDoubleTagProtoId, sleBridgeControlMirrorMode, sleBridgeControlMirrorMonitorPortId, 
				sleBridgeControlMaxLearnPerUnit, sleBridgeControlFdbAgeingTime, sleBridgeControlStackMode, sleBridgeControlStackDeviceName, sleBridgeControlLldpMessageTxInterval, 
				sleBridgeControlLldpTxHoldMultiplier, sleBridgeControlLldpReinitDelay, sleBridgeControlLldpTxDelay, sleBridgeControlLldpNotificationInterval, sleBridgeControlStpActivity, 
				sleBridgeControlStpSelfLoop, sleBridgeControlTcpSyncookie, sleBridgeControlTcpIgnoreRstUnknown, sleBridgePortIndex, sleBridgePortIfIndex, 
				sleBridgePortPVid, sleBridgePortMaxHosts, sleBridgePortCurrentHosts, sleBridgePortMaxLearnPerUnit, sleBridgePortMACFilterPermission, 
				sleBridgePortIngMirrorStatus, sleBridgePortEgMirrorStatus, sleBridgePortBcastThreshold, sleBridgePortMcastThreshold, sleBridgePortDlfThreshold, 
				sleBridgePortQinQStatus, sleBridgePortAdminLinktype, sleBridgePortAdminEdgemode, sleBridgePortOperLinktype, sleBridgePortOperEdgemode, 
				sleBridgePortStpBpduFilter, sleBridgePortPvlanIsolatedStatus, sleBridgePortPvlanPromPorts, sleBridgePortControlRequest, sleBridgePortControlStatus, 
				sleBridgePortControlTimer, sleBridgePortControlTimeStamp, sleBridgePortControlReqResult, sleBridgePortControlIndex, sleBridgePortControlPVid, 
				sleBridgePortControlMaxHosts, sleBridgePortControlMaxLearnPerUnit, sleBridgePortControlMACFilterPermission, sleBridgePortControlIngMirrorStatus, sleBridgePortControlEgMirrorStatus, 
				sleBridgePortControlBcastThreshold, sleBridgePortControlMcastThreshold, sleBridgePortControlDlfThreshold, sleBridgePortControlQinQStatus, sleBridgePortControlAdminLinktype, 
				sleBridgePortControlAdminEdgemode, sleBridgePortControlStpBpduFilter, sleBridgePortControlPvlanIsolatedStatus, sleBridgePortControlPvlanPromPort, sleBridgePortControlStpBpduGuardErrRcv, 
				sleVlanIndex, sleVlanIfIndex, sleVlanName, sleVlanStatus, sleVlanEgressPorts, 
				sleVlanUnTaggedPorts, sleVlanCreationTime, sleVlanAgeingTime, sleVlanControlRequest, sleVlanControlStatus, 
				sleVlanControlTimer, sleVlanControlTimeStamp, sleVlanControlReqResult, sleVlanControlIndex, sleVlanControlName, 
				sleVlanControlEgressPorts, sleVlanControlUnTaggedPorts, sleVlanControlAgeingTime, sleVlanMapFid, sleVlanMapStpId, 
				sleVlanMapErpDomainId, sleVlanMapControlRequest, sleVlanMapControlStatus, sleVlanMapControlTimer, sleVlanMapControlTimeStamp, 
				sleVlanMapControlReqResult, sleVlanMapControlIndex, sleVlanMapControlFid, sleVlanMapControlStpId, sleVlanMapControlErpDomainId, 
				sleStpOperationMode, sleStpFormatSelector, sleStpConfigureName, sleStpRevisionLevel, sleStpFwdDelay, 
				sleStpHelloTime, sleStpMaxAge, sleStpMaxHops, sleStpExtRootBridgeId, sleStpExtPathcost, 
				sleStpBpduGuardMode, sleStpBpduGuardAutoRcvMode, sleStpBpduGuardAutoRcvTime, sleStpControlRequest, sleStpControlStatus, 
				sleStpControlTimer, sleStpControlTimeStamp, sleStpControlReqResult, sleStpControlOperationMode, sleStpControlConfigureName, 
				sleStpControlRevisionLevel, sleStpControlFwdDelay, sleStpControlHelloTime, sleStpControlMaxAge, sleStpControlMaxHops, 
				sleStpControlBpduGuardMode, sleStpControlBpduGuardAutoRcvMode, sleStpControlBpduGuardAutoRcvTime, sleStpInstanceIndex, sleStpInstanceEnable, 
				sleStpInstancePriority, sleStpInstanceRootBridgeId, sleStpInstanceRootPathcost, sleStpInstanceDesignatedBridgeId, sleStpInstanceDesignatedPortId, 
				sleStpInstanceRootPortId, sleStpInstanceFwdDelay, sleStpInstanceHelloTime, sleStpInstanceMaxAge, sleStpInstanceRemainHops, 
				sleStpInstanceBrFwdDelay, sleStpInstanceBrHelloTime, sleStpInstanceBrMaxAge, sleStpInstanceControlRequest, sleStpInstanceControlStatus, 
				sleStpInstanceControlTimer, sleStpInstanceControlTimeStamp, sleStpInstanceControlReqResult, sleStpInstanceControlIndex, sleStpInstanceControlEnable, 
				sleStpInstanceControlPriority, sleStpInstanceControlBrFwdDelay, sleStpInstanceControlBrHelloTime, sleStpInstanceControlBrMaxAge, sleStpInstancePortIndex, 
				sleStpInstancePortPathcost, sleStpInstancePortPriority, sleStpInstancePortRole, sleStpInstancePortState, sleStpInstancePortRootBridgeId, 
				sleStpInstancePortRootPathcost, sleStpInstancePortDesignateBridgeId, sleStpInstancePortDesignatePortId, sleStpInstancePortRootGuardMode, sleStpInstancePortControlRequest, 
				sleStpInstancePortControlStatus, sleStpInstancePortControlTimer, sleStpInstancePortControlTimeStamp, sleStpInstancePortControlReqResult, sleStpInstancePortControlIndex, 
				sleStpInstancePortControlInstanceId, sleStpInstancePortControlPathcost, sleStpInstancePortControlPriority, sleStpInstancePortControlRootGuardMode, sleSubnetVlanIp, 
				sleSubnetVlanMask, sleSubnetVlanVid, sleSubnetVlanControlRequest, sleSubnetVlanControlStatus, sleSubnetVlanControlTimer, 
				sleSubnetVlanControlTimeStamp, sleSubnetVlanControlReqResult, sleSubnetVlanControlIp, sleSubnetVlanControlMask, sleSubnetVlanControlVid, 
				sleProtocolVlanEtype, sleProtocolVlanVid, sleProtocolVlanControlRequest, sleProtocolVlanControlStatus, sleProtocolVlanControlTimer, 
				sleProtocolVlanControlTimeStamp, sleProtocolVlanControlReqResult, sleProtocolVlanControlPortIndex, sleProtocolVlanControlEtype, sleProtocolVlanControlVid, 
				sleLagIndex, sleLagPortId, sleLagDistMode, sleLagPortMap, sleLagMode, 
				sleLagControlRequest, sleLagControlStatus, sleLagControlTimer, sleLagControlTimeStamp, sleLagControlReqResult, 
				sleLagControlIndex, sleLagControlDistMode, sleLagControlPortMap, sleLagControlMode, sleLagLacpIndex, 
				sleLagLacpActorAggregatorKey, sleLagLacpActorSystemMAC, sleLagLacpPartnerSystemMAC, sleLagLacpPartnerSystemPriority, sleLagLacpPartnerAggregatorKey, 
				sleLagLacpPortIndex, sleLagLacpPortActivity, sleLagLacpPortActorPriority, sleLagLacpPortActorAggregatorId, sleLagLacpPortActorAdminKey, 
				sleLagLacpPortActorAdminState, sleLagLacpPortActorOperKey, sleLagLacpPortActorOperState, sleLagLacpPortPartnerAdminSystemMAC, sleLagLacpPortPartnerAdminSystemPriority, 
				sleLagLacpPortPartnerAdminKey, sleLagLacpPortPartnerAdminNum, sleLagLacpPortPartnerAdminPriority, sleLagLacpPortPartnerAdminState, sleLagLacpPortPartnerOperSystemMAC, 
				sleLagLacpPortPartnerOperSystemPriority, sleLagLacpPortPartnerOperKey, sleLagLacpPortPartnerOperNum, sleLagLacpPortPartnerOperPriority, sleLagLacpPortPartnerOperState, 
				sleLagLacpPortControlRequest, sleLagLacpPortControlStatus, sleLagLacpPortControlTimer, sleLagLacpPortControlTimeStamp, sleLagLacpPortControlReqResult, 
				sleLagLacpPortControlIndex, sleLagLacpPortControlActivity, sleLagLacpPortControlMode, sleLagLacpPortControlAdminKey, sleLagLacpPortControlAggregation, 
				sleLagLacpPortControlPriority, sleLagLacpPortControlTimeout, sleFdbEntryFid, sleFdbEntryPort, sleFdbEntryMacAddress, 
				sleFdbEntryVid, sleFdbEntryMode, sleFdbEntryPermission, sleFdbEntryElapsedTime, sleFdbEntryControlRequest, 
				sleFdbEntryControlStatus, sleFdbEntryControlTimer, sleFdbEntryControlTImeStamp, sleFdbEntryControlReqResult, sleFdbEntryControlFid, 
				sleFdbEntryControlPort, sleFdbEntryControlMacAddress, sleIgmpConfVlanIndex, sleIgmpConfEnable, sleIgmpConfMulticastFilter, 
				sleIgmpConfOutmostVlan, sleIgmpConfSnoopEnable, sleIgmpConfSnoopJoinDelay, sleIgmpConfSnoopQueryDelay, sleIgmpConfSnoopMrouter, 
				sleIgmpConfSnoopFastLeave, sleIgmpConfSnoopQuerier, sleIgmpConfControlRequest, sleIgmpConfControlStatus, sleIgmpConfControlTimer, 
				sleIgmpConfControlReqResult, sleIgmpConfControlTimeStamp, sleIgmpConfControlVlanIndex, sleIgmpConfControlEnable, sleIgmpConfControlMulticastFilter, 
				sleIgmpConfControlOutmostVlan, sleIgmpConfControlSnoopEnable, sleIgmpConfControlSnoopJoinDelay, sleIgmpConfControlSnoopQueryDelay, sleIgmpConfControlSnoopMrouter, 
				sleIgmpConfControlSnoopFastLeave, sleIgmpConfControlSnoopQuerier, sleIgmpMcastVlanIndex, sleIgmpMcastIPAddress, sleIgmpMcastPortIndex, 
				sleIgmpMcastType, sleIgmpMcastExpireTime, sleIgmpMcastControlReqest, sleIgmpMcastControlStatus, sleIgmpMcastControlTimer, 
				sleIgmpMcastControlTimeStamp, sleIgmpMcastControlReqResult, sleIgmpMcastControlVlanIndex, sleIgmpMcastControlIPAddress, sleIgmpMcastControlPortIndex, 
				sleStackDeviceMacAddress, sleStackDeviceNodeId, sleStackDeviceDescriptor, sleStackDeviceMode, sleStackDeviceStatus, 
				sleStackDeviceType, sleStackDeviceHostName, sleStackDevicePortNum, sleStackDeviceControlRequest, sleStackDeviceControlStatus, 
				sleStackDeviceControlTimer, sleStackDeviceControlTImeStamp, sleStackDeviceControlReqResult, sleStackDeviceControlMacAddress, sleStackDeviceControlDescriptor, 
				sleErpDomainIndex, sleErpDomainName, sleErpDomainPrimaryPort, sleErpDomainSecondaryPort, sleErpDomainBridgeRole, 
				sleErpDomainProtectionActivation, sleErpDomainOperatorRequest, sleErpDomainWaitToRestoreTime, sleErpDomainTestPacketInterval, sleErpDomainLearningDisabledTime, 
				sleErpDomainNodeStatus, sleErpDomainRingStatus, sleErpDomainLotp, sleErpDomainULotp, sleErpDomainMultipleRM, 
				sleErpDomainRMNodeReacheablility, sleErpDomainControlRequest, sleErpDomainControlStatus, sleErpDomainControlTimer, sleErpDomainControlTImeStamp, 
				sleErpDomainControlReqResult, sleErpDomainControlIndex, sleErpDomainControlName, sleErpDomainControlPrimaryPort, sleErpDomainControlSecondaryPort, 
				sleErpDomainControlBridgeRole, sleErpDomainControlProtectionActivation, sleErpDomainControlOperatorRequest, sleErpDomainControlWaitToRestoreTime, sleErpDomainControlTestPacketInterval, 
				sleErpDomainControlLearningDisabledTime, sleLldpPortIndex, sleLldpPortActivity, sleLldpPortAdminStatus, sleLldpPortNotificationEnable, 
				sleLldpPortTLVsTxEnable, sleLldpPortMgmtTxEnable, sleLldpPortMgmtAddress, sleLldpPortControlRequest, sleLldpPortControlStatus, 
				sleLldpPortControlTimer, sleLldpPortControlTimeStamp, sleLldpPortControlReqResult, sleLldpPortControlIndex, sleLldpPortControlActivity, 
				sleLldpPortControlAdminstatus, sleLldpPortControlNotificationEnable, sleLldpPortControlTLVsTxEnable, sleLldpPortControlMgmtTxEnable, sleLldpPortControlMgmtAddress, 
				sleLldpRemIndex, sleLldpRemTimeMark, sleLldpRemChassisIdSubtype, sleLldpRemChassisId, sleLldpRemPortIdSubtype, 
				sleLldpRemPortId, sleLldpRemPortDesc, sleLldpRemSysName, sleLldpRemSysDesc, sleLldpRemSysCapSupported, 
				sleLldpRemSysCapEnabled, sleLldpStatsTxPortFramesTotal, sleLldpStatsRxPortFramesDiscardedTotal, sleLldpStatsRxPortFramesErrors, sleLldpStatsRxPortFramesTotal, 
				sleLldpStatsRxPortTLVsDiscardedTotal, sleLldpStatsRxPortTLVsUnrecognizedTotal, sleLldpStatsRxPortAgeoutsTotal, sleLldpStatsControlRequest, sleLldpStatsControlStatus, 
				sleLldpStatsControlTimer, sleLldpStatsControlTimeStamp, sleLldpStatsControlReqResult, sleLldpStatsControlPortIndex, sleBridgePSIndex, 
				sleBridgePSStatus, sleBridgePSMaxCount, sleBridgePSCurrCount, sleBridgePSAgingType, sleBridgePSAgingTimer, 
				sleBridgePSAgingStatic, sleBridgePSViolation, sleBridgePSControlRequest, sleBridgePSControlStatus, sleBridgePSControlTimer, 
				sleBridgePSControlTimeStamp, sleBridgePSControlReqResult, sleBridgePSControlIndex, sleBridgePSControlPSStatus, sleBridgePSControlMaxCount, 
				sleBridgePSControlAgingType, sleBridgePSControlAgingTimer, sleBridgePSControlAgingStatic, sleBridgePScontrolViolation, sleBridgePSFdbPort, 
				sleBridgePSFdbVid, sleBridgePSFdbMacAddress, sleBridgePSFdbMode, sleBridgePSFdbElapsedTime, sleBridgePSFdbControlRequest, 
				sleBridgePSFdbControlStatus, sleBridgePSFdbControlTimer, sleBridgePSFdbControlTimeStamp, sleBridgePSFdbControlReqResult, sleBridgePSFdbControlPort, 
				sleBridgePSFdbControlVid, sleErpDomainControlRingPriority, sleErpDomainHoldOffTime, sleErpDomainRingPriority, sleErpDomainControlHoldOffTime, 
				sleErpDomainControlLotp, sleErpDomainControlULotp, sleErpDomainControlMultipleRM, sleErpDomainControlRMNodeReacheablility, sleBridgeFGBaseControlRequest, 
				sleBridgeFGBaseSfgdEnabled, sleBridgeFGBaseMfgdEnabled, sleBridgeFGBaseCfgdEnabled, sleBridgePSFdbControlMacAddress, sleBridgePortDhcpFilterServer, 
				sleBridgePortControlDhcpFilterServer, sleBridgeFGBaseControlStatus, sleBridgeFGBaseControlTimer, sleBridgeFGBaseControlTimeStamp, sleBridgeFGBaseControlReqResult, 
				sleBridgeFGBaseControlCfgdEnable, sleBridgeFGBaseControlSfgdEnable, sleBridgeFGPortControlRequest, sleBridgeFGPortControlStatus, sleBridgeFGPortControlTimer, 
				sleBridgeFGPortControlTimeStamp, sleBridgeFGPortControlReqResult, sleBridgeFGPortControlIndex, sleBridgeFGPortType, sleBridgeFGPortFrame, 
				sleBridgeFGPortBlocked, sleBridgeFGPortTimer, sleBridgeFGPortControlFrame, sleBridgeFGPortFrameType, sleBridgeFGPortControlBlock, 
				sleBridgeAutoInterfaceActivation, sleBridgeControlAutoInterfaceActivation, sleBridgeLoopDetectStatus, sleBridgeLoopDetectPacketType, sleBridgeControlLoopDetectStatus, 
				sleBridgeControlLoopDetectPacketType, sleBridgePortLoopDetectStatus, sleBridgePortLoopDetectBlock, sleBridgePortLoopDetectPeriod, sleBridgePortLoopDetectTimer, 
				sleBridgePortLoopDetectBlockStatus, sleBridgePortControlLoopDetectStatus, sleBridgePortControlLoopDetectBlock, sleBridgePortControlLoopDetectPeriod, sleBridgePortControlLoopDetectTimer, 
				sleBridgePvlanPromSelectMode, sleBridgePvlanPromiscuousPorts, sleBridgeControlPvlanPromSelectMode, sleBridgeControlPvlanPromiscuousPorts, sleBridgeVTServiceId, 
				sleBridgeVTSubscriberId, sleBridgeVTRuleMac, sleBridgeVTRuleVid, sleBridgeVTRuleRDirVid, sleBridgeVTRuleRDirPort, 
				sleBridgeVTRuleStatus, sleBridgeVTControlRequest, sleBridgeVTControlStatus, sleBridgeVTControlTimer, sleBridgeVTControlTimeStamp, 
				sleBridgeVTControlServerId, sleBridgeVTControlClientId, sleBridgeGvrpStatus, sleBridgeGmrpStatus, sleBridgeGarpTimerJoin, 
				sleBridgeGarpTimerLeave, sleBridgeGarpTimerLeaveAll, sleBridgeGarpBaseControlRequest, sleBridgeGarpBaseControlStatus, sleBridgeGarpBaseControlTimer, 
				sleBridgeGarpBaseControlTimeStamp, sleBridgeGarpBaseControlReqResult, sleBridgeGarpBaseControlGvrpStatus, sleBridgeGarpBaseControlGmrpStatus, sleBridgeGarpBaseControlTimerJoin, 
				sleBridgeGarpBaseControlTimerLeave, sleBridgeGarpBaseControlTimerLeaveAll, sleBridgeGarpAppPortIndex, sleBridgeGarpAppPortType, sleBridgeGarpAppPortStatus, 
				sleBridgeGarpAppPortFailedRegistrations, sleBridgeGarpAppPortLastPduOrigin, sleBridgeGarpAppPortRegistration, sleBridgeGarpAppPortApplicant, sleBridgeGarpAppPortFwdAll, 
				sleBridgeGarpAppPortTimerJoin, sleBridgeGarpAppPortTimerLeave, sleBridgeGarpAppPortTimerLeaveAll, sleBridgeGarpAppPortControlRequest, sleBridgeGarpAppPortControlStatus, 
				sleBridgeGarpAppPortControlTimer, sleBridgeGarpAppPortControlTimeStamp, sleBridgeGarpAppPortControlReqResult, sleBridgeGarpAppPortControlIndex, sleBridgeGarpAppPortControlType, 
				sleBridgeGarpAppPortControlPortStatus, sleBridgeGarpAppPortControlRegistration, sleBridgeGarpAppPortControlApplicant, sleBridgeGarpAppPortControlFwdAll, sleBridgeGarpAppPortControlTimerJoin, 
				sleBridgeGarpAppPortControlTimerLeave, sleBridgeGarpAppPortControlTimerLeaveAll, sleBridgeGarpStatsJoinEmptyReceived, sleBridgeGarpStatsJoinInReceived, sleBridgeGarpStatsLeaveInReceived, 
				sleBridgeGarpStatsLeaveEmptyReceived, sleBridgeGarpStatsLeaveAllReceived, sleBridgeGarpStatsJoinInTransmitted, sleBridgeGarpStatsEmptyTransmitted, sleBridgeGarpStatsLeaveInTransmitted, 
				sleBridgeGarpStatsLeaveEmptyTransmitted, sleBridgeGarpStatsControlRequest, sleBridgeGarpStatstControlStatus, sleBridgeGarpStatsControlTimer, sleBridgeGarpStatsControlTimeStamp, 
				sleBridgeGarpStatsControlReqResult, sleBridgeGarpStatsControlIndex, sleBridgeGarpStatsControlType, sleBridgeGmrpStaticVid, sleBridgeGmrpStaticPort, 
				sleBridgeGmrpStaticGmac, sleBridgeGmrpStaticControlRequest, sleBridgeGmrpStaticControlStatus, sleBridgeGmrpStaticControlTimer, sleBridgeGmrpStaticControlTimeStamp, 
				sleBridgeGmrpStaticControlReqResult, sleBridgeGmrpStaticControlVid, sleBridgeGmrpStaticControlPort, sleBridgeGmrpStaticControlGmac, sleBridgePortNetBIOSFilter, 
				sleBridgePortControlNetBIOSFilter, sleBridgePortPopInnertag, sleBridgePortInnertag, sleBridgePortPriority, sleBridgePortControlPushInnertag, 
				sleBridgePortControlPopInnertag, sleBridgePortControlInnertag, sleBridgePortControlPriority, sleBridgePortPushInnertag, sleVlanInboundTagPortIndex, 
				sleVlanInboundTagVlanIndex, sleVlanInboundTagOuterVid, sleVlanInboundTagControlRequest, sleVlanInboundTagControlStatus, sleVlanInboundTagControlTimer, 
				sleVlanInboundTagControlTimeStamp, sleVlanInboundTagControlReqResult, sleVlanInboundTagControlPortIndex, sleVlanInboundTagControlVlanIndex, sleVlanInboundTagControlOuterVid, 
				sleVlanOutboundTagPortIndex, sleVlanOutboundTagControlRequest, sleVlanOutboundTagControlStatus, sleVlanOutboundTagControlTimer, sleVlanOutboundTagControlTimeStamp, 
				sleVlanOutboundTagControlReqResult, sleVlanOutboundTagControlPortIndex, sleVlanOutboundTagControlOuterVid, sleVlanOutboundTagVlanIndex, sleBridgePortInner2outerVid, 
				sleBridgePortInner2outerPri, sleBridgeFGPortControlFrameType, sleBridgeFGPortControlType, sleBridgeFGPortControlSetTimer, sleBridgeGarpStatsEmptyReceived, 
				sleBridgeGarpStatsJoinEmptyTransmitted, sleIgmpMcastCounterInfoGroupCount, sleIgmpMcastCounterInfoSnoopingCount, sleMcastMrouteJoinedCount, sleBridgePortLinkUpCnt, 
				sleBridgePortLinkDownCnt, sleBridgePortLinkUpTime, sleBridgePortElapsedTimeAfterClearStats, sleVlanTagTxCounter, sleBridgePortMACLearningStatus, 
				sleBridgePortPortBridgeStatus, sleBridgePortControlMACLearningStatus, sleBridgePortControlPortBridgeStatus, sleBridgeInBoundVTPortIndex, sleBridgeInBoundVTNewVid, 
				sleBridgeInBoundVTControlRequest, sleBridgeInBoundVTControlStatus, sleBridgeInBoundVTControlTimer, sleBridgeInBoundVTControlTimeStamp, sleBridgeInBoundVTControlReqResult, 
				sleBridgeInBoundVTControlPortIndex, sleBridgeInBoundVTControlNewVid, sleBridgeGarpStatsLeaveAllTransmitted, sleBridgePortControlInner2outerPri, sleBridgeInBoundVTVlanIndex, 
				sleBridgeInBoundVTOperStatus, sleBridgeInBoundVTControlVlanIndex, sleVlanInboundTagOperStatus, sleVlanOutboundTagOperStatus, sleVlanRangeInboundTagOperStatus, 
				sleVlanControlIndexTo, sleBridgeUnknownMcastBlockAllPorts, sleBridgeControlUnknownMcastBlockAllPorts, sleBridgePortUnknownMcastBlock, sleBridgePortControlUnknownMcastBlock, 
				sleBridgeEcmpHashType, sleBridgeControlEcmpHashType, sleBridgeTcpSynguard, sleBridgeControlTcpSynguard, sleBridgePortDescription, 
				sleBridgePortHoldTime, sleBridgePortControlDescription, sleBridgePortControlHoldTime, sleLagLacpStatsPduReceived, sleLagLacpStatsPduReceivedErrrors, 
				sleLagLacpStatsPduSent, sleLagLacpStatsPduSentError, sleLagLacpStatsMarkerReceived, sleLagLacpStatsMarkerSent, sleLagLacpStatsMarkerSentError, 
				sleLagLacpControlRequest, sleLagLacpControlStatus, sleLagLacpControlTimer, sleLagLacpControlTimeStamp, sleLagLacpControlReqResult, 
				sleBridgeOuterTagProtoId, sleBridgeControlOuterTagProtoId, sleBridgeOutBoundVTPortIndex, sleBridgeOutBoundVTVlanIndex, sleBridgeOutBoundVTNewVid, 
				sleBridgeOutBoundVTOperStatus, sleBridgeOutBoundVTControlRequest, sleBridgeOutBoundVTControlStatus, sleBridgeOutBoundVTControlTimer, sleBridgeOutBoundVTControlTimeStamp, 
				sleBridgeOutBoundVTControlReqResult, sleBridgeOutBoundVTControlPortIndex, sleBridgeOutBoundVTControlVlanIndex, sleBridgeOutBoundVTControlNewVid, sleBridgeMacAntiSpoofing, 
				sleBridgeMacReplace, sleBridgeControlMacAntiSpoofing, sleBridgeControlMacReplace, sleBridgePortMacAntiSpoofing, sleBridgePortControlMacAntiSpoofing, 
				sleVlanProtoIdVid, sleVlanProtoIdOuterProtoId, sleVlanProtoIdControlRequest, sleVlanProtoIdControlStatus, sleVlanProtoIdControlTimer, 
				sleVlanProtoIdControlTimeStamp, sleVlanProtoIdControlReqResult, sleVlanProtoIdControlVid, sleVlanProtoIdControlOuterProtoId, sleBridgeStormControlBcast, 
				sleBridgeStormControlDLF, sleBridgeStormControlMulticast, sleBridgeControlStormControlBcast, sleBridgeControlStormControlDLF, sleBridgeControlStormControlMulticast, 
				sleVlanMappingIndex, sleVlanMappingPortId, sleVlanMappingOriVlanId, sleVlanMappingTransVlanId, sleVlanMappingMode, 
				sleVlanMappingMatchCos, sleVlanMappingMatchDscp, sleVlanMappingMatchEthType, sleVlanMappingMatchIPPrecedence, sleVlanMappingMatchTos, 
				sleVlanMappingRateLimit, sleVlanMappingCos, sleVlanMappingDscp, sleVlanMappingControlRequest, sleVlanMappingControlStatus, 
				sleVlanMappingControlTimer, sleVlanMappingControlTimeStamp, sleVlanMappingControlReqResult, sleVlanMappingControlPortId, sleVlanMappingControlOriVlanId, 
				sleVlanMappingControlTransVlanID, sleVlanMappingControlMode, sleVlanMappingControlMatchCos, sleVlanMappingControlMatchDscp, sleVlanMappingControlMatchEthType, 
				sleVlanMappingControlMatchIPPrecedence, sleVlanMappingControlMatchTos, sleVlanMappingControlRateLimit, sleVlanMappingControlCos, sleVlanMappingControlDscp, 
				sleVlanMappingControlIndex, sleBridgeMacLearningMode, sleBridgeControlMacLearningMode, sleLldpRemManAddrSubType, sleLldpRemManAddr, 
				sleLldpRemManAddrIfSubType, sleLldpRemManAddrIfId, sleLldpRemAddrOid, sleBridgeLagGlobalDistMode, sleBridgeControlLagGlobalDistMode, 
				sleVlanDescription, sleVlanControlDescription, sleVlanElineEnable, sleVlanControlElineEnable, sleBridgePortSwitchType, 
				sleBridgePortSwitchState, sleBridgePortSwitchMode, sleBridgePortSwitchSubMode, sleBridgePortSwitchDefaultVlan, sleBridgePortSwitchIngressFilter, 
				sleBridgePortSwitchAccFrameType, sleBridgePortSwitchNativeVid, sleBridgePortSwitchAllowedVlan, sleBridgePortSwitchAllowedVlanEtag, sleBridgePortControlSwitchStatus, 
				sleBridgePortControlSwitchMode, sleBridgePortControlSwitchSubMode, sleBridgePortControlSwitchDefaultVlan, sleBridgePortControlSwitchIngressFilter, sleBridgePortControlSwitchAccFrameType, 
				sleBridgePortControlSwitchNativeVid, sleBridgePortControlSwitchAllowedVlan, sleBridgePortControlSwitchAllowedVlanEtag, sleBridgePortControlInner2outerVid, sleBridgeInnerTagProtoId, 
				sleBridgeControlInnerTagProtoId, sleBridgeVTControlReqResult, sleVlanRangeInboundTagPortIndex, sleVlanRangeInboundTagMinVlanIndex, sleVlanRangeInboundTagMaxVlanIndex, 
				sleVlanRangeInboundTagOuterVid, sleVlanRangeInboundTagControlRequest, sleVlanRangeInboundTagControlStatus, sleVlanRangeInboundTagControlTimer, sleVlanRangeInboundTagControlTimeStamp, 
				sleVlanRangeInboundTagControlReqResult, sleVlanRangeInboundTagControlPortIndex, sleVlanRangeInboundTagControlMinVlanIndex, sleVlanRangeInboundTagControlMaxVlanIndex, sleBridgeMultiPortLlcfPortAStatus, 
				sleBridgeMultiPortLlcfPortBStatus, sleVlanRangeInboundTagControlOuterVid, sleBridgeMultiPortLlcfPortA, sleBridgeMultiPortLlcfPortB, sleBridgeMultiPortLlcfTimer, 
				sleBridgeControlMultiPortLlcfPortA, sleBridgeControlMultiPortLlcfPortB, sleBridgeControlMultiPortLlcfPortC, sleVlanOperStatus, sleVlanMtu, 
				sleVlanControlOperStatus, sleVlanControlMtu, sleBridgePortSwitchChannelType, sleBridgePortSwitchStaticChannelGroup, sleBridgePortSwitchChannelLoadbalance, 
				sleBridgePortControlSwitchStaticChannelGroup, sleBridgePortControlSwitchChannelLoadbalance, sleVlanInboundTagVlanPriority, sleVlanInboundTagOuterVlanPriority, sleVlanInboundTagControlVlanPriority, 
				sleVlanInboundTagControlOuterVlanPriority, slePowerInlinePortIndex, slePowerInlineAdminStatus, slePowerInlinePortStatus, slePowerInlineDetectionStatus, 
				slePowerInlinePortClass, slePowerInlinePortMaxPow, slePowerInlinePortLegacy, slePowerInlinePortPriority, slePowerInlinePortPower, 
				slePowerInlinePortCurrent, slePowerInlinePortVoltage, slePowerInlinePortTemperture, slePowerInlineControlRequest, slePowerInlineControlStatus, 
				slePowerInlineControlTimer, slePowerInlineControlTimeStamp, slePowerInlineControlReqResult, slePowerInlineControlPortIndex, slePowerInlineControlPortStatus, 
				slePowerInlineControlPortClass, slePowerInlineControlPortMaxPower, slePowerInlineControlPortLegacy, slePowerInlineControlPriority, slePowerInlineControlAdminStatus, 
				sleLagLeastActive, sleLagControlLeastActive, sleMfdbOldMacAddress, sleMfdbOldEntryPermission, sleMfdbOldVlanIndex, 
				sleMfdbOldPorts, sleMfdbOldControlRequest, sleMfdbOldControlStatus, sleMfdbOldControlTimer, sleMfdbOldControlTimeStamp, 
				sleMfdbOldControlReqResult, sleMfdbOldControlMacAddress, sleMfdbOldControlEntryPermission, sleMfdbOldControlVlanIndex, sleMfdbOldControlPorts, 
				sleMfdbMacAddress, sleMfdbEntryPermission, sleMfdbVlanIndex, sleMfdbPorts, sleMfdbControlRequest, 
				sleMfdbControlStatus, sleMfdbControlTimer, sleMfdbControlTimeStamp, sleMfdbControlReqResult, sleMfdbControlMacAddress, 
				sleMfdbControlEntryPermission, sleMfdbControlVlanIndex, sleMfdbControlPorts, sleBridgeControlMultiPortLlcfTimer, sleBridgeMultiPortLlcfUpPortC, 
				sleBridgeMultiPortLlcfDownPortC, sleBridgeMultiPortLlcfUpPortCStatus, sleBridgeMultiPortLlcfDownPortCStatus }
			STATUS current
			DESCRIPTION 
				"Description."
			::= { sleBridge 31 }

		
		sleBridgeNotificationGroup NOTIFICATION-GROUP
			NOTIFICATIONS { sleBridgeLacpProfileChanged, sleBridgeDoubleTagProtoIdChanged, sleBridgeMirrorProfileChanged, sleBridgeMaxLearnPerUnitChanged, sleBridgeFdbAgeingTimeChanged, 
				sleBridgeStackProfileChanged, sleBridgeLldpProfileChanged, sleBridgeTcpSyncookieChanged, sleBridgeTcpIgnoreRstUnknownChanged, sleBridgePortPVidChanged, 
				sleBridgePortMaxHostsChanged, sleBridgePortMaxLearnPerUnitChanged, sleBridgePortMACFilterPermissionChanged, sleBridgePortMirrorProfileChanged, sleBridgePortBcscThresholdProfileChanged, 
				sleBridgePortQinQStatusChanged, sleBridgePortLinktypeChanged, sleBridgePortEdgemodeChanged, sleBridgePortStpBpduFilterChanged, sleBridgePortPvlanIsolatedStatusChanged, 
				sleVlanCreated, sleVlanDestroyed, sleVlanPortProfileChanged, sleVlanAgeingTimeChanged, sleVlanMapFidChanged, 
				sleVlanMapStpIdChanged, sleVlanMapErpDomainIdChanged, sleStpOperationModeChanged, sleStpConfigureProfileChanged, sleStpTimerProfileChanged, 
				sleStpBpduGuardProfileChanged, sleStpInstanceEnableChanged, sleStpInstanceConfigProfileChanged, sleStpInstancePortProfileChanged, sleSubnetVlanCreated, 
				sleSubnetVlanDestroyed, sleProtocolVlanCreated, sleProtocolVlanDestroyed, sleLagProfileChanged, sleLagLacpPortProfileChanged, 
				sleLagLacpPortAggreChanged, sleFdbEntryCreated, sleFdbEntryDestoryed, sleFdbTableEntriesCleared, sleMfdbEntryCreated, 
				sleMfdbEntryDestoryed, sleMfdbEntryPermissionChanged, sleMfdbEntryTableCleared, sleIgmpConfProfileChanged, sleIgmpStaticMcastCreated, 
				sleIgmpStaticMcastDestroyed, sleStackDeviceCreated, sleStackDeviceDestoryed, sleErpDomainCreated, sleErpDomainDestroyed, 
				sleErpDomainProfileChanged, sleErpProtectionActivationChanged, sleLldpPortProfileChanged, sleLldpStatisticsCleared, sleBridgePSStatusChanged, 
				sleBridgePSMaxCountChanged, sleBridgePSProfileChanged, sleBridgePSFdbEntryCreated, sleBridgePSFdbEntryDestroyed, sleBridgePortStpBpduGuardErrRcvChanged, 
				sleErpHoldOffTimeChanged, sleErpRingPriorityChanged, sleErpTrapChanged, sleBridgeFGBaseCfgdStatusChanged, sleBridgeAutoInterfaceActivationChanged, 
				sleBridgeFGPortUnblockChanged, sleBridgeFGPortProfileChanged, sleBridgeLoopDetectProfileChanged, sleBridgePortLoopDetectProfileChanged, sleBridgePortLoopDetectUnblock, 
				sleBridgePvlanPormSelectModeChanged, sleBridgeVTSet, sleBridgeVTClear, sleBridgeGarpStatusChanged, sleBridgeGarpTimerChanged, 
				sleBridgeGarpAppPortStatusChanged, sleBridgeGarpAppPortProfileChanged, sleBridgeGarpStatisticsCleared, sleBridgeGmrpStaticAdded, sleBridgeGmrpStaticDeleted, 
				sleBridgePortNetBIOSFilterChanged, sleBridgePortPriorityChanged, sleBridgePortInnertagChanged, sleBridgePortPopInnertagChanged, sleBridgePortPushInnertagChanged, 
				sleVlanInboundTagChanged, sleVlanOutboundTagSet, sleVlanOutboundTagClear, sleBridgePortInner2outerVidChanged, sleBridgePortInner2outerPriChanged, 
				sleBridgePSFdbEntryCleared, sleBridgePortDhcpFilterServerChanged, sleBridgePortMACLearningStatusChanged, sleBridgePortPortBridgeStatusChanged, sleBridgeInBoundVTSet, 
				sleBridgeInBoundVTClear, sleBridgeInnerTagProtoIdChanged, sleVlanInboundTagCleared, sleVlanRangeInboundTagChanged, sleVlanRangeInboundTagCleared, 
				sleVlanRangeCreated, sleBridgeUnknownMcastBlockAllPortsChanged, sleBridgePortUnknownMcastBlockChanged, sleBridgeEcmpHashTypeChanged, sleBridgeTcpSynguardChanged, 
				sleBridgePortDescriptionChanged, sleBridgePortHoldTimeChanged, sleLagLacpStatsCleared, sleBridgeOuterTagProtoIdChanged, sleBridgeOutBoundVTSet, 
				sleBridgeOutBoundVTClear, sleBridgeMacAntiSpoofingChanged, sleBridgeMacReplaceChanged, sleBridgePortMacAntiSpoofChanged, sleVlanProtoIdOuterProtoIdChanged, 
				sleBridgeStormControlChanged, sleVlanMappingCreated, sleVlanMappingDeleted, sleBridgeMacLearningModeChanged, sleBridgeLagGlobalDistModeChanged, 
				sleVlanDescriptionChanged, sleVlanElineVlanCreated, sleBridgePortSwitchStatusChanged, sleBridgePortSwitchModeChanged, sleBridgePortSwitchDefaultVlanChanged, 
				sleBridgePortSwitchNativeVlanChanged, sleBridgePortSwitchAccFramTypeChanged, sleBridgePortSwitchAllowdVlanAdded, sleBridgePortSwitchAllowdVlanDeleted, sleVlanOperStatusChagned, 
				sleVlanMtuChagned, sleBridgePortSwitchStaticChannelChanged, sleBridgePortSwitchChannelLoadbalanceChanged, slePowerInlineEnableChanged, slePowerInlineDisableChanged, 
				slePowerInlineResetChanged, slePowerInlineLegacyChanged, slePowerInlinePriorityChanged, slePowerInlineClassChanged, slePowerInlinePowerChanged, 
				sleMfdbOldEntryCreated, sleMfdbOldEntryDestoryed, sleMfdbOldEntryPermissionChanged, sleMfdbOldEntryTableCleared, sleBridgeFGBaseSfgdStatusChanged, 
				sleBridgeStpProfileChanged, sleBridgeMultiPortLlcfChanged, sleBridgeMultiPortLlcfDeleted, sleBridgeMultiPortLlcfTimerChanged }
			STATUS current
			DESCRIPTION 
				"Description."
			::= { sleBridge 32 }

		
	
	END

--
-- sle-bridge-mib.mib
--
