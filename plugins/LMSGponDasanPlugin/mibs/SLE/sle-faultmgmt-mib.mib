--
-- SLE-FAULTMGMT-MIB.my
-- MIB generated by MG-SOFT Visual MIB Builder Version 6.0  Build 88
-- Tuesday, November 19, 2013 at 11:02:43
--

--  SLE-FAULTMGMT-MIB.my
-- MIB generated by MG-SOFT Visual MIB Builder Version 6.0  Build 88
-- Tuesday, September 24, 2013 at 13:45:01
-- 
--  SLE-FAULTMGMT-MIB.mib
-- MIB generated by MG-SOFT Visual MIB Builder 2010 Version 8.0  Build 400
-- Friday, September 14, 2012 at 17:24:23
-- 

	SLE-FAULTMGMT-MIB DEFINITIONS ::= BEGIN
 
		IMPORTS
			sleMgmt			
				FROM DASAN-SMI			
			SleControlStatusType, SleControlRequestResultType			
				FROM SLE-TC-MIB			
			OBJECT-GROUP, NOTIFICATION-GROUP			
				FROM SNMPv2-CONF			
			TimeTicks, IpAddress, Integer32, Unsigned32, Gauge32, 
			Counter32, Counter64, BITS, OBJECT-TYPE, MODULE-IDENTITY, 
			NOTIFICATION-TYPE			
				FROM SNMPv2-SMI			
			MacAddress, TimeStamp, TEXTUAL-CONVENTION			
				FROM SNMPv2-TC;
	
	
--   1.3.6.1.4.1.6296.101.4
-- August 13, 2010 at 00:00 GMT
-- December 08, 1904 at 00:00 GMT
-- 1.3.6.1.4.1.6296.101.4
-- August 13, 2010 at 00:00 GMT
-- December 08, 1904 at 00:00 GMT
		-- 1.3.6.1.4.1.6296.101.4
		sleFaultMgmt MODULE-IDENTITY 
			LAST-UPDATED "201008130000Z"		-- August 13, 2010 at 00:00 GMT
			ORGANIZATION 
				" DASAN Networks"
			CONTACT-INFO 
				"
				"
			DESCRIPTION 
				"The MIB module representing multiple logical
				entities for the SLE alarm management. "
			REVISION "190412080000Z"		-- December 08, 1904 at 00:00 GMT
			DESCRIPTION 
				" "
			::= { sleMgmt 4 }

		
	
--
-- Textual conventions
--
	
--  Textual conventions
-- 
		SpecificNum ::= TEXTUAL-CONVENTION
			STATUS current
			DESCRIPTION 
				"Description."
			SYNTAX INTEGER
				{
				portDown(1),
				portUp(2),
				portRemoved(3),
				portInstalled(4),
				powerFail(5),
				powerOK(6),
				powerRemoved(7),
				powerInstalled(8),
				fanFail(9),
				fanOK(10),
				fanRemoved(11),
				fanInstalled(12),
				moduleRemoved(13),
				moduleInstalled(14),
				systemRestart(15),
				systemStart(16),
				broadcastOver(17),
				broadcastUnder(18),
				cpuOverLoad(19),
				cpuUnderLoad(20),
				memoryOverUsed(21),
				memoryUnderUsed(22),
				portOverThreshold(23),
				portUnderThreshold(24),
				temperatureHigh(25),
				temperatureLow(26),
				mfgdBlocked(27),
				mfgdReleased(28),
				ipConflict(29),
				ipUnconflict(30),
				dhcpLeaseShortage(31),
				dhcpLeaseSufficient(32),
				dhcpOccuredIllegalEntry(33),
				dhcpRemovedIllegalEntry(34),
				rmonAlarmRising(35),
				rmonAlarmNoRising(36),
				rmonAlarmFalling(37),
				rmonAlarmNoFalling(38),
				bpduGuardDisabled(39),
				rootGuardDisabled(40),
				portSecurity(41),
				userLogin(42),
				userLogout(43),
				systemWarmStart(44),
				igmpGroupJoined(51),
				igmpGroupLeaved(52),
				dhcpIpaddressBound(53),
				dhcpIpaddressFree(54),
				doorOpened(55),
				doorClosed(56),
				powerModeChangedPowerToBattery(57),
				powerModeChangedBatteryToPower(58),
				batterylowcapacity(59),
				batterynormalcapacity(60),
				batteryhighTemperature(61),
				batterynormalTemperature(62),
				authenticationFail(63),
				authenticationNoFail(64),
				psuAcHighTemperature(65),
				psuAcNormalTemperature(66),
				batteryRemoved(67),
				batteryEquipped(68),
				batteryLowVoltage(69),
				batteryNormalVoltage(70),
				adminAccessLogin(71),
				adminAccessLogout(72),
				cfgdBlocked(73),
				cfgdReleased(74),
				sfgdBlocked(75),
				sfgdReleased(76),
				swWatchdogAbnomalState(77),
				swWatchdogNomalState(78),
				swWatchdogDetectError(79),
				swWatchdogClearError(80),
				ppsControlBlocked(81),
				ppsControlReleased(82),
				gotDMITempHighOverAlarm(83),
				gotDMITempHighFallAlarm(84),
				gotDMITempLowOverAlarm(85),
				gotDMITempLowFallAlarm(86),
				gotDMITempHighOverWarning(87),
				gotDMITempHighFallWarning(88),
				gotDMITempLowOverWarning(89),
				gotDMITempLowFallWarning(90),
				gotDMIVolHighOverAlarm(91),
				gotDMIVolHighFallAlarm(92),
				gotDMIVolLowOverAlarm(93),
				gotDMIVolLowFallAlarm(94),
				gotDMIVolHighOverWarning(95),
				gotDMIVolHighFallWarning(96),
				gotDMIVolLowOverWarning(97),
				gotDMIVolLowFallWarning(98),
				gotDMITxBiasHighOverAlarm(99),
				gotDMITxBiasHighFallAlarm(100),
				gotDMITxBiasLowOverAlarm(101),
				gotDMITxBiasLowFallAlarm(102),
				gotDMITxBiasHighOverWarning(103),
				gotDMITxBiasHighFallWarning(104),
				gotDMITxBiasLowOverWarning(105),
				gotDMITxBiasLowFallWarning(106),
				gotDMITxPowerHighOverAlarm(107),
				gotDMITxPowerHighFallAlarm(108),
				gotDMITxPowerLowOverAlarm(109),
				gotDMITxPowerLowFallAlarm(110),
				gotDMITxPowerHighOverWarning(111),
				gotDMITxPowerHighFallWarning(112),
				gotDMITxPowerLowOverWarning(113),
				gotDMITxPowerLowFallWarning(114),
				gotDMIRxPowerHighOverAlarm(115),
				gotDMIRxPowerHighFallAlarm(116),
				gotDMIRxPowerLowOverAlarm(117),
				gotDMIRxPowerLowFallAlarm(118),
				gotDMIRxPowerHighOverWarning(119),
				gotDMIRxPowerHighFallWarning(120),
				gotDMIRxPowerLowOverWarning(121),
				gotDMIRxPowerLowFallWarning(122),
				nosRemoteUpgradeRequest(123),
				nosRemoteUpgradeSuccess(124),
				nosRemoteUpgradeFailAbort(125),
				nosRemoteUpgradeFailHeaderError(126),
				nosRemoteUpgradeFailDownloadError(127),
				nosRemoteUpgradeFailFlashError(128),
				nosRemoteUpgradeStart(129),
				systemDyingGasp(130),
				remoteOamDyingGasp(131),
				remoteOamDyingGaspRestoration(132),
				cliHistory(133),
				cliHistoryNo(134),
				ntpConnectionFail(135),
				nmsConnectionTypeChanged(137),
				fanSpeedFallUnderThreshold(138),
				fanSpeedRisingOverThreshold(139),
				userLoginFail(140),
				swWatchdogInetAbnormalState(150),
				swWatchdogInetNormalState(151),
				swWatchdogInetDetectError(152),
				swWatchdogInetClearError(153),
				swWatchdogPonAbnormalState(154),
				swWatchdogPonNormalState(155),
				swWatchdogPonDetectError(156),
				swWatchdogPonClearError(157),
				arpInspectInvalid(158),
				clockModuleRemoved(159),
				clockModuleInstalled(160),
				clockModuleInitFail(161),
				clockModuleInitOk(162),
				cliHistoryLog(163),
				cliHistoryLogNo(164),
				slotActionEvent(165),
				slotStateChange(166),
				interfaceAdminDown(167),
				interfaceAdminUp(168),
				slotPowerMonAbnormal(169),
				slotPowerMonNormal(170),
				slotErrorLEDChanged(171),
				bfdSessionStateChanged(172),
				clockModuleOPModeChanged(173),
				clockModuleRefChanged(174),
				clockModuleInSrcStatusChanged(175),
				clockModuleInSrcAISStatusChanged(176),
				clockModuleInSrcLoSStatusChanged(177),
				clockModuleInSrcLSDCStatusChanged(178),
				clockModuleInSrcNtrClockChanged(179),
				portRxOverThreshold(181),
				portRxUnderThreshold(182),
				portTxOverThreshold(183),
				portTxUnderThreshold(184),
				cpuPpsOverThreshold(185),
				cpuPpsUnderThreshold(186),
				pairFanPowerOff(191),
				pairFanPowerOn(192),
				slotHealthStatusTimeout(199),
				slotHealthStatusTimeoutCleared(200),
				advaTemperature(201),
				advaTemperatureNo(202),
				advaPSUFailure(203),
				advaPSUFailureNo(204),
				advaFanFailure(205),
				advaFanFailureNo(206),
				advaInterfaceReceiveFailure(207),
				advaInterfaceReceiveFailureNo(208),
				advaInterfaceOpticalThreshold(209),
				advaInterfaceOpticalThresholdNo(210),
				advaInterfaceTransmitFault(211),
				advaInterfaceTransmitFaultNo(212),
				advaInterfaceMisconfiguration(213),
				advaInterfaceMisconfigurationNo(214),
				advaInterfaceSFPMismatch(215),
				advaInterfaceSFPMismatchNo(216),
				advaVoltageLow(217),
				advaVoltageLowNo(218),
				advaVoltageHigh(219),
				advaVoltageHighNo(220),
				criticalAlarmLedOn(251),
				criticalAlarmLedOff(252),
				majorAlarmLedOn(253),
				majorAlarmLedOff(254),
				minorAlarmLedOn(255),
				minorAlarmLedOff(256),
				erpDomainLotp(301),
				erpDomainLotpNo(302),
				erpDomainULotp(303),
				erpDomainULotpNo(304),
				erpDomainMultipleRM(305),
				erpDomainMultipleRMNo(306),
				erpDomainRMNodeReacheablity(307),
				erpDomainRMNodeReacheablityNo(308),
				startupConfigLoadEnded(391),
				eponOnuDeregister(401),
				eponOnuRegister(402),
				eponOnuRegistrationError(403),
				eponOnuNoRegistrationError(404),
				eponBadEncryptionKey(405),
				eponNoBadEncryptionKey(406),
				eponLlidMistmatch(407),
				eponNoLlidMismatch(408),
				eponTooManyRegister(409),
				eponNoTooManyRegister(410),
				eponDyingGASP(411),
				eponNoDyingGASP(412),
				eponOnuErrFramePeriod(413),
				eponOnuNoErrFramePeriod(414),
				eponOnuErrFrame(415),
				eponOnuNoErrFrame(416),
				eponOnuErrFrameSecondSummary(417),
				eponOnuNoErrFrameSecondSummary(418),
				eponOnuLastOnuDeregister(419),
				eponOnuNoLastOnuDeregister(420),
				eponOltCableDown(421),
				eponOltRecoverCableDown(422),
				eponOltHealthCheckError(423),
				eponOnuOpticSignalErr(424),
				eponOnuRecoverOpticSignalErr(425),
				standardLinkFault(428),
				standardLinkFaultCleared(429),
				lossOfSignal(430),
				lossOfSignalCleared(431),
				transmitFail(432),
				transmitFailCleared(433),
				macLearningOverflow(434),
				macLearningOverflowCleared(435),
				loopback(436),
				loopbackCleared(437),
				standardDyinggasp(438),
				standardDyinggaspCleared(439),
				externalDyinggasp(440),
				externalDyinggaspCleared(441),
				standardCriticalEvent(442),
				standardCriticalEventCleared(443),
				externalCriticalEvent(444),
				externalCriticalEventCleared(445),
				eponStandbyLos(446),
				eponStandbyLosCleared(447),
				eponOnuPingTest(448),
				eponOnuDmiThresholdTemperOverHighWarn(450),
				clearEponOnuDmiThresholdTemperOverHighWarn(451),
				eponOnuDmiThresholdTemperFallLowWarn(452),
				clearEponOnuDmiThresholdTemperFallLowWarn(453),
				eponOnuDmiThresholdTemperOverHighAlarm(454),
				clearEponOnuDmiThresholdTemperOverHighAlarm(455),
				eponOnuDmiThresholdTemperFallLowAlarm(456),
				clearEponOnuDmiThresholdTemperFallLowAlarm(457),
				eponOnuDmiThresholdVoltageOverHighWarn(458),
				clearEponOnuDmiThresholdVoltageOverHighWarn(459),
				eponOnuDmiThresholdVoltageFallLowWarn(460),
				clearEponOnuDmiThresholdVoltageFallLowWarn(461),
				eponOnuDmiThresholdVoltageOverHighAlarm(462),
				clearEponOnuDmiThresholdVoltageOverHighAlarm(463),
				eponOnuDmiThresholdVoltageFallLowAlarm(464),
				clearEponOnuDmiThresholdVoltageFallLowAlarm(465),
				eponOnuDmiThresholdTxbiasOverHighWarn(466),
				clearEponOnuDmiThresholdTxbiasOverHighWarn(467),
				eponOnuDmiThresholdTxbiasFallLowWarn(468),
				clearEponOnuDmiThresholdTxbiasFallLowWarn(469),
				eponOnuDmiThresholdTxbiasOverHighAlarm(470),
				clearEponOnuDmiThresholdTxbiasOverHighAlarm(471),
				eponOnuDmiThresholdTxbiasFallLowAlarm(472),
				clearEponOnuDmiThresholdTxbiasFallLowAlarm(473),
				eponOnuDmiThresholdTxpowerOverHighWarn(474),
				clearEponOnuDmiThresholdTxpowerOverHighWarn(475),
				eponOnuDmiThresholdTxpowerFallLowWarn(476),
				clearEponOnuDmiThresholdTxpowerFallLowWarn(477),
				eponOnuDmiThresholdTxpowerOverHighAlarm(478),
				clearEponOnuDmiThresholdTxpowerOverHighAlarm(479),
				eponOnuDmiThresholdTxpowerFallLowAlarm(480),
				clearEponOnuDmiThresholdTxpowerFallLowAlarm(481),
				eponOnuDmiThresholdRxpowerOverHighWarn(482),
				clearEponOnuDmiThresholdRxpowerOverHighWarn(483),
				eponOnuDmiThresholdRxpowerFallLowWarn(484),
				clearEponOnuDmiThresholdRxpowerFallLowWarn(485),
				eponOnuDmiThresholdRxpowerOverHighAlarm(486),
				clearEponOnuDmiThresholdRxpowerOverHighAlarm(487),
				eponOnuDmiThresholdRxpowerFallLowAlarm(488),
				clearEponOnuDmiThresholdRxpowerFallLowAlarm(489),
				eponDetectRouge(490),
				clearEpoonDetectRouge(491),
				eponDetectRougeOnuPowerOff(492),
				eponDetectRougeOnuPowerOffFailed(493),
				eponDetectRougeOnuDeregisterSuccess(494),
				eponDetectRougeOnuDeregisterFailed(495),
				eponDetectRougeOnuFoundFailed(496),
				eponOltRedundancyDetectRxpower(497),
				clearEponOltRedundancyDetectRxpower(498),
				eponOltRedundancySwitchoverReasonForce(499),
				eponOltRedundancySwitchoverReasonLos(500),
				autoCLIStart(501),
				autoCLINoStart(502),
				autoCLIComplete(503),
				autoCLINoComplete(504),
				autoCLIRemoveOutputFile(505),
				autoCLINoRemoveOutputFile(506),
				autoResetSystem(507),
				autoResetNoSystem(508),
				autoResetPingReplyLoss(509),
				autoResetNoPingReplyLoss(510),
				autoResetMemoryLeakDetect(511),
				autoResetNoMemoryLeakDetect(512),
				loopDetectBlocked(551),
				loopDetectUnBlockedByExpireTimer(552),
				loopDetectUnBlockedByLinkDown(553),
				loopDetectUnBlockedByClearCmd(554),
				oamRemoteTestLoopback(562),
				arulePacketDropDetect(601),
				arulePacketDropRelease(602),
				autoCpeUpgradeStart(605),
				autoCpeUpgradeFail(607),
				autoCpeUpgradeSuccess(609),
				batteryUnderTemper(611),
				batteryTemperUnderToNormal(612),
				batteryCellAbnormal(613),
				batteryCellNormal(614),
				batteryCellTestChargeStarted(615),
				batteryCellTestChargeFinished(616),
				batteryAcPowerFault(617),
				batteryAcPowerOk(618),
				bME1CardNoDetect(620),
				clearBME1CardNoDetect(621),
				bME1CardAFEerror(622),
				clearBME1CardAFEerror(623),
				bME1CardIFEerror(624),
				clearBME1CardIFEerror(625),
				bME1CardFWerror(626),
				clearBME1CardFWerror(627),
				bME1CardPROVerror(628),
				clearBME1CardPROVerror(629),
				bME1CrashDetect(630),
				clearBME1CrashDetect(631),
				bME2CardNoDetect(632),
				clearBME2CardNoDetect(633),
				bME2CardAFEerror(634),
				clearBME2CardAFEerror(635),
				bME2CardIFEerror(636),
				clearBME2CardIFEerror(637),
				bME2CardFWerror(638),
				clearBME2CardFWerror(639),
				bME2CardPROVerror(640),
				clearBME2CardPROVerror(641),
				bME2CrashDetect(642),
				clearBME2CrashDetect(643),
				bME3CardNoDetect(644),
				clearBME3CardNoDetect(645),
				bME3CardAFEerror(646),
				clearBME3CardAFEerror(647),
				bME3CardIFEerror(648),
				clearBME3CardIFEerror(649),
				bME3CardFWerror(650),
				clearBME3CardFWerror(651),
				bME3CardPROVerror(652),
				clearBME3CardPROVerror(653),
				bME3CrashDetect(654),
				clearBME3CrashDetect(655),
				powerFromBattery(656),
				clearPowerFromBattery(657),
				invalidBatteryStatus(658),
				clearInvalidBatteryStatus(659),
				batteryChargeLow(660),
				clearBatteryChargeLow(661),
				batteryNotPresent(662),
				clearBatteryNotPresent(663),
				voltageLow(664),
				clearVoltageLow(665),
				tempOverThreshold(666),
				clearTempOverThreshold(667),
				tempUnderThreshold(668),
				clearTempUnderThreshold(669),
				cpuOverThreshold(670),
				clearCpuOverThreshold(671),
				trafficOverload(672),
				clearTrafficOverload(673),
				gEPONModuleNotDetect(674),
				clearGEPONModuleNotDetect(675),
				gEPONPortOperationDown(676),
				clearGEPONPortOperationDown(677),
				gEPONNoIncomingTraffic(678),
				clearGEPONNoIncomingTraffic(679),
				processCrashDetect(680),
				clearProcessCrashDetect(681),
				memoryLeakDetect(682),
				clearMemoryLeakDetect(683),
				memoryCorrupDetect(684),
				clearMemoryCorrupDetect(685),
				memoryLowDetect(686),
				clearMemoryLowDetect(687),
				dataLineerror(688),
				clearDataLineerror(689),
				addressLineerror(690),
				clearAddressLineerror(691),
				chipsetNotDetcet(692),
				clearChipsetNotDetcet(693),
				pciBuserror(694),
				clearPciBuserror(695),
				securityAdminConnect(696),
				clearSecurityAdminConnect(697),
				oNUPowerDown(698),
				clearONUPowerDown(699),
				oNUNotRegister(700),
				clearONUNotRegister(701),
				oNTOpticPre(702),
				clearONTOpticPre(703),
				switchoverInitiated(800),
				switchoverDone(801),
				boardChangeState(802),
				redConfigurationMisMatch(803),
				aiuAlarmInput1(851),
				aiuAlarmInput1Cleared(852),
				aiuAlarmInput2(853),
				aiuAlarmInput2Cleared(854),
				aiuAlarmInput3(855),
				aiuAlarmInput3Cleared(856),
				aiuAlarmInput4(857),
				aiuAlarmInput4Cleared(858),
				aiuSlotUninstalled(859),
				aiuSlotInstalled(860),
				gponNoAuthCBU(901),
				gponDuplicateONU(902),
				gponDyingGasp(903),
				gponUpgradeComplete(904),
				gponDeregistered(905),
				gponRegistered(906),
				gponRogueOnu(907),
				gponOnuBatteryEvent(908),
				clearGponOnuBetteryEvent(909),
				gponOnuPortOperStatus(910),
				gponTransceiverChanged(911),
				gponOltLosOn(912),
				gponOltLosOff(913),
				gponOltLosiOn(914),
				gponOltLosiOff(915),
				gponDyingGaspOn(916),
				gponDyingGaspOff(917),
				gponOntOSUpgradeStatus(918),
				gponOntBLUpgradeStatus(919),
				gponOltRxPowerLoss(920),
				gponOltRxPowerDetected(921),
				gponOnuTemperatureHighOverThreshold(922),
				gponOnuTemperatureHighFallThreshold(923),
				gponOnuTemperatureLowOverThreshold(924),
				gponOnuTemperatureLowFallThreshold(925),
				gponOnuCpuOverThreshold(926),
				gponOnuCpuFallThreshold(927),
				gponOnuMemoryOverThreshold(928),
				gponOnuMemoryFallThreshold(929),
				gponOnuI2cFail(930),
				gponOnuRxOpticLowThreshAlarmOn(931),
				gponOnuRxOpticLowThreshAlarmOff(932),
				gponOnuRxOpticHighThreshAlarmOn(933),
				gponOnuRxOpticHighThreshAlarmOff(934),
				gponOltLOFIOn(935),
				gponOltLOFIOff(936),
				gponOltDOWOn(937),
				gponOltDOWOff(938),
				gponOltSFOn(939),
				gponOltSFOff(940),
				gponOltSDOn(941),
				gponOltSDOff(942),
				gponOltLCDGIOn(943),
				gponOltLCDGIOff(944),
				gponOltRDOn(945),
				gponOltRDOff(946),
				gponOltSUFOn(947),
				gponOltSUFOff(948),
				gponOltLOAOn(949),
				gponOltLOAOff(950),
				gponOltLOAMIOn(951),
				gponOltLOAMIOff(952),
				gponOltMEMOn(953),
				gponOltMEMOff(954),
				gponOltPEEOn(955),
				gponOltPEEOff(956),
				gponOltPSTOn(957),
				gponOltPSTOff(958),
				gponOltERROn(959),
				gponOltERROff(960),
				gponOltREIOn(961),
				gponOltREIOff(962),
				gponAntiSpoofingDupPortOn(963),
				gponAntiSpoofingDupPortOff(964),
				gponRedundancySwitchOver(965),
				gponDuplicatedRangingResponse(966),
				gponOnuPortOpticModuleRemove(967),
				gponOnuPortOpticModuleInstall(968),
				gponOnuOMCCProblemDetected(969),
				gponOnuOMCCProblemCleared(970),
				gponOltFixedTcontAlarmOn(971),
				gponOltFixedTcontAlarmOff(972),
				gponOltDynamicTcontAlarmOn(973),
				gponOltDynamicTcontAlarmOff(974),
				gponOltPortCountAlarmOn(975),
				gponOltPortCountAlarmOff(976),
				gponOltCableDownAlarmOn(977),
				gponOltCableDownAlarmOff(978),
				gponOltDeactiveMonitorAlarmOn(979),
				gponOltDeactiveMonitorAlarmOff(980),
				gponOltDfiOn(981),
				gponOltDfiOff(982),
				gponOltTransceiverPortChanged(984),
				gponOnuPortOperStatusDown(985),
				gponOnuPortOperStatusUp(986),
				gponOltRxPowerHighOver(987),
				gponOltRxPowerHighCleared(988),
				gponOltRxPowerLowUnder(989),
				gponOltRxPowerLowCleared(990),
				oamRapsEastPortStatusChanged(1001),
				oamRapsWestPortStatusChanged(1002),
				oamURNodePortStatusChanged(1003),
				oamRemoteLlcfLinkDown(1008),
				oamRemoteLlcfLinkUp(1009),
				oamInterfaceStatusChanged(1010),
				oamMepRDIDetected(1011),
				oamMepRDICleared(1012),
				oamMepLOCDetected(1013),
				oamMepLOCCleared(1014),
				oamMepUNPDetected(1015),
				oamMepUNPCleared(1016),
				oamMepUNMDetected(1017),
				oamMepUNMCleared(1018),
				oamMepMMGDetected(1019),
				oamMepMMGCleared(1020),
				oamMepUNLDetected(1021),
				oamMepUNLCleared(1022),
				oamMepAISDetected(1023),
				oamMepAISCleared(1024),
				oamMepLCKDetected(1025),
				oamMepLCKCleared(1026),
				oamMepMISSINGDetected(1027),
				oamMepMISSINGCleared(1028),
				voipPortStatusEnabled(1051),
				voipPortStatusDisabled(1052),
				emLogDefectCPUHighOver(1101),
				emLogDefectCPUHighUnder(1102),
				emLogTemperHighOver(1103),
				emLogTemperHighUnder(1104),
				emLogTemperLowUnder(1105),
				emLogTemperLowOver(1106),
				emLogMemLowUnder(1107),
				emLogMemLowOver(1108),
				emLogFanFail(1109),
				emLogFanFailCleared(1110),
				emLogPhyCRCFail(1111),
				emLogPhyCRCFailCleared(1112),
				emLogPhyDetectFail(1113),
				emLogPhyDetectFailCleared(1114),
				emLogSFUMateInitFail(1115),
				emLogSFUMateInitFailCleared(1116),
				emLogDaemonHealthBad(1117),
				emLogDaemonHealthBadCleared(1118),
				emLogGPIURavenLinkDown(1119),
				emLogGPIURavenLinkDownCleared(1120),
				emLogRPMLow(1121),
				emLogRPMLowCleared(1122),
				emLogNAKError(1123),
				emLogNAKErrorCleared(1124),
				snmpAllConfCleared(1141),
				slotNosUpgradeStart(1151),
				slotNosUpgradeEnd(1152),
				autonegoMissmatedSpeed(1171),
				autonegoMissmatedDuplex(1172),
				autonegoMismatched(1174),
				dmiTempHighOverDurationAlarm(1201),
				dmiTempLowFallDurationAlarm(1202),
				dmiTempHighOverDurationWarning(1203),
				dmiTempLowFallDurationWarning(1204),
				dmiVolHighOverDurationAlarm(1205),
				dmiVolLowFallDurationAlarm(1206),
				dmiVolHighOverDurationWarning(1207),
				dmiVolLowFallDurationWarning(1208),
				dmiTxBiasHighOverDurationAlarm(1209),
				dmiTxBiasLowFallDurationAlarm(1210),
				dmiTxBiasHighOverDurationWarning(1211),
				dmiTxBiasLowFallDurationWarning(1212),
				dmiTxPowerHighOverDurationAlarm(1213),
				dmiTxPowerLowFallDurationAlarm(1214),
				dmiTxPowerHighOverDurationWarning(1215),
				dmiTxPowerLowFallDurationWarning(1216),
				dmiRxPowerHighOverDurationAlarm(1217),
				dmiRxPowerLowFallDurationAlarm(1218),
				dmiRxPowerHighOverDurationWarning(1219),
				dmiRxPowerLowFallDurationWarning(1220),
				attackGuard(1221),
				attackGuardNo(1222),
				activeLinkDown(1223),
				activeLinkDownNo(1224),
				activeLinkUp(1225),
				activeLinkUpNo(1226),
				redundantLinkDown(1227),
				redundantLinkDownNo(1228),
				redundantLinkUp(1229),
				redundantLinkUpNo(1230),
				inputErrorThreshold(1231),
				inputErrorThresholdNo(1232),
				overSizeFrameThreshold(1233),
				overSizeFrameThresholdNo(1234),
				configLoadFail(1235),
				configLoadFailNo(1236),
				nosLoadFail(1237),
				nosLoadFailNo(1238),
				securityViolation(1239),
				securityViolationNo(1240),
				selfTestCompleted(1241),
				selfTestCompletedNo(1242),
				risingAlarm(1243),
				risingAlarmNo(1244),
				fallingAlarm(1245),
				fallingAlarmNo(1246),
				newRoot(1247),
				newRootNo(1248),
				topologyChange(1249),
				topologyChangeNo(1250),
				broadcastStormStart(1251),
				broadcastStormStartNo(1252),
				broadcastStormEnd(1253),
				broadcastStormEndNo(1254),
				duplicateMac(1255),
				duplicateMacNo(1256),
				trapLog(1257),
				trapLogNo(1258),
				scriptLoadFail(1259),
				scriptLoadFailNo(1260),
				monitorEvent(1261),
				monitorEventNo(1262),
				powerDetectFail(1263),
				powerDetectOk(1264),
				underSizeFrameThreshold(1265),
				underSizeFrameThresholdNo(1266),
				runtFrameThreshold(1267),
				runtFrameThresholdNo(1268),
				dyingGasp(1269),
				dyingGaspNo(1270),
				voipPortStatusEnable(1271),
				voipPortStatusDisable(1272),
				fanStop(1281),
				fanRun(1282),
				mllcfLinkDown(1301),
				mllcfLinkUp(1302),
				gponOnuAniVoltageLowThreshAlarmOn(1331),
				gponOnuAniVoltageLowThreshAlarmOff(1332),
				gponOnuAniVoltageHighThreshAlarmOn(1333),
				gponOnuAniVoltageHighThreshAlarmOff(1334),
				gponOnuAniTemperatureLowThreshAlarmOn(1335),
				gponOnuAniTemperatureLowThreshAlarmOff(1336),
				gponOnuAniTemperatureHighThreshAlarmOn(1337),
				gponOnuAniTemperatureHighThreshAlarmOff(1338),
				gponOnuAniTxBiasLowThreshAlarmOn(1339),
				gponOnuAniTxBiasLowThreshAlarmOff(1340),
				gponOnuAniTxBiasHighThreshAlarmOn(1341),
				gponOnuAniTxBiasHighThreshAlarmOff(1342),
				gponOnuAniTxpowerLowThreshAlarmOn(1343),
				gponOnuAniTxpowerLowThreshAlarmOff(1344),
				gponOnuAniTxpowerHighThreshAlarmOn(1345),
				gponOnuAniTxpowerHighThreshAlarmOff(1346),
				portThresholdTxOverAlarm(1351),
				portThresholdTxOverAlarmCleared(1352),
				portThresholdTxOverWarn(1353),
				portThresholdTxOverWarnCleared(1354),
				portThresholdRxOverAlarm(1355),
				portThresholdRxOverAlarmCleared(1356),
				portThresholdRxOverWarn(1357),
				portThresholdRxOverWarnCleared(1358),
				tempThresholdHighOverAlarm(1361),
				tempThresholdHighOverAlarmCleared(1362),
				tempThresholdLowOverAlarm(1363),
				tempThresholdLowOverAlarmCleared(1364),
				tempThresholdHighOverWarn(1365),
				tempThresholdHighOverWarnCleared(1366),
				tempThresholdLowOverWarn(1367),
				tempThresholdLowOverWarnCleared(1368),
				moduleDmiReadError(1381),
				moduleDmiReadErrorCleared(1382),
				stormControlRxOver(1391),
				stormControlRxOverCleared(1392),
				rmonCrcAlignErrorRising(1401),
				rmonCrcAlignErrorRisingCleared(1402),
				rmonJabberRising(1403),
				rmonJabberRisingCleared(1404),
				rmonOversizePacketRising(1405),
				rmonOversizePacketRisingCleared(1406),
				rmonUndersizePacketRising(1407),
				rmonUndersizePacketRisingCleared(1408),
				rmonFragmentRising(1409),
				rmonFragmentRisingCleared(1410),
				rmonDropEventRising(1411),
				rmonDropEventRisingCleared(1412),
				eponOltRedundancySwitchoverReasonSlotRemove(1500),
				eponOltRedundancySwitchoverReasonSlotRestart(1501),
				eponOltRedundancySwitchoverReasonAutoDetect(1502),
				eponOltRedundancySwitchoverReasonWtrDetect(1503),
				eponOnuCrcUpStreamAlarmErr(1504),
				eponOnuCrcUpStreamAlarmErrClean(1505),
				eponOnuTooFrequentlyRegisteredErr(1506),
				eponOnuTooFrequentlyRegisteredErrClean(1507),
				eponOnuCrcDownStreamAlarmErr(1508),
				eponOnuCrcDownStreamAlarmErrClean(1509),
				tcpDosAttack(2001),
				tcpDosAttackCleared(2002),
				tcpPortFlooding(2003),
				tcpPortFloodingCleared(2004),
				tcpHostRandomFlooding(2005),
				tcpHostRandomFloodingCleared(2006),
				tcpHostScanning(2007),
				tcpHostScanningCleared(2008),
				ipSppfing(2009),
				ipSppfingCleared(2010),
				udpDosAttack(2011),
				udpDosAttackCleared(2012),
				udpPortFlooding(2013),
				udpPortFloodingCleared(2014),
				udpHostRandomFlooding(2015),
				udpHostRandomFloodingCleared(2016),
				udpHostScanning(2017),
				udpHostScanningCleared(2018),
				udpIPSppfing(2019),
				udpIPSppfingCleared(2020),
				icmpDosAttack(2021),
				icmpDosAttackCleared(2022),
				icmpIPSppfing(2023),
				icmpIPSppfingCleared(2024),
				icmpHostScanning(2025),
				icmpHostScanningCleared(2026),
				arpMacFlooding(2027),
				arpMacFloodingCleared(2028),
				arpSpoofing(2029),
				arpSpoofingCleared(2030),
				decoySnare(2031),
				decoySnareCleared(2032),
				hostScan(2033),
				hostScanCleared(2034),
				portScan(2035),
				portScanCleared(2036),
				tcpPortScanning(2037),
				tcpPortScanningCleared(2038),
				udpPortScanning(2039),
				udpPortScanningCleared(2040),
				staticAttack(2041),
				staticAttackCleared(2042)
				}

	
--
-- Node definitions
--
	
--  Node definitions
-- 
-- Node definitions
-- 
-- 1.3.6.1.4.1.6296.101.4.1
-- 1.3.6.1.4.1.6296.101.4.1
		-- 1.3.6.1.4.1.6296.101.4.1
		sleFaultMgmtBase OBJECT IDENTIFIER ::= { sleFaultMgmt 1 }

		
--   1.3.6.1.4.1.6296.101.4.1.1
-- 1.3.6.1.4.1.6296.101.4.1.1
		-- 1.3.6.1.4.1.6296.101.4.1.1
		sleFaultMgmtBaseGroup OBJECT IDENTIFIER ::= { sleFaultMgmtBase 1 }

		
--   1.3.6.1.4.1.6296.101.4.1.1.1
-- 1.3.6.1.4.1.6296.101.4.1.1.1
		-- 1.3.6.1.4.1.6296.101.4.1.1.1
		sleFaultDefaultSeverity OBJECT-TYPE
			SYNTAX INTEGER
				{
				critical(1),
				major(2),
				minor(3),
				warning(4),
				intermediate(5)
				}
			MAX-ACCESS read-only
			STATUS current
			DESCRIPTION
				" The severity of alarm. "
			::= { sleFaultMgmtBaseGroup 1 }

		
--   1.3.6.1.4.1.6296.101.4.1.1.2
-- 1.3.6.1.4.1.6296.101.4.1.1.2
		-- 1.3.6.1.4.1.6296.101.4.1.1.2
		sleFaultCriteriaSeverity OBJECT-TYPE
			SYNTAX INTEGER
				{
				critical(1),
				major(2),
				minor(3),
				warning(4),
				intermediate(5)
				}
			MAX-ACCESS read-only
			STATUS current
			DESCRIPTION
				" The severity of alarm. "
			::= { sleFaultMgmtBaseGroup 2 }

		
--   1.3.6.1.4.1.6296.101.4.1.1.3
-- 1.3.6.1.4.1.6296.101.4.1.1.3
		-- 1.3.6.1.4.1.6296.101.4.1.1.3
		sleFaultNotifiyActivity OBJECT-TYPE
			SYNTAX INTEGER
				{
				disabled(0),
				enabled(1)
				}
			MAX-ACCESS read-only
			STATUS current
			DESCRIPTION
				" The severity of alarm. "
			::= { sleFaultMgmtBaseGroup 3 }

		
--   1.3.6.1.4.1.6296.101.4.1.1.4
-- 1.3.6.1.4.1.6296.101.4.1.1.4
		-- 1.3.6.1.4.1.6296.101.4.1.1.4
		sleFaultNextSeqNum OBJECT-TYPE
			SYNTAX Counter32
			MAX-ACCESS read-only
			STATUS current
			DESCRIPTION
				"Sequence number for the alarm synchronization. 
				This value has a number to be used for the next alarm trap."
			::= { sleFaultMgmtBaseGroup 4 }

		
--   1.3.6.1.4.1.6296.101.4.1.2
-- 1.3.6.1.4.1.6296.101.4.1.2
		-- 1.3.6.1.4.1.6296.101.4.1.2
		sleFaultMgmtBaseControl OBJECT IDENTIFIER ::= { sleFaultMgmtBase 2 }

		
--   1.3.6.1.4.1.6296.101.4.1.2.1
-- 1.3.6.1.4.1.6296.101.4.1.2.1
		-- 1.3.6.1.4.1.6296.101.4.1.2.1
		sleFaultControlRequest OBJECT-TYPE
			SYNTAX INTEGER
				{
				setAlarmDefaultSeverity(1),
				setAlarmCriteriaSeverity(2),
				setNotificationActivity(3)
				}
			MAX-ACCESS read-write
			STATUS current
			DESCRIPTION
				" This attribute identifies the control commands.
				updateAlarmList:
				   the NE updates entries of alarms in the sleAlarmListTable
				   after having changed alarm severities of alarms 
				   (due to change profile pointers in
				   managed entities or after modification of alarm severities 
				   in profiles). This command should be applied once after having 
				   finisled modifications of severties.
				modifyAlarmSeverity: 
				   modifies the severity of an alarm in specific profile.
				createAlarmSeverityProfile: 
				   creates a new profile with default severities.
				   The severities then have to be modified with command changeAlarmSeverity.
				deleteAlarmSeverityProfile: 
				   deletes a profile. Profile 1 is not allowed to be deleted.
				 
				Notifications : none "
			::= { sleFaultMgmtBaseControl 1 }

		
--   1.3.6.1.4.1.6296.101.4.1.2.2
-- 1.3.6.1.4.1.6296.101.4.1.2.2
		-- 1.3.6.1.4.1.6296.101.4.1.2.2
		sleFaultControlStatus OBJECT-TYPE
			SYNTAX SleControlStatusType
			MAX-ACCESS read-only
			STATUS current
			DESCRIPTION
				" The status of a control request. "
			::= { sleFaultMgmtBaseControl 2 }

		
--   1.3.6.1.4.1.6296.101.4.1.2.3
-- 1.3.6.1.4.1.6296.101.4.1.2.3
		-- 1.3.6.1.4.1.6296.101.4.1.2.3
		sleFaultControlTimer OBJECT-TYPE
			SYNTAX Unsigned32
			MAX-ACCESS read-write
			STATUS current
			DESCRIPTION
				" The maximum wait time for the manager for command ending.
				For long running commands.
				The manager reads this value from the DSLAM. "
			::= { sleFaultMgmtBaseControl 3 }

		
--   1.3.6.1.4.1.6296.101.4.1.2.4
-- 1.3.6.1.4.1.6296.101.4.1.2.4
		-- 1.3.6.1.4.1.6296.101.4.1.2.4
		sleFaultControlTimeStamp OBJECT-TYPE
			SYNTAX TimeTicks
			MAX-ACCESS read-only
			STATUS current
			DESCRIPTION
				" The time stamp of the last command (end of command). "
			::= { sleFaultMgmtBaseControl 4 }

		
--   1.3.6.1.4.1.6296.101.4.1.2.5
-- 1.3.6.1.4.1.6296.101.4.1.2.5
		-- 1.3.6.1.4.1.6296.101.4.1.2.5
		sleFaultControlReqResult OBJECT-TYPE
			SYNTAX SleControlRequestResultType
			MAX-ACCESS read-only
			STATUS current
			DESCRIPTION
				" The result of the last user command. "
			::= { sleFaultMgmtBaseControl 5 }

		
--   1.3.6.1.4.1.6296.101.4.1.2.6
-- 1.3.6.1.4.1.6296.101.4.1.2.6
		-- 1.3.6.1.4.1.6296.101.4.1.2.6
		sleFaultControlDefaultSeverity OBJECT-TYPE
			SYNTAX INTEGER
				{
				critical(1),
				major(2),
				minor(3),
				warning(4),
				intermediate(5)
				}
			MAX-ACCESS read-write
			STATUS current
			DESCRIPTION
				" The severity of alarm. "
			::= { sleFaultMgmtBaseControl 6 }

		
--   1.3.6.1.4.1.6296.101.4.1.2.7
-- 1.3.6.1.4.1.6296.101.4.1.2.7
		-- 1.3.6.1.4.1.6296.101.4.1.2.7
		sleFaultControlCriteriaSeverity OBJECT-TYPE
			SYNTAX INTEGER
				{
				critical(1),
				major(2),
				minor(3),
				warning(4),
				intermediate(5)
				}
			MAX-ACCESS read-write
			STATUS current
			DESCRIPTION
				" The severity of alarm. "
			::= { sleFaultMgmtBaseControl 7 }

		
--   1.3.6.1.4.1.6296.101.4.1.2.8
-- 1.3.6.1.4.1.6296.101.4.1.2.8
		-- 1.3.6.1.4.1.6296.101.4.1.2.8
		sleFaultControlNotifiyActivity OBJECT-TYPE
			SYNTAX INTEGER
				{
				diabled(0),
				enabled(1)
				}
			MAX-ACCESS read-write
			STATUS current
			DESCRIPTION
				" The severity of alarm. "
			::= { sleFaultMgmtBaseControl 8 }

		
--   1.3.6.1.4.1.6296.101.4.1.3
-- 1.3.6.1.4.1.6296.101.4.1.3
		-- 1.3.6.1.4.1.6296.101.4.1.3
		sleFaultMgmtBaseNotification OBJECT IDENTIFIER ::= { sleFaultMgmtBase 3 }

		
--   1.3.6.1.4.1.6296.101.4.1.3.1
-- 1.3.6.1.4.1.6296.101.4.1.3.1
		-- 1.3.6.1.4.1.6296.101.4.1.3.1
		sleAlarmDefaultSeverityChanged NOTIFICATION-TYPE
			OBJECTS { sleFaultDefaultSeverity, sleFaultControlRequest, sleFaultControlTimeStamp, sleFaultControlReqResult }
			STATUS current
			DESCRIPTION 
				"Description."
			::= { sleFaultMgmtBaseNotification 1 }

		
--   1.3.6.1.4.1.6296.101.4.1.3.2
-- 1.3.6.1.4.1.6296.101.4.1.3.2
		-- 1.3.6.1.4.1.6296.101.4.1.3.2
		sleAlarmDefaultCriteriaChanged NOTIFICATION-TYPE
			OBJECTS { sleFaultCriteriaSeverity, sleFaultControlRequest, sleFaultControlTimeStamp, sleFaultControlReqResult }
			STATUS current
			DESCRIPTION 
				"Description."
			::= { sleFaultMgmtBaseNotification 2 }

		
--   1.3.6.1.4.1.6296.101.4.1.3.3
-- 1.3.6.1.4.1.6296.101.4.1.3.3
		-- 1.3.6.1.4.1.6296.101.4.1.3.3
		sleNotificationActivityChanged NOTIFICATION-TYPE
			OBJECTS { sleFaultControlRequest, sleFaultControlTimeStamp, sleFaultControlReqResult, sleFaultNotifiyActivity }
			STATUS current
			DESCRIPTION 
				"Description."
			::= { sleFaultMgmtBaseNotification 3 }

		
--   1.3.6.1.4.1.6296.101.4.2
-- 1.3.6.1.4.1.6296.101.4.2
		-- 1.3.6.1.4.1.6296.101.4.2
		sleAlarmSeverity OBJECT IDENTIFIER ::= { sleFaultMgmt 2 }

		
--   1.3.6.1.4.1.6296.101.4.2.1
-- 1.3.6.1.4.1.6296.101.4.2.1
		-- 1.3.6.1.4.1.6296.101.4.2.1
		sleAlarmSeverityTable OBJECT-TYPE
			SYNTAX SEQUENCE OF SleAlarmSeverityEntry
			MAX-ACCESS not-accessible
			STATUS current
			DESCRIPTION
				" The alarm severity table.
				The alarm severity table associates
				profile index and AlarmID pairs with severities to be
				used for alarm traps.
				(Note that this table does not apply to cleared alarms). "
			::= { sleAlarmSeverity 1 }

		
--   1.3.6.1.4.1.6296.101.4.2.1.1
-- 1.3.6.1.4.1.6296.101.4.2.1.1
		-- 1.3.6.1.4.1.6296.101.4.2.1.1
		sleAlarmSeverityEntry OBJECT-TYPE
			SYNTAX SleAlarmSeverityEntry
			MAX-ACCESS not-accessible
			STATUS current
			DESCRIPTION
				" Entry of the alarm severity table. "
			INDEX { sleAlarmSeverityIndex }
			::= { sleAlarmSeverityTable 1 }

		
		SleAlarmSeverityEntry ::=
			SEQUENCE { 
				sleAlarmSeverityIndex
					SpecificNum,
				sleAlarmSeverityValue
					INTEGER
			 }

--    1.3.6.1.4.1.6296.101.4.2.1.1.1
-- 1.3.6.1.4.1.6296.101.4.2.1.1.1
-- 1.3.6.1.4.1.6296.101.4.2.1.1.1
		-- 1.3.6.1.4.1.6296.101.4.2.1.1.1
		sleAlarmSeverityIndex OBJECT-TYPE
			SYNTAX SpecificNum
			MAX-ACCESS read-only
			STATUS current
			DESCRIPTION
				"The following alarms is devided by the specific character, ===============.
				The division basis is that alarms is bounded or released.
				
				001: portDown: To detect whether physical or logical interface's link status is up or down.
				002: portUp: 
				===============
				003: portRemoved: To detect whether physical interface is installed or not.
				004: portInstalled: 
				===============
				005: powerFail: To detect whether power module's operation status is good or not.
						(Without doubt, more than 1 power module should be equipped.)
				006: powerOK: 
				===============
				007: powerRemoved: To detect whether power module is installed or not, through the PLD access.
						   (Without doubt, more than 1 power module should be equipped.)
				008: powerInstalled: 
				===============
				009: fanFail: To detect whether FAN module's operation status is good or not.
				010: fanOK: 
				===============
				011: fanRemoved: To detect whether FAN module is installed or not, through the PLD access.
				012: fanInstalled: 
				===============
				013: moduleRemoved: To detect whether physical interface module is installed or not, through the S/W I2C
				014: moduleInstalled: 
				===============
				015: systemRestart: Network system is restarted by operator. This is not H/W start but S/W start.
				===============
				016: systemStart: Network system is restarted by operator or system status. This is not S/W start but H/W start.
						  (This alarm isn’t used current)
				===============
				017: broadcastOver: To detect the receipt of broadcast packet.
				 			    (This alarm isn’t used current)
				018: broadcastUnder: 
				===============
				019: cpuOverLoad: To detect whether the configured CPU load threshold is less than current CPU load usage or not.
				020: cpuUnderLoad: 
				===============
				021: memoryOverUsed: To detect whether the configured memory threshold is less than current memory usage or not.
				022: memoryUnderUsed: 
				===============
				023: portOverThreshold: To detect whether the configured physical or logical interface threshold is 
							less than delta value of current interface's InOctects or not.
				024: portUnderThreshold: 
				===============
				025: temperatureHigh: To detect whether the configured system's temperature threshold is 
						      less than current temperature or not.
				026: temperatureLow: 
				===============
				027: mfgdBlocked: To detect whether the specific MAC by MAC flood guard is blocked or not.
				028: mfgdReleased: 
				===============
				029: ipConflict: To detect whether the same IP address on different network node is configured or not.
				030: ipUnconflict: 
				===============
				031: dhcpLeaseShortage: To detect whether IP address that can be assigned to subscriber by DHCP server is 
							sufficient or not.
				032: dhcpLeaseSufficient: 
				===============
				033: dhcpOccuredIllegalEntry: To detect whether a subsceiber is using a static IP address or not.
				034: dhcpRemovedIllegalEntry: 
				===============
				035: rmonAlarmRising: To detect whether rising threshold of a specific MO in RMON alarm sampling is 
						      less than current calculated value by alarm sample type or not. But alarm generation 
						      would be issued by means of event type in RMON event.
				036: rmonAlarmNoRising: 
				===============
				037: rmonAlarmFalling: To detect whether falling threshold of a specific MO in RMON alarm sampling is 
						       less than current calculated value by alarm sample type or not. 
						       But alarm generation would be issued by means of event type in RMON event.
				038: rmonAlarmNoFalling: 
				===============
				039: bpduGuardDisabled: To detect whether edge ports is guarded about superior BPDU or not. 
							In case of insertion edge node with 0 or lower priority than priority of current root bridge node, 
							it will be disarrangement during a short time because of recognition a new inserted node 
							as root bridge. 
							So these edge ports is guarded, and then edge ports is blocked about all superior BPDU. 
							So STP reconfiguration doesn't use this edge ports.
				===============
				040: rootGuardDisabled: To detect whether edge ports is guarded about superior BPDU or not. 
							In case of insertion edge node with 0 or lower priority than priority of current root bridge node, 
							it will be disarrangement during a short time because of recognition a new inserted node 
							as root bridge. 
							So, Root guard prevents a new inserted node from being root bridge as well as 
							receiving a superior BPDU from root bridge. 
							but this node participates in STP topology reconfiguration. 
							If root bridge does not send a superior BPDU, then this node acts usually though STP state change.
				===============
				041: portSecurity: To detect whether interface is configured for security or not. 
						   This can be used to prevent MAC from flooding as well as spoofing. 
						   That is, As a result, this will obstruct an attack as like DoS attack.
				===============
				042: userLogin: 
				043: userLogout: 
				===============
				051: igmpGroupJoined: To detect whether a subscriber is joined a multicast group or not.
				052: igmpGroupLeaved: 
				===============
				053: dhcpIpaddressBound: To detect wether a dynamic IP address is assigned to a subscriber or not.
				054: dhcpIpaddressFree: 
				===============
				055: doorOpened: To detect whether outer door is opeded or not, as external alarm.
				056: doorClosed: 
				===============
				057: powerModeChangedPowerToBattery: To detect whether a system is using AC power or battery. 
								     A system is using AC power usually. 
								     If there is any power problems as like a power failure, 
								     a system is using battery instead of AC power. 
				058: powerModeChangedBatteryToPower: 
				===============
				059: batterylowcapacity: To detect whether current battery capacity is less 
							 capacity threshold according to battery usage or not. 
							 The capacity of AC power is 16 voltage and battery is 20. 
							 Capacity threshold is configured by H/W specification.
							 So operator can't change it.
				060: batterynormalcapacity: 
				===============
				061: batteryhighTemperature: To detect whether current temperature of battery is greater than temperature threshold or not. 
				062: batterynormalTemperature: 
				===============
				063: authenticationFail: To detect whether the connected user is authentic or non-authentic.
				064: authenticationNofail: 
				===============
				065: psuAcHighTemperature: To detect whether current temperature of Power Supply Unit is 
							   greater than temperature threshold or not. 
				066: psuAcNormalTemperature: 
				===============
				067: batteryRemoved: To detect whether battery is equipped at network system or not. 
						     Battery is used as redundancy power service. So operator can decide the installation of battery.
				068: batteryEquipped: 
				===============
				069: batteryLowVoltage: To detect whether battery voltage is less than 12.5 volt or not. 
							12.5 volt value is configured by H/W specification. So operator can't change it.
				070: batteryNormalVoltage: 
				===============
				071: adminAccessLogin: To detect whether a operator connects at this network system or not.
				072: adminAccessLogout: 
				===============
				073: cfgdBlocked: To detect whether it is blocked flood to CPU or not.
				074: cfgdReleased: 
				===============
				075: sfgdBlocked: To detect whether it is blocked flood to system or not.
				076: sfgdReleased: 
				===============
				077: swWatchdogAbnormalState: To detect whether a specific process acts normally or not.
				078: swWatchdogNormalState: 
				===============
				079: swWatchdogDetectError: To detect whether a specific process is detected a error related to itself or cleared.
				080: swWatchdogClearError: 
				===============
				081: ppsControlBlocked: To detect whether it is blocked by pps-control or not.
				082: ppsControlReleased: 
				===============
				083: gotDMITempHighOverAlarm: To detect whether internal temperature exceeds high alarm level or not.
				084: gotDMITempHighFallAlarm: 
				===============
				085: gotDMITempLowOverAlarm: To detect whether internal temperature is below low alarm level or not.
				086: gotDMITempLowFallAlarm: 
				===============
				087: gotDMITempHighOverWarning: To detect whether internal temperature exceeds high warning level or not.
				088: gotDMITempHighFallWarning: 
				===============
				089: gotDMITempLowOverWarning: To detect whether internal temperature is below low warning level or not.
				090: gotDMITempLowFallWarning: 
				===============
				091: gotDMIVolHighOverAlarm: To detect whether internal supply voltage exceeds high alarm level or not.
				092: gotDMIVolHighFallAlarm: 
				===============
				093: gotDMIVolLowOverAlarm: To detect whether internal supply voltage is below low alarm level or not.
				094: gotDMIVolLowFallAlarm: 
				===============
				095: gotDMIVolHighOverWarning: To detect whether internal supply voltage exceeds high warning level or not.
				096: gotDMIVolHighFallWarning: 
				===============
				097: gotDMIVolLowOverWarning: To detect whether internal supply voltage is below low warning level or not.
				098: gotDMIVolLowFallWarning: 
				===============
				099: gotDMITxBiasHighOverAlarm: To detect whether TX Bias current exceeds high alarm level or not.
				100: gotDMITxBiasHighFallAlarm: 
				===============
				101: gotDMITxBiasLowOverAlarm: To detect whether TX Bias current is below low alarm level or not.
				102: gotDMITxBiasLowFallAlarm: 
				===============
				103: gotDMITxBiasHighOverWarning: To detect whether TX Bias current exceeds high warning level or not.
				104: gotDMITxBiasHighFallWarning: 
				===============
				105: gotDMITxBiasLowOverWarning: To detect whether TX Bias current is below low warning level or not.
				106: gotDMITxBiasLowFallWarning: 
				===============
				107: gotDMITxPowerHighOverAlarm: To detect whether TX output power exceeds high alarm level or not.
				108: gotDMITxPowerHighFallAlarm: 
				===============
				109: gotDMITxPowerLowOverAlarm: To detect whether TX output power is below low alarm level or not.
				110: gotDMITxPowerLowFallAlarm: 
				===============
				111: gotDMITxPowerHighOverWarning: To detect whether TX output power exceeds high warning level or not.
				112: gotDMITxPowerHighFallWarning: 
				===============
				113: gotDMITxPowerLowOverWarning: To detect whether TX output power is below low warning level or not.
				114: gotDMITxPowerLowFallWarning: 
				===============
				115: gotDMIRxPowerHighOverAlarm: To detect whether RX output power exceeds high alarm level or not.
				116: gotDMIRxPowerHighFallAlarm: 
				===============
				117: gotDMIRxPowerLowOverAlarm: To detect whether RX output power is below low alarm level or not.
				118: gotDMIRxPowerLowFallAlarm: 
				===============
				119: gotDMIRxPowerHighOverWarning: To detect whether RX output power exceeds high warning level or not.
				120: gotDMIRxPowerHighFallWarning: 
				===============
				121: gotDMIRxPowerLowOverWarning: To detect whether RX output power is below low warning level or not.
				122: gotDMIRxPowerLowFallWarning: 
				===============
				123: nosRemoteUpgradeRequest: 
				124: nosRemoteUpgradeSuccess: 
				125: nosRemoteUpgradeFailAbort: 
				126: nosRemoteUpgradeFailHeaderError: 
				127: nosRemoteUpgradeFailDownloadError: 
				128: nosRemoteUpgradeFailFlashError: 
				129: nosRemoteUpgradeStart: 
				===============
				130: systemDyingGasp:
				===============
				133: cliHistory: To detect whether CLI history is detected or not.
				134: cliHistoryNo:
				===============
				135: ntpConnectionFail: To detect whether NTP connection is failed or not.
				136: ntpConnectionFailNo:
				===============
				137: nmsConnectionTypeChanged:  To detect whether NMS connection type is changed.
				===============
				159: clockModuleRemoved:  To detect whether clock module is removed or installed.
				160: clockModuleInstalled:
				161: clockModuleInitFail:  To detect whether clock module initiolization is failed or not.
				162: clockModuleInitOk:
				===============
				163: cliHistoryLog: To detect whether CLI history log is over or not.
				164: cliHistoryLogNo:
				===============
				165: slotActionEvent: To detect whether slot action is changed.
				166: slotStateChange: To detect whether slot state is changed.
				===============
				167: interfaceAdminDown: To detect whether physical or logical interface's admin link status is up or down.
				168: interfaceAdminUp:
				===============
				169: slotPowerMonAbnormal: To detect whether slot power monitor abnormal or normal is detected.
				170: slotPowerMonNormal:
				===============
				171: slotErrorLEDChanged: To detect whether error LED is changed.
				===============
				185: cpuPpsOverThreshold: To detect whether PPS is over threshold or not.
				186: cpuPpsUnderThreshold:
				===============
				199: slotHealthStatusTimeout: To detect whether slot health status is time out or not.
				200: slotHealthStatusTimeoutCleared:
				===============
				201: advaTemperature: To detect whether current chassis temperature is less than chassis temperature threshold or not.
				202: advaTemperatureNo: 
				===============
				203: advaPSUFailure: To detect whether ADVA system's power supply unit has a failure or not.
				204: advaPSUFailureNo: 
				===============
				205: advaFanFailure: To detect whether ADVA system's FAN has a failure or not.
				206: advaFanFailureNo: 
				===============
				207: advaInterfaceReceiveFailure: To detect whether ADVA system's receipt has a failure or not.
				208: advaInterfaceReceiveFailureNo:  
				===============
				209: advaInterfaceOpticalThreshold: To detect whether Adva system's optical receive power level is 
								    less than optical threshold or not.
				210: advaInterfaceOpticalThresholdNo: 
				===============
				211: advaInterfaceTransmitFault: To detect whether ADVA system's transmission has a failure or not.
				212: advaInterfaceTransmitFaultNo: 
				===============
				213: dvaInterfaceMisconfiguration: To detect whether ADVA system's interface is configured rightly or not.
				214: advaInterfaceMisconfigurationNo: 
				===============
				215: advaInterfaceSFPMismatch: To detect whether ADVA system's SFP interface is mismatched or not.
				216: advaInterfaceSFPMismatchNo: 
				===============
				217: advaVoltageLow: To detect whether ADVA system's current voltage is less than voltage threshold or not.
				218: advaVoltageLowNo: 
				===============
				219: advaVoltageHigh: To detect whether ADVA system's current voltage is greater than voltage threshold or not.
				220: advaVoltageHighNo: 
				===============
				301: erpDomainLotp: To detect whether LOTP(Loss of Test Packet) exists a domain of ERP or not. 
						    The Loss of Test Packet defect is defined when a node does not receive 
						    any test packet at any of its ports for a period of 3 times.
				302: erpDomainLotpNo: 
				===============
				303: erpDomainULotp: To detect whether undirectional LOTP(Loss of Test Packet) exists a domain of ERP or not. 
						     The Loss of Test Packet defect is defined when a RM node of one domain does not 
						     receive any test packet at one port for a period of 3 times.
				304: erpDomainULotpNo: 
				===============
				305: erpDomainMultipleRM: To detect whether Multiple RM node is supported or not. 
							  The defect is raised when a RM node receives its own test packets 
							  with an Ack destination address field with a non-zero value.
				306: erpDomainMultipleRMNo: 
				===============
				307: erpDomainRMNodeReacheablity: To detect whether RM reachability is raised or not. 
								  The detection of multiple failures indicates that the ring is segmented and 
							          that the RM Node is unreacheable. 
								  This is only possible at normal ring nodes isolated from the RM node.
				308: erpDomainRMNodeReacheablityNo: 
				===============
				391: startupConfigLoadEnded: To detect whether startup configuration load is ended.
				===============
				401: eponOnuDeregister: To detect whether ONU is registered into OLT or not. 
							That is, ONU that its operation is service on should be sent registration information to OLT. 
				402: eponOnuRegister: 
				===============
				403: eponOnuRegistrationError: To detect whether ONU is failed registeration process into OLT.
				404: eponOnuNoRegistrationError: 
				===============
				405: eponBadEncryptionKey: To detect wwhether the encryption key is valid or not.
							   A message between ONU and OLT is encrypted using random encryption key. 
							   There is that the encryption key is invalid as transmission failure from time to time.
				406: eponNoBadEncryptionKey: 
				===============
				407: eponLlidMistmatch: To detect whether Llid of message between ONU and OLT is valid or not. 
							On registering, ONU informs unique ID to OLT.
							And then, all communication between ONU and OLT must use the unique ID. 
							The unique ID is called Llid.
				408: eponNoLlidMismatch: 
				===============
				409: eponTooManyRegister: To detect whether the registered ONU per 1 OLT is greater than 32 or not. 
							  That is, ONU can be registered from 1 to the maximum 32 at 1 OLT.
				410: eponNoTooManyRegister: 
				===============
				411: eponDyingGASP: To detect whether a ONU is down from dying gasp or not. 
						    A ONU could be changed to down state as a number of reasons.
						    By the way, ONU that is changed to down as dying gasp would be sent dying gasp signal to OLT and 
						    then ONU's link would be changed to down.
				412: eponNoDyingGASP: 
				===============
				413: eponOnuErrFramePeriod: 
				414: eponOnuNoErrFramePeriod: 
				===============
				415: eponOnuErrFrame: 
				416: eponOnuNoErrFrame: 
				===============
				417: eponOnuErrFrameSecondSummary: 
				418: eponOnuNoErrFrameSecondSummary: 
				===============
				419: eponOnuLastOnuDeregister: To detect whether a deregistered ONU is last ONU or not. 
							       If a deregistered ONU is last ONU, the OLT would be changed to serviceable status. 
				420: eponOnuNoLastOnuDeregister: 
				===============
				421: eponOltCableDown: 
				422: eponOltRecoverCableDown: 
				===============
				501: autoCLIStart: To detect whether the scheduled auto CLI is started or not.
				502: autoCLINoStart: 
				===============
				503: autoCLIComplete: To detect whether the scheduled auto CLI is completed or not. 
				504: autoCLINoComplete: 
				===============
				505: autoCLIRemoveOutputFile: To detect whether the result file of the scheduled auto CLI is removed or not.
							      The reason that the result file is removed is that the configured file size for the result  is
							      less than the stored result file size. 
							      If so, the oldest file would be removed before everything.
				506: autoCLINoRemoveOutputFile: 
				===============
				507: autoResetSystem: To detect whether the system is restarted or not. 
						      The conditions that system is restarted is that ping loss threshold is 
						      less than current ping loss count during the configured interval and 
						      that current free memory size is less than configured free memory size.
				508: autoResetNoSystem: 
				===============
				509: autoResetPingReplyLoss: To detect whether ping reply from the designated network node is received or not.
							     Operator designates any gateway system that can communicate to detect 
							     current network environment. 
							     System sends ICMP packet to the designated gateway system periodically. 
							     If  the system doesn't receive ping reply packet within any interval, 
							     operator recognizes that the system can't communicate any more 
							     because of some problems of the system. 
				510: autoResetNoPingReplyLoss: 
				===============
				511: autoResetMemoryLeakDetect: To detect whether current free memory size is 
								less than the configured free memory size or not. 
								Periodically, free memory size is checked to confirm system availability.
				512: autoResetNoMemoryLeakDetect: 
				===============
				601: arulePacketDropDetect: To detect whether it is dropped some packet by arule or not.
				602: arulePacketDropRelease: 
				===============
				620: bME1CardNoDetect: 
				621: clearBME1CardNoDetect: 
				===============
				622: bME1CardAFEerror: 
				623: clearBME1CardAFEerror: 
				===============
				624: bME1CardIFEerror: 
				625: clearBME1CardIFEerror: 
				===============
				626: bME1CardFWerror: 
				627: clearBME1CardFWerror: 
				===============
				628: bME1CardPROVerror: 
				629: clearBME1CardPROVerror: 
				===============
				630: bME1CrashDetect: 
				631: clearBME1CrashDetect: 
				===============
				632: bME2CardNoDetect: 
				633: clearBME2CardNoDetect: 
				===============
				634: bME2CardAFEerror: 
				635: clearBME2CardAFEerror: 
				===============
				636: bME2CardIFEerror: 
				637: clearBME2CardIFEerror: 
				===============
				638: bME2CardFWerror: 
				639: clearBME2CardFWerror: 
				===============
				640: bME2CardPROVerror: 
				641: clearBME2CardPROVerror: 
				===============
				642: bME2CrashDetect: 
				643: clearBME2CrashDetect: 
				===============
				644: bME3CardNoDetect: 
				645: clearBME3CardNoDetect: 
				===============
				646: bME3CardAFEerror: 
				647: clearBME3CardAFEerror: 
				===============
				648: bME3CardIFEerror: 
				649: clearBME3CardIFEerror: 
				===============
				650: bME3CardFWerror: 
				651: clearBME3CardFWerror: 
				===============
				652: bME3CardPROVerror: 
				653: clearBME3CardPROVerror: 
				===============
				654: bME3CrashDetect: 
				655: clearBME3CrashDetect: 
				===============
				656: powerFromBattery: 
				657: clearPowerFromBattery: 
				===============
				658: invalidBatteryStatus: 
				659: clearInvalidBatteryStatus: 
				===============
				660: batteryChargeLow: 
				661: clearBatteryChargeLow: 
				===============
				662: batteryNotPresent: 
				663: clearBatteryNotPresent: 
				===============
				664: voltageLow: 
				665: clearVoltageLow: 
				===============
				666: tempOverThreshold: 
				667: clearTempOverThreshold: 
				===============
				668: tempUnderThreshold: 
				669: clearTempUnderThreshold: 
				===============
				670: cpuOverThreshold: 
				671: clearCpuOverThreshold: 
				===============
				672: trafficOverload: 
				673: clearTrafficOverload: 
				===============
				674: gEPONModuleNotDetect: 
				675: clearGEPONModuleNotDetect:
				===============
				676: gEPONPortOperationDown: 
				677: clearGEPONPortOperationDown: 
				===============
				678: gEPONNoIncomingTraffic: 
				679: clearGEPONNoIncomingTraffic: 
				===============
				680: processCrashDetect: 
				681: clearProcessCrashDetect: 
				===============
				682: memoryLeakDetect: 
				683: clearMemoryLeakDetect: 
				===============
				684: memoryCorrupDetect: 
				685: clearMemoryCorrupDetect: 
				===============
				686: memoryLowDetect: 
				687: clearMemoryLowDetect: 
				===============
				688: dataLineerror: 
				689: clearDataLineerror: 
				===============
				690: addressLineerror: 
				691: clearAddressLineerror: 
				===============
				692: chipsetNotDetcet: 
				693: clearChipsetNotDetcet: 
				===============
				694: pciBuserror: 
				695: clearPciBuserror: 
				===============
				696: securityAdminConnect: 
				697: clearSecurityAdminConnect: 
				===============
				698: oNUPowerDown: 
				699: clearONUPowerDown: 
				===============
				700: oNUNotRegister: 
				701: clearONUNotRegister: 
				===============
				702: oNTOpticPre: 
				703: clearONTOpticPre: 
				===============
				800: switchoverInitiated: 
				===============
				801: switchoverDone: 
				===============
				803: redConfigurationMisMatch: To detect whether redundancy configuration is mismatched.
				===============
				901: gponNoAuthCBU: To detect no auth CBU is detected.
				902: gponDuplicateONU: To detect ONU is duplicated.
				903: gponDyingGasp: To detect dying GASP is detected.
				904: gponUpgradeComplete: To detect upgrade complete is detected.
				905: gponDeregistered: To detect whether deregistered is detected or not.
				906: gponRegistered: 
				907: gponRogueOnu: To detect rogue ONU is detected
				908: gponOnuBatteryEvent: To detect whether ONU battery event is detected or not.
				909: clearGponOnuBetteryEvent:
				910: gponOnuPortOperStatus: To detectONU port operation statue is chagned.
				911: gponTransceiverChanged: To detect transceiver is changed.
				912: gponOltLosOn: To detect whether OLT LOS is on or off
				913: gponOltLosOff:
				914: gponOltLosiOn: To detect whether OLT LOSI is on or off
				915: gponOltLosiOff:
				916: gponDyingGaspOn: To detect whether dying GASP is on or off
				917: gponDyingGaspOff:
				918: gponOntOSUpgradeStatus: To detect ONT OS upgrade status is changed.
				919: gponOntBLUpgradeStatus: To detect BL upgrade status is changed.
				920: gponOltRxPowerLoss: To detect OLT RX power is loss.
				921: gponOltRxPowerDetected: To detect OLT RX power status is changed.
				922: gponOnuTemperatureHighOverThreshold: To detect whether ONU temperature exceeds high threshold or not.
				923: gponOnuTemperatureHighFallThreshold:
				924: gponOnuTemperatureLowOverThreshold: To detect whether ONU temperature belows low threshold or not.
				925: gponOnuTemperatureLowFallThreshold:
				926: gponOnuCpuOverThreshold: To detect whether ONU CPU exceeds threshold or not.
				927: gponOnuCpuFallThreshold: 
				928: gponOnuMemoryOverThreshold: To detect whether memory exceeds threshold or not.
				929: gponOnuMemoryFallThreshold: 
				930: gponOnuI2cFail: To detect ONU L2C fail is detected.
				931: gponOnuRxOpticLowThreshAlarmOn: To detect whether ONU RX optic belows low threshold or not.
				932: gponOnuRxOpticLowThreshAlarmOff: 
				933: gponOnuRxOpticHighThreshAlarmOn: To detect whether ONU RX optic exceeds high threshold or not.
				934: gponOnuRxOpticHighThreshAlarmOff:
				935: gponOltLOFIOn: To detect whether OLT LOFL is on or off
				936: gponOltLOFIOff:
				937: gponOltDOWOn: To detect whether OLT DOW is on or off
				938: gponOltDOWOff:
				939: gponOltSFOn: To detect whether OLT SF is on or off
				940: gponOltSFOff:
				941: gponOltSDOn: To detect whether OLT SD is on or off
				942: gponOltSDOff:
				943: gponOltLCDGIOn: To detect whether OLT LCDGL is on or off
				944: gponOltLCDGIOff:
				945: gponOltRDOn: To detect whether OLT RD is on or off
				946: gponOltRDOff:
				947: gponOltSUFOn: To detect whether OLT SUF is on or off
				948: gponOltSUFOff:
				949: gponOltLOAOn: To detect whether OLT LOA is on or off
				950: gponOltLOAOff:
				951: gponOltLOAMIOn: To detect whether OLT LOAML is on or off
				952: gponOltLOAMIOff:
				953: gponOltMEMOn: To detect whether OLT MEM is on or off
				954: gponOltMEMOff:
				955: gponOltPEEOn: To detect whether OLT PEE is on or off
				956: gponOltPEEOff:
				957: gponOltPSTOn: To detect whether OLT PST is on or off
				958: gponOltPSTOff:
				959: gponOltERROn: To detect whether OLT ERR is on or off
				960: gponOltERROff:
				961: gponOltREIOn: To detect whether OLT REI is on or off
				962: gponOltREIOff:
				963: gponAntiSpoofingDupPortOn: To detect whether anti spoofing port is duplicated or not.
				964: gponAntiSpoofingDupPortOff:
				965: gponRedundancySwitchOver: To detect redundancy switchover is changed.
				966: gponDuplicatedRangingResponse: To detect ranging response is changed.
				967: gponOnuPortOpticModuleRemove: To detect whether ONU port optic module is removed or installed.
				968: gponOnuPortOpticModuleInstall:
				969: gponOnuOMCCProblemDetected: To detect whether ONU OMCC problem is detected or not.
				970: gponOnuOMCCProblemCleared:
				971: gponOltFixedTcontAlarmOn: To detect whether OLT fixed Tcont alarm is on or off.
				972: gponOltFixedTcontAlarmOff:
				973: gponOltDynamicTcontAlarmOn: To detect whether OLT dynamic Tcont alarm is on or off.
				974: gponOltDynamicTcontAlarmOff:
				975: gponOltPortCountAlarmOn: To detect whether OLT port count alarm is on or off.
				976: gponOltPortCountAlarmOff:
				977: gponOltCableDownAlarmOn: To detect whether OLT cable down alarm is on or off.
				978: gponOltCableDownAlarmOff:
				979: gponOltDeactiveMonitorAlarmOn: To detect whether deactive monitor alarm is on or off.
				980: gponOltDeactiveMonitorAlarmOff:
				981: gponOltDfiOn: To detect whether OLT DFI is on or off.
				982: gponOltDfiOff:
				984: gponOltTransceiverPortChanged: To detect OLT transeiver port is changed.
				985: gponOnuPortOperStatusDown: To detect whether ONU port operation status is down or up.
				986: gponOnuPortOperStatusUp::
				===============
				1101: emLogDefectCPUHighOver: To detect whether EM log detect CPU exceeds threshold or not.
				1102: emLogDefectCPUHighUnder:
				1103: emLogTemperHighOver: To detect whether EM log temperature exceeds high threshold or not.
				1104: emLogTemperHighUnder:
				1105: emLogTemperLowUnder: To detect whether EM log CPU belows low threshold or not.
				1106: emLogTemperLowOver:
				1107: emLogMemLowUnder:  To detect whether EM log memory belows low threshold or not.
				1108: emLogMemLowOver:
				1109: emLogFanFail:  To detect whether EM log fan status is failed or not.
				1110: emLogFanFailCleared:
				1111: emLogPhyCRCFail: To detect whether EM log physical CRC is failed or not.
				1112: emLogPhyCRCFailCleared:
				1113: emLogPhyDetectFail: To detect whether EM log physical status is failed or not.
				1114: emLogPhyDetectFailCleared:
				1115: emLogSFUMateInitFail: To detect whether EM log SFU mate initialization is failed or not.
				1116: emLogSFUMateInitFailCleared:
				1117: emLogDaemonHealthBad: To detect whether EM log daemon health is bad or not.
				1118: emLogDaemonHealthBadCleared:
				1119: emLogGPIURavenLinkDown: To detect whether EM log GPIU RAVEN link is down or not.
				1120: emLogGPIURavenLinkDownCleared:
				===============
				1151: slotNosUpgradeStart: To detect whether slot NOS upgrade is started or ended.
				1152: slotNosUpgradeEnd:
				===============
				1331: gponOnuAniVoltageLowThreshAlarmOn: To detect whether ONU ANI voltage belows low threshold or not.
				1332: gponOnuAniVoltageLowThreshAlarmOff:
				1333: gponOnuAniVoltageHighThreshAlarmOn: To detect whether ONU ANI voltage exceeds high threshold or not.
				1334: gponOnuAniVoltageHighThreshAlarmOff:
				1335: gponOnuAniTemperatureLowThreshAlarmOn: To detect whether ONU ANI temperature belows low threshold or not.
				1336: gponOnuAniTemperatureLowThreshAlarmOff:
				1337: gponOnuAniTemperatureHighThreshAlarmOn: To detect whether ONU ANI temperature exceeds high threshold or not.
				1338: gponOnuAniTemperatureHighThreshAlarmOff:
				1339: gponOnuAniTxBiasLowThreshAlarmOn: To detect whether ONU ANI TX bias belows low threshold or not.
				1340: gponOnuAniTxBiasLowThreshAlarmOff:
				1341: gponOnuAniTxBiasHighThreshAlarmOn: To detect whether ONU ANI TX bias exceeds high threshold or not. 
				1342: gponOnuAniTxBiasHighThreshAlarmOff:
				1343: gponOnuAniTxpowerLowThreshAlarmOn: To detect whether ONU ANI TX power belows low threshold or not.
				1344: gponOnuAniTxpowerLowThreshAlarmOff:
				1345: gponOnuAniTxpowerHighThreshAlarmOn: To detect whether ONU ANI TX power exceeds high threshold or not.
				1346: gponOnuAniTxpowerHighThreshAlarmOff:"
			::= { sleAlarmSeverityEntry 1 }

		
--   1.3.6.1.4.1.6296.101.4.2.1.1.2
-- 1.3.6.1.4.1.6296.101.4.2.1.1.2
		-- 1.3.6.1.4.1.6296.101.4.2.1.1.2
		sleAlarmSeverityValue OBJECT-TYPE
			SYNTAX INTEGER
				{
				critical(1),
				major(2),
				minor(3),
				warning(4),
				intermediate(5)
				}
			MAX-ACCESS read-only
			STATUS current
			DESCRIPTION
				" The severity of alarm. "
			::= { sleAlarmSeverityEntry 2 }

		
--   1.3.6.1.4.1.6296.101.4.2.2
-- 1.3.6.1.4.1.6296.101.4.2.2
		-- 1.3.6.1.4.1.6296.101.4.2.2
		sleAlarmSeverityControl OBJECT IDENTIFIER ::= { sleAlarmSeverity 2 }

		
--   1.3.6.1.4.1.6296.101.4.2.2.1
-- 1.3.6.1.4.1.6296.101.4.2.2.1
		-- 1.3.6.1.4.1.6296.101.4.2.2.1
		sleAlarmSeverityControlRequest OBJECT-TYPE
			SYNTAX INTEGER
				{
				createAlarmSeveriity(1),
				destroyAlarmSeveriity(2),
				setAlarmSeveriity(3)
				}
			MAX-ACCESS read-write
			STATUS current
			DESCRIPTION
				" This attribute identifies the control commands.
				updateAlarmList:
				   the NE updates entries of alarms in the sleAlarmListTable
				   after having changed alarm severities of alarms 
				   (due to change profile pointers in
				   managed entities or after modification of alarm severities 
				   in profiles). This command should be applied once after having 
				   finisled modifications of severties.
				modifyAlarmSeverity: 
				   modifies the severity of an alarm in specific profile.
				createAlarmSeverityProfile: 
				   creates a new profile with default severities.
				   The severities then have to be modified with command changeAlarmSeverity.
				deleteAlarmSeverityProfile: 
				   deletes a profile. Profile 1 is not allowed to be deleted.
				 
				Notifications : none "
			::= { sleAlarmSeverityControl 1 }

		
--   1.3.6.1.4.1.6296.101.4.2.2.2
-- 1.3.6.1.4.1.6296.101.4.2.2.2
		-- 1.3.6.1.4.1.6296.101.4.2.2.2
		sleAlarmSeverityControlStatus OBJECT-TYPE
			SYNTAX SleControlStatusType
			MAX-ACCESS read-only
			STATUS current
			DESCRIPTION
				" The status of a control request. "
			::= { sleAlarmSeverityControl 2 }

		
--   1.3.6.1.4.1.6296.101.4.2.2.3
-- 1.3.6.1.4.1.6296.101.4.2.2.3
		-- 1.3.6.1.4.1.6296.101.4.2.2.3
		sleAlarmSeverityControlTimer OBJECT-TYPE
			SYNTAX Unsigned32
			MAX-ACCESS read-write
			STATUS current
			DESCRIPTION
				" The maximum wait time for the manager for command ending.
				For long running commands.
				The manager reads this value from the DSLAM. "
			::= { sleAlarmSeverityControl 3 }

		
--   1.3.6.1.4.1.6296.101.4.2.2.4
-- 1.3.6.1.4.1.6296.101.4.2.2.4
		-- 1.3.6.1.4.1.6296.101.4.2.2.4
		sleAlarmSeverityControlTimeStamp OBJECT-TYPE
			SYNTAX TimeTicks
			MAX-ACCESS read-only
			STATUS current
			DESCRIPTION
				" The time stamp of the last command (end of command). "
			::= { sleAlarmSeverityControl 4 }

		
--   1.3.6.1.4.1.6296.101.4.2.2.5
-- 1.3.6.1.4.1.6296.101.4.2.2.5
		-- 1.3.6.1.4.1.6296.101.4.2.2.5
		sleAlarmSeverityControlReqResult OBJECT-TYPE
			SYNTAX SleControlRequestResultType
			MAX-ACCESS read-only
			STATUS current
			DESCRIPTION
				" The result of the last user command. "
			::= { sleAlarmSeverityControl 5 }

		
--    1.3.6.1.4.1.6296.101.4.2.2.6
-- 1.3.6.1.4.1.6296.101.4.2.2.6
-- 1.3.6.1.4.1.6296.101.4.2.2.6
		-- 1.3.6.1.4.1.6296.101.4.2.2.6
		sleAlarmSeverityControlIndex OBJECT-TYPE
			SYNTAX SpecificNum
			MAX-ACCESS read-write
			STATUS current
			DESCRIPTION
				" A number identifying this alarm severity profile. 
				The following alarms is devided by the specific character, ===============.
				The division basis is that alarms is bounded or released.
				
				001: portDown: To detect whether physical or logical interface's link status is up or down.
				002: portUp: 
				===============
				003: portRemoved: To detect whether physical interface is installed or not.
				004: portInstalled: 
				===============
				005: powerFail: To detect whether power module's operation status is good or not.
						(Without doubt, more than 1 power module should be equipped.)
				006: powerOK: 
				===============
				007: powerRemoved: To detect whether power module is installed or not, through the PLD access.
						   (Without doubt, more than 1 power module should be equipped.)
				008: powerInstalled: 
				===============
				009: fanFail: To detect whether FAN module's operation status is good or not.
				010: fanOK: 
				===============
				011: fanRemoved: To detect whether FAN module is installed or not, through the PLD access.
				012: fanInstalled: 
				===============
				013: moduleRemoved: To detect whether physical interface module is installed or not, through the S/W I2C
				014: moduleInstalled: 
				===============
				015: systemRestart: Network system is restarted by operator. This is not H/W start but S/W start.
				===============
				016: systemStart: Network system is restarted by operator or system status. This is not S/W start but H/W start.
						  (This alarm isn’t used current)
				===============
				017: broadcastOver: To detect the receipt of broadcast packet.
				 			    (This alarm isn’t used current)
				018: broadcastUnder: 
				===============
				019: cpuOverLoad: To detect whether the configured CPU load threshold is less than current CPU load usage or not.
				020: cpuUnderLoad: 
				===============
				021: memoryOverUsed: To detect whether the configured memory threshold is less than current memory usage or not.
				022: memoryUnderUsed: 
				===============
				023: portOverThreshold: To detect whether the configured physical or logical interface threshold is 
							less than delta value of current interface's InOctects or not.
				024: portUnderThreshold: 
				===============
				025: temperatureHigh: To detect whether the configured system's temperature threshold is 
						      less than current temperature or not.
				026: temperatureLow: 
				===============
				027: mfgdBlocked: To detect whether the specific MAC by MAC flood guard is blocked or not.
				028: mfgdReleased: 
				===============
				029: ipConflict: To detect whether the same IP address on different network node is configured or not.
				030: ipUnconflict: 
				===============
				031: dhcpLeaseShortage: To detect whether IP address that can be assigned to subscriber by DHCP server is 
							sufficient or not.
				032: dhcpLeaseSufficient: 
				===============
				033: dhcpOccuredIllegalEntry: To detect whether a subsceiber is using a static IP address or not.
				034: dhcpRemovedIllegalEntry: 
				===============
				035: rmonAlarmRising: To detect whether rising threshold of a specific MO in RMON alarm sampling is 
						      less than current calculated value by alarm sample type or not. But alarm generation 
						      would be issued by means of event type in RMON event.
				036: rmonAlarmNoRising: 
				===============
				037: rmonAlarmFalling: To detect whether falling threshold of a specific MO in RMON alarm sampling is 
						       less than current calculated value by alarm sample type or not. 
						       But alarm generation would be issued by means of event type in RMON event.
				038: rmonAlarmNoFalling: 
				===============
				039: bpduGuardDisabled: To detect whether edge ports is guarded about superior BPDU or not. 
							In case of insertion edge node with 0 or lower priority than priority of current root bridge node, 
							it will be disarrangement during a short time because of recognition a new inserted node 
							as root bridge. 
							So these edge ports is guarded, and then edge ports is blocked about all superior BPDU. 
							So STP reconfiguration doesn't use this edge ports.
				===============
				040: rootGuardDisabled: To detect whether edge ports is guarded about superior BPDU or not. 
							In case of insertion edge node with 0 or lower priority than priority of current root bridge node, 
							it will be disarrangement during a short time because of recognition a new inserted node 
							as root bridge. 
							So, Root guard prevents a new inserted node from being root bridge as well as 
							receiving a superior BPDU from root bridge. 
							but this node participates in STP topology reconfiguration. 
							If root bridge does not send a superior BPDU, then this node acts usually though STP state change.
				===============
				041: portSecurity: To detect whether interface is configured for security or not. 
						   This can be used to prevent MAC from flooding as well as spoofing. 
						   That is, As a result, this will obstruct an attack as like DoS attack.
				===============
				042: userLogin: 
				043: userLogout: 
				===============
				051: igmpGroupJoined: To detect whether a subscriber is joined a multicast group or not.
				052: igmpGroupLeaved: 
				===============
				053: dhcpIpaddressBound: To detect wether a dynamic IP address is assigned to a subscriber or not.
				054: dhcpIpaddressFree: 
				===============
				055: doorOpened: To detect whether outer door is opeded or not, as external alarm.
				056: doorClosed: 
				===============
				057: powerModeChangedPowerToBattery: To detect whether a system is using AC power or battery. 
								     A system is using AC power usually. 
								     If there is any power problems as like a power failure, 
								     a system is using battery instead of AC power. 
				058: powerModeChangedBatteryToPower: 
				===============
				059: batterylowcapacity: To detect whether current battery capacity is less 
							 capacity threshold according to battery usage or not. 
							 The capacity of AC power is 16 voltage and battery is 20. 
							 Capacity threshold is configured by H/W specification.
							 So operator can't change it.
				060: batterynormalcapacity: 
				===============
				061: batteryhighTemperature: To detect whether current temperature of battery is greater than temperature threshold or not. 
				062: batterynormalTemperature: 
				===============
				063: authenticationFail: To detect whether the connected user is authentic or non-authentic.
				064: authenticationNofail: 
				===============
				065: psuAcHighTemperature: To detect whether current temperature of Power Supply Unit is 
							   greater than temperature threshold or not. 
				066: psuAcNormalTemperature: 
				===============
				067: batteryRemoved: To detect whether battery is equipped at network system or not. 
						     Battery is used as redundancy power service. So operator can decide the installation of battery.
				068: batteryEquipped: 
				===============
				069: batteryLowVoltage: To detect whether battery voltage is less than 12.5 volt or not. 
							12.5 volt value is configured by H/W specification. So operator can't change it.
				070: batteryNormalVoltage: 
				===============
				071: adminAccessLogin: To detect whether a operator connects at this network system or not.
				072: adminAccessLogout: 
				===============
				073: cfgdBlocked: To detect whether it is blocked flood to CPU or not.
				074: cfgdReleased: 
				===============
				075: sfgdBlocked: To detect whether it is blocked flood to system or not.
				076: sfgdReleased: 
				===============
				077: swWatchdogAbnormalState: To detect whether a specific process acts normally or not.
				078: swWatchdogNormalState: 
				===============
				079: swWatchdogDetectError: To detect whether a specific process is detected a error related to itself or cleared.
				080: swWatchdogClearError: 
				===============
				081: ppsControlBlocked: To detect whether it is blocked by pps-control or not.
				082: ppsControlReleased: 
				===============
				083: gotDMITempHighOverAlarm: To detect whether internal temperature exceeds high alarm level or not.
				084: gotDMITempHighFallAlarm: 
				===============
				085: gotDMITempLowOverAlarm: To detect whether internal temperature is below low alarm level or not.
				086: gotDMITempLowFallAlarm: 
				===============
				087: gotDMITempHighOverWarning: To detect whether internal temperature exceeds high warning level or not.
				088: gotDMITempHighFallWarning: 
				===============
				089: gotDMITempLowOverWarning: To detect whether internal temperature is below low warning level or not.
				090: gotDMITempLowFallWarning: 
				===============
				091: gotDMIVolHighOverAlarm: To detect whether internal supply voltage exceeds high alarm level or not.
				092: gotDMIVolHighFallAlarm: 
				===============
				093: gotDMIVolLowOverAlarm: To detect whether internal supply voltage is below low alarm level or not.
				094: gotDMIVolLowFallAlarm: 
				===============
				095: gotDMIVolHighOverWarning: To detect whether internal supply voltage exceeds high warning level or not.
				096: gotDMIVolHighFallWarning: 
				===============
				097: gotDMIVolLowOverWarning: To detect whether internal supply voltage is below low warning level or not.
				098: gotDMIVolLowFallWarning: 
				===============
				099: gotDMITxBiasHighOverAlarm: To detect whether TX Bias current exceeds high alarm level or not.
				100: gotDMITxBiasHighFallAlarm: 
				===============
				101: gotDMITxBiasLowOverAlarm: To detect whether TX Bias current is below low alarm level or not.
				102: gotDMITxBiasLowFallAlarm: 
				===============
				103: gotDMITxBiasHighOverWarning: To detect whether TX Bias current exceeds high warning level or not.
				104: gotDMITxBiasHighFallWarning: 
				===============
				105: gotDMITxBiasLowOverWarning: To detect whether TX Bias current is below low warning level or not.
				106: gotDMITxBiasLowFallWarning: 
				===============
				107: gotDMITxPowerHighOverAlarm: To detect whether TX output power exceeds high alarm level or not.
				108: gotDMITxPowerHighFallAlarm: 
				===============
				109: gotDMITxPowerLowOverAlarm: To detect whether TX output power is below low alarm level or not.
				110: gotDMITxPowerLowFallAlarm: 
				===============
				111: gotDMITxPowerHighOverWarning: To detect whether TX output power exceeds high warning level or not.
				112: gotDMITxPowerHighFallWarning: 
				===============
				113: gotDMITxPowerLowOverWarning: To detect whether TX output power is below low warning level or not.
				114: gotDMITxPowerLowFallWarning: 
				===============
				115: gotDMIRxPowerHighOverAlarm: To detect whether RX output power exceeds high alarm level or not.
				116: gotDMIRxPowerHighFallAlarm: 
				===============
				117: gotDMIRxPowerLowOverAlarm: To detect whether RX output power is below low alarm level or not.
				118: gotDMIRxPowerLowFallAlarm: 
				===============
				119: gotDMIRxPowerHighOverWarning: To detect whether RX output power exceeds high warning level or not.
				120: gotDMIRxPowerHighFallWarning: 
				===============
				121: gotDMIRxPowerLowOverWarning: To detect whether RX output power is below low warning level or not.
				122: gotDMIRxPowerLowFallWarning: 
				===============
				123: nosRemoteUpgradeRequest: 
				124: nosRemoteUpgradeSuccess: 
				125: nosRemoteUpgradeFailAbort: 
				126: nosRemoteUpgradeFailHeaderError: 
				127: nosRemoteUpgradeFailDownloadError: 
				128: nosRemoteUpgradeFailFlashError: 
				129: nosRemoteUpgradeStart: 
				===============
				130: systemDyingGasp:
				===============
				133: cliHistory: To detect whether CLI history is detected or not.
				134: cliHistoryNo:
				===============
				135: ntpConnectionFail: To detect whether NTP connection is failed or not.
				136: ntpConnectionFailNo:
				===============
				137: nmsConnectionTypeChanged:  To detect whether NMS connection type is changed.
				===============
				159: clockModuleRemoved:  To detect whether clock module is removed or installed.
				160: clockModuleInstalled:
				161: clockModuleInitFail:  To detect whether clock module initiolization is failed or not.
				162: clockModuleInitOk:
				===============
				163: cliHistoryLog: To detect whether CLI history log is over or not.
				164: cliHistoryLogNo:
				===============
				165: slotActionEvent: To detect whether slot action is changed.
				166: slotStateChange: To detect whether slot state is changed.
				===============
				167: interfaceAdminDown: To detect whether physical or logical interface's admin link status is up or down.
				168: interfaceAdminUp:
				===============
				169: slotPowerMonAbnormal: To detect whether slot power monitor abnormal or normal is detected.
				170: slotPowerMonNormal:
				===============
				171: slotErrorLEDChanged: To detect whether error LED is changed.
				===============
				185: cpuPpsOverThreshold: To detect whether PPS is over threshold or not.
				186: cpuPpsUnderThreshold:
				===============
				199: slotHealthStatusTimeout: To detect whether slot health status is time out or not.
				200: slotHealthStatusTimeoutCleared:
				===============
				201: advaTemperature: To detect whether current chassis temperature is less than chassis temperature threshold or not.
				202: advaTemperatureNo: 
				===============
				203: advaPSUFailure: To detect whether ADVA system's power supply unit has a failure or not.
				204: advaPSUFailureNo: 
				===============
				205: advaFanFailure: To detect whether ADVA system's FAN has a failure or not.
				206: advaFanFailureNo: 
				===============
				207: advaInterfaceReceiveFailure: To detect whether ADVA system's receipt has a failure or not.
				208: advaInterfaceReceiveFailureNo:  
				===============
				209: advaInterfaceOpticalThreshold: To detect whether Adva system's optical receive power level is 
								    less than optical threshold or not.
				210: advaInterfaceOpticalThresholdNo: 
				===============
				211: advaInterfaceTransmitFault: To detect whether ADVA system's transmission has a failure or not.
				212: advaInterfaceTransmitFaultNo: 
				===============
				213: dvaInterfaceMisconfiguration: To detect whether ADVA system's interface is configured rightly or not.
				214: advaInterfaceMisconfigurationNo: 
				===============
				215: advaInterfaceSFPMismatch: To detect whether ADVA system's SFP interface is mismatched or not.
				216: advaInterfaceSFPMismatchNo: 
				===============
				217: advaVoltageLow: To detect whether ADVA system's current voltage is less than voltage threshold or not.
				218: advaVoltageLowNo: 
				===============
				219: advaVoltageHigh: To detect whether ADVA system's current voltage is greater than voltage threshold or not.
				220: advaVoltageHighNo: 
				===============
				301: erpDomainLotp: To detect whether LOTP(Loss of Test Packet) exists a domain of ERP or not. 
						    The Loss of Test Packet defect is defined when a node does not receive 
						    any test packet at any of its ports for a period of 3 times.
				302: erpDomainLotpNo: 
				===============
				303: erpDomainULotp: To detect whether undirectional LOTP(Loss of Test Packet) exists a domain of ERP or not. 
						     The Loss of Test Packet defect is defined when a RM node of one domain does not 
						     receive any test packet at one port for a period of 3 times.
				304: erpDomainULotpNo: 
				===============
				305: erpDomainMultipleRM: To detect whether Multiple RM node is supported or not. 
							  The defect is raised when a RM node receives its own test packets 
							  with an Ack destination address field with a non-zero value.
				306: erpDomainMultipleRMNo: 
				===============
				307: erpDomainRMNodeReacheablity: To detect whether RM reachability is raised or not. 
								  The detection of multiple failures indicates that the ring is segmented and 
							          that the RM Node is unreacheable. 
								  This is only possible at normal ring nodes isolated from the RM node.
				308: erpDomainRMNodeReacheablityNo: 
				===============
				391: startupConfigLoadEnded: To detect whether startup configuration load is ended.
				===============
				401: eponOnuDeregister: To detect whether ONU is registered into OLT or not. 
							That is, ONU that its operation is service on should be sent registration information to OLT. 
				402: eponOnuRegister: 
				===============
				403: eponOnuRegistrationError: To detect whether ONU is failed registeration process into OLT.
				404: eponOnuNoRegistrationError: 
				===============
				405: eponBadEncryptionKey: To detect wwhether the encryption key is valid or not.
							   A message between ONU and OLT is encrypted using random encryption key. 
							   There is that the encryption key is invalid as transmission failure from time to time.
				406: eponNoBadEncryptionKey: 
				===============
				407: eponLlidMistmatch: To detect whether Llid of message between ONU and OLT is valid or not. 
							On registering, ONU informs unique ID to OLT.
							And then, all communication between ONU and OLT must use the unique ID. 
							The unique ID is called Llid.
				408: eponNoLlidMismatch: 
				===============
				409: eponTooManyRegister: To detect whether the registered ONU per 1 OLT is greater than 32 or not. 
							  That is, ONU can be registered from 1 to the maximum 32 at 1 OLT.
				410: eponNoTooManyRegister: 
				===============
				411: eponDyingGASP: To detect whether a ONU is down from dying gasp or not. 
						    A ONU could be changed to down state as a number of reasons.
						    By the way, ONU that is changed to down as dying gasp would be sent dying gasp signal to OLT and 
						    then ONU's link would be changed to down.
				412: eponNoDyingGASP: 
				===============
				413: eponOnuErrFramePeriod: 
				414: eponOnuNoErrFramePeriod: 
				===============
				415: eponOnuErrFrame: 
				416: eponOnuNoErrFrame: 
				===============
				417: eponOnuErrFrameSecondSummary: 
				418: eponOnuNoErrFrameSecondSummary: 
				===============
				419: eponOnuLastOnuDeregister: To detect whether a deregistered ONU is last ONU or not. 
							       If a deregistered ONU is last ONU, the OLT would be changed to serviceable status. 
				420: eponOnuNoLastOnuDeregister: 
				===============
				421: eponOltCableDown: 
				422: eponOltRecoverCableDown: 
				===============
				501: autoCLIStart: To detect whether the scheduled auto CLI is started or not.
				502: autoCLINoStart: 
				===============
				503: autoCLIComplete: To detect whether the scheduled auto CLI is completed or not. 
				504: autoCLINoComplete: 
				===============
				505: autoCLIRemoveOutputFile: To detect whether the result file of the scheduled auto CLI is removed or not.
							      The reason that the result file is removed is that the configured file size for the result  is
							      less than the stored result file size. 
							      If so, the oldest file would be removed before everything.
				506: autoCLINoRemoveOutputFile: 
				===============
				507: autoResetSystem: To detect whether the system is restarted or not. 
						      The conditions that system is restarted is that ping loss threshold is 
						      less than current ping loss count during the configured interval and 
						      that current free memory size is less than configured free memory size.
				508: autoResetNoSystem: 
				===============
				509: autoResetPingReplyLoss: To detect whether ping reply from the designated network node is received or not.
							     Operator designates any gateway system that can communicate to detect 
							     current network environment. 
							     System sends ICMP packet to the designated gateway system periodically. 
							     If  the system doesn't receive ping reply packet within any interval, 
							     operator recognizes that the system can't communicate any more 
							     because of some problems of the system. 
				510: autoResetNoPingReplyLoss: 
				===============
				511: autoResetMemoryLeakDetect: To detect whether current free memory size is 
								less than the configured free memory size or not. 
								Periodically, free memory size is checked to confirm system availability.
				512: autoResetNoMemoryLeakDetect: 
				===============
				601: arulePacketDropDetect: To detect whether it is dropped some packet by arule or not.
				602: arulePacketDropRelease: 
				===============
				620: bME1CardNoDetect: 
				621: clearBME1CardNoDetect: 
				===============
				622: bME1CardAFEerror: 
				623: clearBME1CardAFEerror: 
				===============
				624: bME1CardIFEerror: 
				625: clearBME1CardIFEerror: 
				===============
				626: bME1CardFWerror: 
				627: clearBME1CardFWerror: 
				===============
				628: bME1CardPROVerror: 
				629: clearBME1CardPROVerror: 
				===============
				630: bME1CrashDetect: 
				631: clearBME1CrashDetect: 
				===============
				632: bME2CardNoDetect: 
				633: clearBME2CardNoDetect: 
				===============
				634: bME2CardAFEerror: 
				635: clearBME2CardAFEerror: 
				===============
				636: bME2CardIFEerror: 
				637: clearBME2CardIFEerror: 
				===============
				638: bME2CardFWerror: 
				639: clearBME2CardFWerror: 
				===============
				640: bME2CardPROVerror: 
				641: clearBME2CardPROVerror: 
				===============
				642: bME2CrashDetect: 
				643: clearBME2CrashDetect: 
				===============
				644: bME3CardNoDetect: 
				645: clearBME3CardNoDetect: 
				===============
				646: bME3CardAFEerror: 
				647: clearBME3CardAFEerror: 
				===============
				648: bME3CardIFEerror: 
				649: clearBME3CardIFEerror: 
				===============
				650: bME3CardFWerror: 
				651: clearBME3CardFWerror: 
				===============
				652: bME3CardPROVerror: 
				653: clearBME3CardPROVerror: 
				===============
				654: bME3CrashDetect: 
				655: clearBME3CrashDetect: 
				===============
				656: powerFromBattery: 
				657: clearPowerFromBattery: 
				===============
				658: invalidBatteryStatus: 
				659: clearInvalidBatteryStatus: 
				===============
				660: batteryChargeLow: 
				661: clearBatteryChargeLow: 
				===============
				662: batteryNotPresent: 
				663: clearBatteryNotPresent: 
				===============
				664: voltageLow: 
				665: clearVoltageLow: 
				===============
				666: tempOverThreshold: 
				667: clearTempOverThreshold: 
				===============
				668: tempUnderThreshold: 
				669: clearTempUnderThreshold: 
				===============
				670: cpuOverThreshold: 
				671: clearCpuOverThreshold: 
				===============
				672: trafficOverload: 
				673: clearTrafficOverload: 
				===============
				674: gEPONModuleNotDetect: 
				675: clearGEPONModuleNotDetect:
				===============
				676: gEPONPortOperationDown: 
				677: clearGEPONPortOperationDown: 
				===============
				678: gEPONNoIncomingTraffic: 
				679: clearGEPONNoIncomingTraffic: 
				===============
				680: processCrashDetect: 
				681: clearProcessCrashDetect: 
				===============
				682: memoryLeakDetect: 
				683: clearMemoryLeakDetect: 
				===============
				684: memoryCorrupDetect: 
				685: clearMemoryCorrupDetect: 
				===============
				686: memoryLowDetect: 
				687: clearMemoryLowDetect: 
				===============
				688: dataLineerror: 
				689: clearDataLineerror: 
				===============
				690: addressLineerror: 
				691: clearAddressLineerror: 
				===============
				692: chipsetNotDetcet: 
				693: clearChipsetNotDetcet: 
				===============
				694: pciBuserror: 
				695: clearPciBuserror: 
				===============
				696: securityAdminConnect: 
				697: clearSecurityAdminConnect: 
				===============
				698: oNUPowerDown: 
				699: clearONUPowerDown: 
				===============
				700: oNUNotRegister: 
				701: clearONUNotRegister: 
				===============
				702: oNTOpticPre: 
				703: clearONTOpticPre: 
				===============
				800: switchoverInitiated: 
				===============
				801: switchoverDone: 
				===============
				803: redConfigurationMisMatch: To detect whether redundancy configuration is mismatched.
				===============
				901: gponNoAuthCBU: To detect no auth CBU is detected.
				902: gponDuplicateONU: To detect ONU is duplicated.
				903: gponDyingGasp: To detect dying GASP is detected.
				904: gponUpgradeComplete: To detect upgrade complete is detected.
				905: gponDeregistered: To detect whether deregistered is detected or not.
				906: gponRegistered: 
				907: gponRogueOnu: To detect rogue ONU is detected
				908: gponOnuBatteryEvent: To detect whether ONU battery event is detected or not.
				909: clearGponOnuBetteryEvent:
				910: gponOnuPortOperStatus: To detectONU port operation statue is chagned.
				911: gponTransceiverChanged: To detect transceiver is changed.
				912: gponOltLosOn: To detect whether OLT LOS is on or off
				913: gponOltLosOff:
				914: gponOltLosiOn: To detect whether OLT LOSI is on or off
				915: gponOltLosiOff:
				916: gponDyingGaspOn: To detect whether dying GASP is on or off
				917: gponDyingGaspOff:
				918: gponOntOSUpgradeStatus: To detect ONT OS upgrade status is changed.
				919: gponOntBLUpgradeStatus: To detect BL upgrade status is changed.
				920: gponOltRxPowerLoss: To detect OLT RX power is loss.
				921: gponOltRxPowerDetected: To detect OLT RX power status is changed.
				922: gponOnuTemperatureHighOverThreshold: To detect whether ONU temperature exceeds high threshold or not.
				923: gponOnuTemperatureHighFallThreshold:
				924: gponOnuTemperatureLowOverThreshold: To detect whether ONU temperature belows low threshold or not.
				925: gponOnuTemperatureLowFallThreshold:
				926: gponOnuCpuOverThreshold: To detect whether ONU CPU exceeds threshold or not.
				927: gponOnuCpuFallThreshold: 
				928: gponOnuMemoryOverThreshold: To detect whether memory exceeds threshold or not.
				929: gponOnuMemoryFallThreshold: 
				930: gponOnuI2cFail: To detect ONU L2C fail is detected.
				931: gponOnuRxOpticLowThreshAlarmOn: To detect whether ONU RX optic belows low threshold or not.
				932: gponOnuRxOpticLowThreshAlarmOff: 
				933: gponOnuRxOpticHighThreshAlarmOn: To detect whether ONU RX optic exceeds high threshold or not.
				934: gponOnuRxOpticHighThreshAlarmOff:
				935: gponOltLOFIOn: To detect whether OLT LOFL is on or off
				936: gponOltLOFIOff:
				937: gponOltDOWOn: To detect whether OLT DOW is on or off
				938: gponOltDOWOff:
				939: gponOltSFOn: To detect whether OLT SF is on or off
				940: gponOltSFOff:
				941: gponOltSDOn: To detect whether OLT SD is on or off
				942: gponOltSDOff:
				943: gponOltLCDGIOn: To detect whether OLT LCDGL is on or off
				944: gponOltLCDGIOff:
				945: gponOltRDOn: To detect whether OLT RD is on or off
				946: gponOltRDOff:
				947: gponOltSUFOn: To detect whether OLT SUF is on or off
				948: gponOltSUFOff:
				949: gponOltLOAOn: To detect whether OLT LOA is on or off
				950: gponOltLOAOff:
				951: gponOltLOAMIOn: To detect whether OLT LOAML is on or off
				952: gponOltLOAMIOff:
				953: gponOltMEMOn: To detect whether OLT MEM is on or off
				954: gponOltMEMOff:
				955: gponOltPEEOn: To detect whether OLT PEE is on or off
				956: gponOltPEEOff:
				957: gponOltPSTOn: To detect whether OLT PST is on or off
				958: gponOltPSTOff:
				959: gponOltERROn: To detect whether OLT ERR is on or off
				960: gponOltERROff:
				961: gponOltREIOn: To detect whether OLT REI is on or off
				962: gponOltREIOff:
				963: gponAntiSpoofingDupPortOn: To detect whether anti spoofing port is duplicated or not.
				964: gponAntiSpoofingDupPortOff:
				965: gponRedundancySwitchOver: To detect redundancy switchover is changed.
				966: gponDuplicatedRangingResponse: To detect ranging response is changed.
				967: gponOnuPortOpticModuleRemove: To detect whether ONU port optic module is removed or installed.
				968: gponOnuPortOpticModuleInstall:
				969: gponOnuOMCCProblemDetected: To detect whether ONU OMCC problem is detected or not.
				970: gponOnuOMCCProblemCleared:
				971: gponOltFixedTcontAlarmOn: To detect whether OLT fixed Tcont alarm is on or off.
				972: gponOltFixedTcontAlarmOff:
				973: gponOltDynamicTcontAlarmOn: To detect whether OLT dynamic Tcont alarm is on or off.
				974: gponOltDynamicTcontAlarmOff:
				975: gponOltPortCountAlarmOn: To detect whether OLT port count alarm is on or off.
				976: gponOltPortCountAlarmOff:
				977: gponOltCableDownAlarmOn: To detect whether OLT cable down alarm is on or off.
				978: gponOltCableDownAlarmOff:
				979: gponOltDeactiveMonitorAlarmOn: To detect whether deactive monitor alarm is on or off.
				980: gponOltDeactiveMonitorAlarmOff:
				981: gponOltDfiOn: To detect whether OLT DFI is on or off.
				982: gponOltDfiOff:
				984: gponOltTransceiverPortChanged: To detect OLT transeiver port is changed.
				985: gponOnuPortOperStatusDown: To detect whether ONU port operation status is down or up.
				986: gponOnuPortOperStatusUp::
				===============
				1101: emLogDefectCPUHighOver: To detect whether EM log detect CPU exceeds threshold or not.
				1102: emLogDefectCPUHighUnder:
				1103: emLogTemperHighOver: To detect whether EM log temperature exceeds high threshold or not.
				1104: emLogTemperHighUnder:
				1105: emLogTemperLowUnder: To detect whether EM log CPU belows low threshold or not.
				1106: emLogTemperLowOver:
				1107: emLogMemLowUnder:  To detect whether EM log memory belows low threshold or not.
				1108: emLogMemLowOver:
				1109: emLogFanFail:  To detect whether EM log fan status is failed or not.
				1110: emLogFanFailCleared:
				1111: emLogPhyCRCFail: To detect whether EM log physical CRC is failed or not.
				1112: emLogPhyCRCFailCleared:
				1113: emLogPhyDetectFail: To detect whether EM log physical status is failed or not.
				1114: emLogPhyDetectFailCleared:
				1115: emLogSFUMateInitFail: To detect whether EM log SFU mate initialization is failed or not.
				1116: emLogSFUMateInitFailCleared:
				1117: emLogDaemonHealthBad: To detect whether EM log daemon health is bad or not.
				1118: emLogDaemonHealthBadCleared:
				1119: emLogGPIURavenLinkDown: To detect whether EM log GPIU RAVEN link is down or not.
				1120: emLogGPIURavenLinkDownCleared:
				===============
				1151: slotNosUpgradeStart: To detect whether slot NOS upgrade is started or ended.
				1152: slotNosUpgradeEnd:
				===============
				1331: gponOnuAniVoltageLowThreshAlarmOn: To detect whether ONU ANI voltage belows low threshold or not.
				1332: gponOnuAniVoltageLowThreshAlarmOff:
				1333: gponOnuAniVoltageHighThreshAlarmOn: To detect whether ONU ANI voltage exceeds high threshold or not.
				1334: gponOnuAniVoltageHighThreshAlarmOff:
				1335: gponOnuAniTemperatureLowThreshAlarmOn: To detect whether ONU ANI temperature belows low threshold or not.
				1336: gponOnuAniTemperatureLowThreshAlarmOff:
				1337: gponOnuAniTemperatureHighThreshAlarmOn: To detect whether ONU ANI temperature exceeds high threshold or not.
				1338: gponOnuAniTemperatureHighThreshAlarmOff:
				1339: gponOnuAniTxBiasLowThreshAlarmOn: To detect whether ONU ANI TX bias belows low threshold or not.
				1340: gponOnuAniTxBiasLowThreshAlarmOff:
				1341: gponOnuAniTxBiasHighThreshAlarmOn: To detect whether ONU ANI TX bias exceeds high threshold or not. 
				1342: gponOnuAniTxBiasHighThreshAlarmOff:
				1343: gponOnuAniTxpowerLowThreshAlarmOn: To detect whether ONU ANI TX power belows low threshold or not.
				1344: gponOnuAniTxpowerLowThreshAlarmOff:
				1345: gponOnuAniTxpowerHighThreshAlarmOn: To detect whether ONU ANI TX power exceeds high threshold or not.
				1346: gponOnuAniTxpowerHighThreshAlarmOff:"
			::= { sleAlarmSeverityControl 6 }

		
--   1.3.6.1.4.1.6296.101.4.2.2.7
-- 1.3.6.1.4.1.6296.101.4.2.2.7
		-- 1.3.6.1.4.1.6296.101.4.2.2.7
		sleAlarmSeverityControlValue OBJECT-TYPE
			SYNTAX INTEGER
				{
				critical(1),
				major(2),
				minor(3),
				warning(4),
				intermediate(5)
				}
			MAX-ACCESS read-write
			STATUS current
			DESCRIPTION
				" The severity of alarm. "
			::= { sleAlarmSeverityControl 7 }

		
--   1.3.6.1.4.1.6296.101.4.2.3
-- 1.3.6.1.4.1.6296.101.4.2.3
		-- 1.3.6.1.4.1.6296.101.4.2.3
		sleAlarmSeverityNotification OBJECT IDENTIFIER ::= { sleAlarmSeverity 3 }

		
--   1.3.6.1.4.1.6296.101.4.2.3.1
-- 1.3.6.1.4.1.6296.101.4.2.3.1
		-- 1.3.6.1.4.1.6296.101.4.2.3.1
		sleAlarmSeveriityCreated NOTIFICATION-TYPE
			OBJECTS { sleAlarmSeverityValue, sleAlarmSeverityControlRequest, sleAlarmSeverityControlTimeStamp, sleAlarmSeverityControlReqResult }
			STATUS current
			DESCRIPTION 
				"Description."
			::= { sleAlarmSeverityNotification 1 }

		
--   1.3.6.1.4.1.6296.101.4.2.3.2
-- 1.3.6.1.4.1.6296.101.4.2.3.2
		-- 1.3.6.1.4.1.6296.101.4.2.3.2
		sleAlarmSeveriityDestroyed NOTIFICATION-TYPE
			OBJECTS { sleAlarmSeverityControlRequest, sleAlarmSeverityControlTimeStamp, sleAlarmSeverityControlReqResult, sleAlarmSeverityValue }
			STATUS current
			DESCRIPTION 
				"Description."
			::= { sleAlarmSeverityNotification 2 }

		
--   1.3.6.1.4.1.6296.101.4.2.3.3
-- 1.3.6.1.4.1.6296.101.4.2.3.3
		-- 1.3.6.1.4.1.6296.101.4.2.3.3
		sleAlarmSeverityChanged NOTIFICATION-TYPE
			OBJECTS { sleAlarmSeverityValue, sleAlarmSeverityControlRequest, sleAlarmSeverityControlTimeStamp, sleAlarmSeverityControlReqResult }
			STATUS current
			DESCRIPTION 
				"Description."
			::= { sleAlarmSeverityNotification 3 }

		
--   1.3.6.1.4.1.6296.101.4.3
-- 1.3.6.1.4.1.6296.101.4.3
		-- 1.3.6.1.4.1.6296.101.4.3
		sleAlarmReport OBJECT IDENTIFIER ::= { sleFaultMgmt 3 }

		
--   1.3.6.1.4.1.6296.101.4.3.1
-- 1.3.6.1.4.1.6296.101.4.3.1
		-- 1.3.6.1.4.1.6296.101.4.3.1
		sleAlarmReportTable OBJECT-TYPE
			SYNTAX SEQUENCE OF SleAlarmReportEntry
			MAX-ACCESS not-accessible
			STATUS current
			DESCRIPTION
				" The alarm list table is used to store all reported alarms. "
			::= { sleAlarmReport 1 }

		
--   1.3.6.1.4.1.6296.101.4.3.1.1
-- 1.3.6.1.4.1.6296.101.4.3.1.1
		-- 1.3.6.1.4.1.6296.101.4.3.1.1
		sleAlarmReportEntry OBJECT-TYPE
			SYNTAX SleAlarmReportEntry
			MAX-ACCESS not-accessible
			STATUS current
			DESCRIPTION
				" Entry of the alarm lis table. "
			INDEX { sleAlarmSpecificCode, sleAlarmReportingSourceType, sleAlarmReportingSource }
			::= { sleAlarmReportTable 1 }

		
		SleAlarmReportEntry ::=
			SEQUENCE { 
				sleAlarmSpecificCode
					SpecificNum,
				sleAlarmReportingSourceType
					INTEGER,
				sleAlarmReportingSource
					OCTET STRING,
				sleAlarmSpecificSeverity
					INTEGER,
				sleAlarmSpecificProblem
					Unsigned32,
				sleAlarmSpecificProblemText
					OCTET STRING,
				sleAlarmTimeAndDate
					Integer32,
				sleAlarmSpecificSeqNum
					Counter32,
				sleAlarmReportPairType
					INTEGER
			 }

--    1.3.6.1.4.1.6296.101.4.3.1.1.1
-- 1.3.6.1.4.1.6296.101.4.3.1.1.1
-- 1.3.6.1.4.1.6296.101.4.3.1.1.1
		-- 1.3.6.1.4.1.6296.101.4.3.1.1.1
		sleAlarmSpecificCode OBJECT-TYPE
			SYNTAX SpecificNum
			MAX-ACCESS read-only
			STATUS current
			DESCRIPTION
				" The OID of alarm. 
				The following alarms is devided by the specific character, ===============.
				The division basis is that alarms is bounded or released.
				
				001: portDown: To detect whether physical or logical interface's link status is up or down.
				002: portUp: 
				===============
				003: portRemoved: To detect whether physical interface is installed or not.
				004: portInstalled: 
				===============
				005: powerFail: To detect whether power module's operation status is good or not.
						(Without doubt, more than 1 power module should be equipped.)
				006: powerOK: 
				===============
				007: powerRemoved: To detect whether power module is installed or not, through the PLD access.
						   (Without doubt, more than 1 power module should be equipped.)
				008: powerInstalled: 
				===============
				009: fanFail: To detect whether FAN module's operation status is good or not.
				010: fanOK: 
				===============
				011: fanRemoved: To detect whether FAN module is installed or not, through the PLD access.
				012: fanInstalled: 
				===============
				013: moduleRemoved: To detect whether physical interface module is installed or not, through the S/W I2C
				014: moduleInstalled: 
				===============
				015: systemRestart: Network system is restarted by operator. This is not H/W start but S/W start.
				===============
				016: systemStart: Network system is restarted by operator or system status. This is not S/W start but H/W start.
						  (This alarm isn’t used current)
				===============
				017: broadcastOver: To detect the receipt of broadcast packet.
				 			    (This alarm isn’t used current)
				018: broadcastUnder: 
				===============
				019: cpuOverLoad: To detect whether the configured CPU load threshold is less than current CPU load usage or not.
				020: cpuUnderLoad: 
				===============
				021: memoryOverUsed: To detect whether the configured memory threshold is less than current memory usage or not.
				022: memoryUnderUsed: 
				===============
				023: portOverThreshold: To detect whether the configured physical or logical interface threshold is 
							less than delta value of current interface's InOctects or not.
				024: portUnderThreshold: 
				===============
				025: temperatureHigh: To detect whether the configured system's temperature threshold is 
						      less than current temperature or not.
				026: temperatureLow: 
				===============
				027: mfgdBlocked: To detect whether the specific MAC by MAC flood guard is blocked or not.
				028: mfgdReleased: 
				===============
				029: ipConflict: To detect whether the same IP address on different network node is configured or not.
				030: ipUnconflict: 
				===============
				031: dhcpLeaseShortage: To detect whether IP address that can be assigned to subscriber by DHCP server is 
							sufficient or not.
				032: dhcpLeaseSufficient: 
				===============
				033: dhcpOccuredIllegalEntry: To detect whether a subsceiber is using a static IP address or not.
				034: dhcpRemovedIllegalEntry: 
				===============
				035: rmonAlarmRising: To detect whether rising threshold of a specific MO in RMON alarm sampling is 
						      less than current calculated value by alarm sample type or not. But alarm generation 
						      would be issued by means of event type in RMON event.
				036: rmonAlarmNoRising: 
				===============
				037: rmonAlarmFalling: To detect whether falling threshold of a specific MO in RMON alarm sampling is 
						       less than current calculated value by alarm sample type or not. 
						       But alarm generation would be issued by means of event type in RMON event.
				038: rmonAlarmNoFalling: 
				===============
				039: bpduGuardDisabled: To detect whether edge ports is guarded about superior BPDU or not. 
							In case of insertion edge node with 0 or lower priority than priority of current root bridge node, 
							it will be disarrangement during a short time because of recognition a new inserted node 
							as root bridge. 
							So these edge ports is guarded, and then edge ports is blocked about all superior BPDU. 
							So STP reconfiguration doesn't use this edge ports.
				===============
				040: rootGuardDisabled: To detect whether edge ports is guarded about superior BPDU or not. 
							In case of insertion edge node with 0 or lower priority than priority of current root bridge node, 
							it will be disarrangement during a short time because of recognition a new inserted node 
							as root bridge. 
							So, Root guard prevents a new inserted node from being root bridge as well as 
							receiving a superior BPDU from root bridge. 
							but this node participates in STP topology reconfiguration. 
							If root bridge does not send a superior BPDU, then this node acts usually though STP state change.
				===============
				041: portSecurity: To detect whether interface is configured for security or not. 
						   This can be used to prevent MAC from flooding as well as spoofing. 
						   That is, As a result, this will obstruct an attack as like DoS attack.
				===============
				042: userLogin: 
				043: userLogout: 
				===============
				051: igmpGroupJoined: To detect whether a subscriber is joined a multicast group or not.
				052: igmpGroupLeaved: 
				===============
				053: dhcpIpaddressBound: To detect wether a dynamic IP address is assigned to a subscriber or not.
				054: dhcpIpaddressFree: 
				===============
				055: doorOpened: To detect whether outer door is opeded or not, as external alarm.
				056: doorClosed: 
				===============
				057: powerModeChangedPowerToBattery: To detect whether a system is using AC power or battery. 
								     A system is using AC power usually. 
								     If there is any power problems as like a power failure, 
								     a system is using battery instead of AC power. 
				058: powerModeChangedBatteryToPower: 
				===============
				059: batterylowcapacity: To detect whether current battery capacity is less 
							 capacity threshold according to battery usage or not. 
							 The capacity of AC power is 16 voltage and battery is 20. 
							 Capacity threshold is configured by H/W specification.
							 So operator can't change it.
				060: batterynormalcapacity: 
				===============
				061: batteryhighTemperature: To detect whether current temperature of battery is greater than temperature threshold or not. 
				062: batterynormalTemperature: 
				===============
				063: authenticationFail: To detect whether the connected user is authentic or non-authentic.
				064: authenticationNofail: 
				===============
				065: psuAcHighTemperature: To detect whether current temperature of Power Supply Unit is 
							   greater than temperature threshold or not. 
				066: psuAcNormalTemperature: 
				===============
				067: batteryRemoved: To detect whether battery is equipped at network system or not. 
						     Battery is used as redundancy power service. So operator can decide the installation of battery.
				068: batteryEquipped: 
				===============
				069: batteryLowVoltage: To detect whether battery voltage is less than 12.5 volt or not. 
							12.5 volt value is configured by H/W specification. So operator can't change it.
				070: batteryNormalVoltage: 
				===============
				071: adminAccessLogin: To detect whether a operator connects at this network system or not.
				072: adminAccessLogout: 
				===============
				073: cfgdBlocked: To detect whether it is blocked flood to CPU or not.
				074: cfgdReleased: 
				===============
				075: sfgdBlocked: To detect whether it is blocked flood to system or not.
				076: sfgdReleased: 
				===============
				077: swWatchdogAbnormalState: To detect whether a specific process acts normally or not.
				078: swWatchdogNormalState: 
				===============
				079: swWatchdogDetectError: To detect whether a specific process is detected a error related to itself or cleared.
				080: swWatchdogClearError: 
				===============
				081: ppsControlBlocked: To detect whether it is blocked by pps-control or not.
				082: ppsControlReleased: 
				===============
				083: gotDMITempHighOverAlarm: To detect whether internal temperature exceeds high alarm level or not.
				084: gotDMITempHighFallAlarm: 
				===============
				085: gotDMITempLowOverAlarm: To detect whether internal temperature is below low alarm level or not.
				086: gotDMITempLowFallAlarm: 
				===============
				087: gotDMITempHighOverWarning: To detect whether internal temperature exceeds high warning level or not.
				088: gotDMITempHighFallWarning: 
				===============
				089: gotDMITempLowOverWarning: To detect whether internal temperature is below low warning level or not.
				090: gotDMITempLowFallWarning: 
				===============
				091: gotDMIVolHighOverAlarm: To detect whether internal supply voltage exceeds high alarm level or not.
				092: gotDMIVolHighFallAlarm: 
				===============
				093: gotDMIVolLowOverAlarm: To detect whether internal supply voltage is below low alarm level or not.
				094: gotDMIVolLowFallAlarm: 
				===============
				095: gotDMIVolHighOverWarning: To detect whether internal supply voltage exceeds high warning level or not.
				096: gotDMIVolHighFallWarning: 
				===============
				097: gotDMIVolLowOverWarning: To detect whether internal supply voltage is below low warning level or not.
				098: gotDMIVolLowFallWarning: 
				===============
				099: gotDMITxBiasHighOverAlarm: To detect whether TX Bias current exceeds high alarm level or not.
				100: gotDMITxBiasHighFallAlarm: 
				===============
				101: gotDMITxBiasLowOverAlarm: To detect whether TX Bias current is below low alarm level or not.
				102: gotDMITxBiasLowFallAlarm: 
				===============
				103: gotDMITxBiasHighOverWarning: To detect whether TX Bias current exceeds high warning level or not.
				104: gotDMITxBiasHighFallWarning: 
				===============
				105: gotDMITxBiasLowOverWarning: To detect whether TX Bias current is below low warning level or not.
				106: gotDMITxBiasLowFallWarning: 
				===============
				107: gotDMITxPowerHighOverAlarm: To detect whether TX output power exceeds high alarm level or not.
				108: gotDMITxPowerHighFallAlarm: 
				===============
				109: gotDMITxPowerLowOverAlarm: To detect whether TX output power is below low alarm level or not.
				110: gotDMITxPowerLowFallAlarm: 
				===============
				111: gotDMITxPowerHighOverWarning: To detect whether TX output power exceeds high warning level or not.
				112: gotDMITxPowerHighFallWarning: 
				===============
				113: gotDMITxPowerLowOverWarning: To detect whether TX output power is below low warning level or not.
				114: gotDMITxPowerLowFallWarning: 
				===============
				115: gotDMIRxPowerHighOverAlarm: To detect whether RX output power exceeds high alarm level or not.
				116: gotDMIRxPowerHighFallAlarm: 
				===============
				117: gotDMIRxPowerLowOverAlarm: To detect whether RX output power is below low alarm level or not.
				118: gotDMIRxPowerLowFallAlarm: 
				===============
				119: gotDMIRxPowerHighOverWarning: To detect whether RX output power exceeds high warning level or not.
				120: gotDMIRxPowerHighFallWarning: 
				===============
				121: gotDMIRxPowerLowOverWarning: To detect whether RX output power is below low warning level or not.
				122: gotDMIRxPowerLowFallWarning: 
				===============
				123: nosRemoteUpgradeRequest: 
				124: nosRemoteUpgradeSuccess: 
				125: nosRemoteUpgradeFailAbort: 
				126: nosRemoteUpgradeFailHeaderError: 
				127: nosRemoteUpgradeFailDownloadError: 
				128: nosRemoteUpgradeFailFlashError: 
				129: nosRemoteUpgradeStart: 
				===============
				130: systemDyingGasp:
				===============
				133: cliHistory: To detect whether CLI history is detected or not.
				134: cliHistoryNo:
				===============
				135: ntpConnectionFail: To detect whether NTP connection is failed or not.
				136: ntpConnectionFailNo:
				===============
				137: nmsConnectionTypeChanged:  To detect whether NMS connection type is changed.
				===============
				159: clockModuleRemoved:  To detect whether clock module is removed or installed.
				160: clockModuleInstalled:
				161: clockModuleInitFail:  To detect whether clock module initiolization is failed or not.
				162: clockModuleInitOk:
				===============
				163: cliHistoryLog: To detect whether CLI history log is over or not.
				164: cliHistoryLogNo:
				===============
				165: slotActionEvent: To detect whether slot action is changed.
				166: slotStateChange: To detect whether slot state is changed.
				===============
				167: interfaceAdminDown: To detect whether physical or logical interface's admin link status is up or down.
				168: interfaceAdminUp:
				===============
				169: slotPowerMonAbnormal: To detect whether slot power monitor abnormal or normal is detected.
				170: slotPowerMonNormal:
				===============
				171: slotErrorLEDChanged: To detect whether error LED is changed.
				===============
				185: cpuPpsOverThreshold: To detect whether PPS is over threshold or not.
				186: cpuPpsUnderThreshold:
				===============
				199: slotHealthStatusTimeout: To detect whether slot health status is time out or not.
				200: slotHealthStatusTimeoutCleared:
				===============
				201: advaTemperature: To detect whether current chassis temperature is less than chassis temperature threshold or not.
				202: advaTemperatureNo: 
				===============
				203: advaPSUFailure: To detect whether ADVA system's power supply unit has a failure or not.
				204: advaPSUFailureNo: 
				===============
				205: advaFanFailure: To detect whether ADVA system's FAN has a failure or not.
				206: advaFanFailureNo: 
				===============
				207: advaInterfaceReceiveFailure: To detect whether ADVA system's receipt has a failure or not.
				208: advaInterfaceReceiveFailureNo:  
				===============
				209: advaInterfaceOpticalThreshold: To detect whether Adva system's optical receive power level is 
								    less than optical threshold or not.
				210: advaInterfaceOpticalThresholdNo: 
				===============
				211: advaInterfaceTransmitFault: To detect whether ADVA system's transmission has a failure or not.
				212: advaInterfaceTransmitFaultNo: 
				===============
				213: dvaInterfaceMisconfiguration: To detect whether ADVA system's interface is configured rightly or not.
				214: advaInterfaceMisconfigurationNo: 
				===============
				215: advaInterfaceSFPMismatch: To detect whether ADVA system's SFP interface is mismatched or not.
				216: advaInterfaceSFPMismatchNo: 
				===============
				217: advaVoltageLow: To detect whether ADVA system's current voltage is less than voltage threshold or not.
				218: advaVoltageLowNo: 
				===============
				219: advaVoltageHigh: To detect whether ADVA system's current voltage is greater than voltage threshold or not.
				220: advaVoltageHighNo: 
				===============
				301: erpDomainLotp: To detect whether LOTP(Loss of Test Packet) exists a domain of ERP or not. 
						    The Loss of Test Packet defect is defined when a node does not receive 
						    any test packet at any of its ports for a period of 3 times.
				302: erpDomainLotpNo: 
				===============
				303: erpDomainULotp: To detect whether undirectional LOTP(Loss of Test Packet) exists a domain of ERP or not. 
						     The Loss of Test Packet defect is defined when a RM node of one domain does not 
						     receive any test packet at one port for a period of 3 times.
				304: erpDomainULotpNo: 
				===============
				305: erpDomainMultipleRM: To detect whether Multiple RM node is supported or not. 
							  The defect is raised when a RM node receives its own test packets 
							  with an Ack destination address field with a non-zero value.
				306: erpDomainMultipleRMNo: 
				===============
				307: erpDomainRMNodeReacheablity: To detect whether RM reachability is raised or not. 
								  The detection of multiple failures indicates that the ring is segmented and 
							          that the RM Node is unreacheable. 
								  This is only possible at normal ring nodes isolated from the RM node.
				308: erpDomainRMNodeReacheablityNo: 
				===============
				391: startupConfigLoadEnded: To detect whether startup configuration load is ended.
				===============
				401: eponOnuDeregister: To detect whether ONU is registered into OLT or not. 
							That is, ONU that its operation is service on should be sent registration information to OLT. 
				402: eponOnuRegister: 
				===============
				403: eponOnuRegistrationError: To detect whether ONU is failed registeration process into OLT.
				404: eponOnuNoRegistrationError: 
				===============
				405: eponBadEncryptionKey: To detect wwhether the encryption key is valid or not.
							   A message between ONU and OLT is encrypted using random encryption key. 
							   There is that the encryption key is invalid as transmission failure from time to time.
				406: eponNoBadEncryptionKey: 
				===============
				407: eponLlidMistmatch: To detect whether Llid of message between ONU and OLT is valid or not. 
							On registering, ONU informs unique ID to OLT.
							And then, all communication between ONU and OLT must use the unique ID. 
							The unique ID is called Llid.
				408: eponNoLlidMismatch: 
				===============
				409: eponTooManyRegister: To detect whether the registered ONU per 1 OLT is greater than 32 or not. 
							  That is, ONU can be registered from 1 to the maximum 32 at 1 OLT.
				410: eponNoTooManyRegister: 
				===============
				411: eponDyingGASP: To detect whether a ONU is down from dying gasp or not. 
						    A ONU could be changed to down state as a number of reasons.
						    By the way, ONU that is changed to down as dying gasp would be sent dying gasp signal to OLT and 
						    then ONU's link would be changed to down.
				412: eponNoDyingGASP: 
				===============
				413: eponOnuErrFramePeriod: 
				414: eponOnuNoErrFramePeriod: 
				===============
				415: eponOnuErrFrame: 
				416: eponOnuNoErrFrame: 
				===============
				417: eponOnuErrFrameSecondSummary: 
				418: eponOnuNoErrFrameSecondSummary: 
				===============
				419: eponOnuLastOnuDeregister: To detect whether a deregistered ONU is last ONU or not. 
							       If a deregistered ONU is last ONU, the OLT would be changed to serviceable status. 
				420: eponOnuNoLastOnuDeregister: 
				===============
				421: eponOltCableDown: 
				422: eponOltRecoverCableDown: 
				===============
				501: autoCLIStart: To detect whether the scheduled auto CLI is started or not.
				502: autoCLINoStart: 
				===============
				503: autoCLIComplete: To detect whether the scheduled auto CLI is completed or not. 
				504: autoCLINoComplete: 
				===============
				505: autoCLIRemoveOutputFile: To detect whether the result file of the scheduled auto CLI is removed or not.
							      The reason that the result file is removed is that the configured file size for the result  is
							      less than the stored result file size. 
							      If so, the oldest file would be removed before everything.
				506: autoCLINoRemoveOutputFile: 
				===============
				507: autoResetSystem: To detect whether the system is restarted or not. 
						      The conditions that system is restarted is that ping loss threshold is 
						      less than current ping loss count during the configured interval and 
						      that current free memory size is less than configured free memory size.
				508: autoResetNoSystem: 
				===============
				509: autoResetPingReplyLoss: To detect whether ping reply from the designated network node is received or not.
							     Operator designates any gateway system that can communicate to detect 
							     current network environment. 
							     System sends ICMP packet to the designated gateway system periodically. 
							     If  the system doesn't receive ping reply packet within any interval, 
							     operator recognizes that the system can't communicate any more 
							     because of some problems of the system. 
				510: autoResetNoPingReplyLoss: 
				===============
				511: autoResetMemoryLeakDetect: To detect whether current free memory size is 
								less than the configured free memory size or not. 
								Periodically, free memory size is checked to confirm system availability.
				512: autoResetNoMemoryLeakDetect: 
				===============
				601: arulePacketDropDetect: To detect whether it is dropped some packet by arule or not.
				602: arulePacketDropRelease: 
				===============
				620: bME1CardNoDetect: 
				621: clearBME1CardNoDetect: 
				===============
				622: bME1CardAFEerror: 
				623: clearBME1CardAFEerror: 
				===============
				624: bME1CardIFEerror: 
				625: clearBME1CardIFEerror: 
				===============
				626: bME1CardFWerror: 
				627: clearBME1CardFWerror: 
				===============
				628: bME1CardPROVerror: 
				629: clearBME1CardPROVerror: 
				===============
				630: bME1CrashDetect: 
				631: clearBME1CrashDetect: 
				===============
				632: bME2CardNoDetect: 
				633: clearBME2CardNoDetect: 
				===============
				634: bME2CardAFEerror: 
				635: clearBME2CardAFEerror: 
				===============
				636: bME2CardIFEerror: 
				637: clearBME2CardIFEerror: 
				===============
				638: bME2CardFWerror: 
				639: clearBME2CardFWerror: 
				===============
				640: bME2CardPROVerror: 
				641: clearBME2CardPROVerror: 
				===============
				642: bME2CrashDetect: 
				643: clearBME2CrashDetect: 
				===============
				644: bME3CardNoDetect: 
				645: clearBME3CardNoDetect: 
				===============
				646: bME3CardAFEerror: 
				647: clearBME3CardAFEerror: 
				===============
				648: bME3CardIFEerror: 
				649: clearBME3CardIFEerror: 
				===============
				650: bME3CardFWerror: 
				651: clearBME3CardFWerror: 
				===============
				652: bME3CardPROVerror: 
				653: clearBME3CardPROVerror: 
				===============
				654: bME3CrashDetect: 
				655: clearBME3CrashDetect: 
				===============
				656: powerFromBattery: 
				657: clearPowerFromBattery: 
				===============
				658: invalidBatteryStatus: 
				659: clearInvalidBatteryStatus: 
				===============
				660: batteryChargeLow: 
				661: clearBatteryChargeLow: 
				===============
				662: batteryNotPresent: 
				663: clearBatteryNotPresent: 
				===============
				664: voltageLow: 
				665: clearVoltageLow: 
				===============
				666: tempOverThreshold: 
				667: clearTempOverThreshold: 
				===============
				668: tempUnderThreshold: 
				669: clearTempUnderThreshold: 
				===============
				670: cpuOverThreshold: 
				671: clearCpuOverThreshold: 
				===============
				672: trafficOverload: 
				673: clearTrafficOverload: 
				===============
				674: gEPONModuleNotDetect: 
				675: clearGEPONModuleNotDetect:
				===============
				676: gEPONPortOperationDown: 
				677: clearGEPONPortOperationDown: 
				===============
				678: gEPONNoIncomingTraffic: 
				679: clearGEPONNoIncomingTraffic: 
				===============
				680: processCrashDetect: 
				681: clearProcessCrashDetect: 
				===============
				682: memoryLeakDetect: 
				683: clearMemoryLeakDetect: 
				===============
				684: memoryCorrupDetect: 
				685: clearMemoryCorrupDetect: 
				===============
				686: memoryLowDetect: 
				687: clearMemoryLowDetect: 
				===============
				688: dataLineerror: 
				689: clearDataLineerror: 
				===============
				690: addressLineerror: 
				691: clearAddressLineerror: 
				===============
				692: chipsetNotDetcet: 
				693: clearChipsetNotDetcet: 
				===============
				694: pciBuserror: 
				695: clearPciBuserror: 
				===============
				696: securityAdminConnect: 
				697: clearSecurityAdminConnect: 
				===============
				698: oNUPowerDown: 
				699: clearONUPowerDown: 
				===============
				700: oNUNotRegister: 
				701: clearONUNotRegister: 
				===============
				702: oNTOpticPre: 
				703: clearONTOpticPre: 
				===============
				800: switchoverInitiated: 
				===============
				801: switchoverDone: 
				===============
				803: redConfigurationMisMatch: To detect whether redundancy configuration is mismatched.
				===============
				901: gponNoAuthCBU: To detect no auth CBU is detected.
				902: gponDuplicateONU: To detect ONU is duplicated.
				903: gponDyingGasp: To detect dying GASP is detected.
				904: gponUpgradeComplete: To detect upgrade complete is detected.
				905: gponDeregistered: To detect whether deregistered is detected or not.
				906: gponRegistered: 
				907: gponRogueOnu: To detect rogue ONU is detected
				908: gponOnuBatteryEvent: To detect whether ONU battery event is detected or not.
				909: clearGponOnuBetteryEvent:
				910: gponOnuPortOperStatus: To detectONU port operation statue is chagned.
				911: gponTransceiverChanged: To detect transceiver is changed.
				912: gponOltLosOn: To detect whether OLT LOS is on or off
				913: gponOltLosOff:
				914: gponOltLosiOn: To detect whether OLT LOSI is on or off
				915: gponOltLosiOff:
				916: gponDyingGaspOn: To detect whether dying GASP is on or off
				917: gponDyingGaspOff:
				918: gponOntOSUpgradeStatus: To detect ONT OS upgrade status is changed.
				919: gponOntBLUpgradeStatus: To detect BL upgrade status is changed.
				920: gponOltRxPowerLoss: To detect OLT RX power is loss.
				921: gponOltRxPowerDetected: To detect OLT RX power status is changed.
				922: gponOnuTemperatureHighOverThreshold: To detect whether ONU temperature exceeds high threshold or not.
				923: gponOnuTemperatureHighFallThreshold:
				924: gponOnuTemperatureLowOverThreshold: To detect whether ONU temperature belows low threshold or not.
				925: gponOnuTemperatureLowFallThreshold:
				926: gponOnuCpuOverThreshold: To detect whether ONU CPU exceeds threshold or not.
				927: gponOnuCpuFallThreshold: 
				928: gponOnuMemoryOverThreshold: To detect whether memory exceeds threshold or not.
				929: gponOnuMemoryFallThreshold: 
				930: gponOnuI2cFail: To detect ONU L2C fail is detected.
				931: gponOnuRxOpticLowThreshAlarmOn: To detect whether ONU RX optic belows low threshold or not.
				932: gponOnuRxOpticLowThreshAlarmOff: 
				933: gponOnuRxOpticHighThreshAlarmOn: To detect whether ONU RX optic exceeds high threshold or not.
				934: gponOnuRxOpticHighThreshAlarmOff:
				935: gponOltLOFIOn: To detect whether OLT LOFL is on or off
				936: gponOltLOFIOff:
				937: gponOltDOWOn: To detect whether OLT DOW is on or off
				938: gponOltDOWOff:
				939: gponOltSFOn: To detect whether OLT SF is on or off
				940: gponOltSFOff:
				941: gponOltSDOn: To detect whether OLT SD is on or off
				942: gponOltSDOff:
				943: gponOltLCDGIOn: To detect whether OLT LCDGL is on or off
				944: gponOltLCDGIOff:
				945: gponOltRDOn: To detect whether OLT RD is on or off
				946: gponOltRDOff:
				947: gponOltSUFOn: To detect whether OLT SUF is on or off
				948: gponOltSUFOff:
				949: gponOltLOAOn: To detect whether OLT LOA is on or off
				950: gponOltLOAOff:
				951: gponOltLOAMIOn: To detect whether OLT LOAML is on or off
				952: gponOltLOAMIOff:
				953: gponOltMEMOn: To detect whether OLT MEM is on or off
				954: gponOltMEMOff:
				955: gponOltPEEOn: To detect whether OLT PEE is on or off
				956: gponOltPEEOff:
				957: gponOltPSTOn: To detect whether OLT PST is on or off
				958: gponOltPSTOff:
				959: gponOltERROn: To detect whether OLT ERR is on or off
				960: gponOltERROff:
				961: gponOltREIOn: To detect whether OLT REI is on or off
				962: gponOltREIOff:
				963: gponAntiSpoofingDupPortOn: To detect whether anti spoofing port is duplicated or not.
				964: gponAntiSpoofingDupPortOff:
				965: gponRedundancySwitchOver: To detect redundancy switchover is changed.
				966: gponDuplicatedRangingResponse: To detect ranging response is changed.
				967: gponOnuPortOpticModuleRemove: To detect whether ONU port optic module is removed or installed.
				968: gponOnuPortOpticModuleInstall:
				969: gponOnuOMCCProblemDetected: To detect whether ONU OMCC problem is detected or not.
				970: gponOnuOMCCProblemCleared:
				971: gponOltFixedTcontAlarmOn: To detect whether OLT fixed Tcont alarm is on or off.
				972: gponOltFixedTcontAlarmOff:
				973: gponOltDynamicTcontAlarmOn: To detect whether OLT dynamic Tcont alarm is on or off.
				974: gponOltDynamicTcontAlarmOff:
				975: gponOltPortCountAlarmOn: To detect whether OLT port count alarm is on or off.
				976: gponOltPortCountAlarmOff:
				977: gponOltCableDownAlarmOn: To detect whether OLT cable down alarm is on or off.
				978: gponOltCableDownAlarmOff:
				979: gponOltDeactiveMonitorAlarmOn: To detect whether deactive monitor alarm is on or off.
				980: gponOltDeactiveMonitorAlarmOff:
				981: gponOltDfiOn: To detect whether OLT DFI is on or off.
				982: gponOltDfiOff:
				984: gponOltTransceiverPortChanged: To detect OLT transeiver port is changed.
				985: gponOnuPortOperStatusDown: To detect whether ONU port operation status is down or up.
				986: gponOnuPortOperStatusUp::
				===============
				1101: emLogDefectCPUHighOver: To detect whether EM log detect CPU exceeds threshold or not.
				1102: emLogDefectCPUHighUnder:
				1103: emLogTemperHighOver: To detect whether EM log temperature exceeds high threshold or not.
				1104: emLogTemperHighUnder:
				1105: emLogTemperLowUnder: To detect whether EM log CPU belows low threshold or not.
				1106: emLogTemperLowOver:
				1107: emLogMemLowUnder:  To detect whether EM log memory belows low threshold or not.
				1108: emLogMemLowOver:
				1109: emLogFanFail:  To detect whether EM log fan status is failed or not.
				1110: emLogFanFailCleared:
				1111: emLogPhyCRCFail: To detect whether EM log physical CRC is failed or not.
				1112: emLogPhyCRCFailCleared:
				1113: emLogPhyDetectFail: To detect whether EM log physical status is failed or not.
				1114: emLogPhyDetectFailCleared:
				1115: emLogSFUMateInitFail: To detect whether EM log SFU mate initialization is failed or not.
				1116: emLogSFUMateInitFailCleared:
				1117: emLogDaemonHealthBad: To detect whether EM log daemon health is bad or not.
				1118: emLogDaemonHealthBadCleared:
				1119: emLogGPIURavenLinkDown: To detect whether EM log GPIU RAVEN link is down or not.
				1120: emLogGPIURavenLinkDownCleared:
				===============
				1151: slotNosUpgradeStart: To detect whether slot NOS upgrade is started or ended.
				1152: slotNosUpgradeEnd:
				===============
				1331: gponOnuAniVoltageLowThreshAlarmOn: To detect whether ONU ANI voltage belows low threshold or not.
				1332: gponOnuAniVoltageLowThreshAlarmOff:
				1333: gponOnuAniVoltageHighThreshAlarmOn: To detect whether ONU ANI voltage exceeds high threshold or not.
				1334: gponOnuAniVoltageHighThreshAlarmOff:
				1335: gponOnuAniTemperatureLowThreshAlarmOn: To detect whether ONU ANI temperature belows low threshold or not.
				1336: gponOnuAniTemperatureLowThreshAlarmOff:
				1337: gponOnuAniTemperatureHighThreshAlarmOn: To detect whether ONU ANI temperature exceeds high threshold or not.
				1338: gponOnuAniTemperatureHighThreshAlarmOff:
				1339: gponOnuAniTxBiasLowThreshAlarmOn: To detect whether ONU ANI TX bias belows low threshold or not.
				1340: gponOnuAniTxBiasLowThreshAlarmOff:
				1341: gponOnuAniTxBiasHighThreshAlarmOn: To detect whether ONU ANI TX bias exceeds high threshold or not. 
				1342: gponOnuAniTxBiasHighThreshAlarmOff:
				1343: gponOnuAniTxpowerLowThreshAlarmOn: To detect whether ONU ANI TX power belows low threshold or not.
				1344: gponOnuAniTxpowerLowThreshAlarmOff:
				1345: gponOnuAniTxpowerHighThreshAlarmOn: To detect whether ONU ANI TX power exceeds high threshold or not.
				1346: gponOnuAniTxpowerHighThreshAlarmOff:"
			::= { sleAlarmReportEntry 1 }

		
--   1.3.6.1.4.1.6296.101.4.3.1.1.2
-- 1.3.6.1.4.1.6296.101.4.3.1.1.2
		-- 1.3.6.1.4.1.6296.101.4.3.1.1.2
		sleAlarmReportingSourceType OBJECT-TYPE
			SYNTAX INTEGER
				{
				entPhysicalEntity(1),
				ifIndex(2),
				vccTp(3),
				macAddress(4),
				ipv4(5),
				ipv6(6),
				threshold(7),
				advaSource(8),
				number(9),
				general(10),
				eponSource(11),
				gponSource(12)
				}
			MAX-ACCESS read-only
			STATUS current
			DESCRIPTION
				"The type of Reporting source"
			::= { sleAlarmReportEntry 2 }

		
--   1.3.6.1.4.1.6296.101.4.3.1.1.3
-- 1.3.6.1.4.1.6296.101.4.3.1.1.3
		-- 1.3.6.1.4.1.6296.101.4.3.1.1.3
		sleAlarmReportingSource OBJECT-TYPE
			SYNTAX OCTET STRING (SIZE (0..64))
			MAX-ACCESS read-only
			STATUS current
			DESCRIPTION
				" The alarm severity of alarm. "
			::= { sleAlarmReportEntry 3 }

		
--   1.3.6.1.4.1.6296.101.4.3.1.1.4
-- 1.3.6.1.4.1.6296.101.4.3.1.1.4
		-- 1.3.6.1.4.1.6296.101.4.3.1.1.4
		sleAlarmSpecificSeverity OBJECT-TYPE
			SYNTAX INTEGER
				{
				critical(1),
				major(2),
				minor(3),
				warning(4),
				intermediate(5),
				cleared(6)
				}
			MAX-ACCESS read-only
			STATUS current
			DESCRIPTION
				"The alarm severity. The value cleared indicates the clearing of alarm."
			::= { sleAlarmReportEntry 4 }

		
--   1.3.6.1.4.1.6296.101.4.3.1.1.5
-- 1.3.6.1.4.1.6296.101.4.3.1.1.5
		-- 1.3.6.1.4.1.6296.101.4.3.1.1.5
		sleAlarmSpecificProblem OBJECT-TYPE
			SYNTAX Unsigned32
			MAX-ACCESS read-only
			STATUS current
			DESCRIPTION
				"Describes the spefic problems e.g. when a shePhysCardFailure is sent here the  termperature alarm is specified"
			::= { sleAlarmReportEntry 5 }

		
--   1.3.6.1.4.1.6296.101.4.3.1.1.6
-- 1.3.6.1.4.1.6296.101.4.3.1.1.6
		-- 1.3.6.1.4.1.6296.101.4.3.1.1.6
		sleAlarmSpecificProblemText OBJECT-TYPE
			SYNTAX OCTET STRING (SIZE (0..255))
			MAX-ACCESS read-only
			STATUS current
			DESCRIPTION
				"Textual description of specific problem reported by alarming.
				To be discussed: Option is to define an alarm for every problem
				"
			::= { sleAlarmReportEntry 6 }

		
--   1.3.6.1.4.1.6296.101.4.3.1.1.7
-- 1.3.6.1.4.1.6296.101.4.3.1.1.7
		-- 1.3.6.1.4.1.6296.101.4.3.1.1.7
		sleAlarmTimeAndDate OBJECT-TYPE
			SYNTAX Integer32
			MAX-ACCESS read-only
			STATUS current
			DESCRIPTION
				"The date and time when the alarm appeared or cleared"
			::= { sleAlarmReportEntry 7 }

		
--   1.3.6.1.4.1.6296.101.4.3.1.1.8
-- 1.3.6.1.4.1.6296.101.4.3.1.1.8
		-- 1.3.6.1.4.1.6296.101.4.3.1.1.8
		sleAlarmSpecificSeqNum OBJECT-TYPE
			SYNTAX Counter32
			MAX-ACCESS read-only
			STATUS current
			DESCRIPTION
				"Sequence number for the alarm synchronization. 
				This value has a number to be used for the next alarm trap."
			::= { sleAlarmReportEntry 8 }

		
--  1.3.6.1.4.1.6296.101.4.3.1.1.9
		-- 1.3.6.1.4.1.6296.101.4.3.1.1.9
		sleAlarmReportPairType OBJECT-TYPE
			SYNTAX INTEGER
				{
				pair(0),
				mono(1)
				}
			MAX-ACCESS read-only
			STATUS current
			DESCRIPTION
				"The type is whether alarm trap is pair or mono."
			::= { sleAlarmReportEntry 9 }

		
--   1.3.6.1.4.1.6296.101.4.3.2
-- 1.3.6.1.4.1.6296.101.4.3.2
		-- 1.3.6.1.4.1.6296.101.4.3.2
		sleAlarmReportNotification OBJECT IDENTIFIER ::= { sleAlarmReport 2 }

		
--   1.3.6.1.4.1.6296.101.4.3.2.1
-- 1.3.6.1.4.1.6296.101.4.3.2.1
		-- 1.3.6.1.4.1.6296.101.4.3.2.1
		sleAlarmReportNotified NOTIFICATION-TYPE
			OBJECTS { sleAlarmSpecificCode, sleAlarmReportingSourceType, sleAlarmReportingSource, sleAlarmTimeAndDate, sleAlarmSpecificSeverity, 
				sleAlarmSpecificProblem, sleAlarmSpecificProblemText, sleAlarmSpecificSeqNum }
			STATUS current
			DESCRIPTION 
				"Description."
			::= { sleAlarmReportNotification 1 }

		
--   1.3.6.1.4.1.6296.101.4.3.3
-- 1.3.6.1.4.1.6296.101.4.3.3
		-- 1.3.6.1.4.1.6296.101.4.3.3
		sleAlarmReportControl OBJECT IDENTIFIER ::= { sleAlarmReport 3 }

		
--   1.3.6.1.4.1.6296.101.4.3.3.1
-- 1.3.6.1.4.1.6296.101.4.3.3.1
		-- 1.3.6.1.4.1.6296.101.4.3.3.1
		sleAlarmReportControlRequest OBJECT-TYPE
			SYNTAX INTEGER { clearAlarmReport(1) }
			MAX-ACCESS read-write
			STATUS current
			DESCRIPTION
				"Description."
			::= { sleAlarmReportControl 1 }

		
--   1.3.6.1.4.1.6296.101.4.3.3.2
-- 1.3.6.1.4.1.6296.101.4.3.3.2
		-- 1.3.6.1.4.1.6296.101.4.3.3.2
		sleAlarmReportControlStatus OBJECT-TYPE
			SYNTAX SleControlStatusType
			MAX-ACCESS read-only
			STATUS current
			DESCRIPTION
				"Description."
			::= { sleAlarmReportControl 2 }

		
--   1.3.6.1.4.1.6296.101.4.3.3.3
-- 1.3.6.1.4.1.6296.101.4.3.3.3
		-- 1.3.6.1.4.1.6296.101.4.3.3.3
		sleAlarmReportControlTimer OBJECT-TYPE
			SYNTAX Gauge32
			MAX-ACCESS read-write
			STATUS current
			DESCRIPTION
				"Description."
			::= { sleAlarmReportControl 3 }

		
--   1.3.6.1.4.1.6296.101.4.3.3.4
-- 1.3.6.1.4.1.6296.101.4.3.3.4
		-- 1.3.6.1.4.1.6296.101.4.3.3.4
		sleAlarmReportControlTimeStamp OBJECT-TYPE
			SYNTAX TimeTicks
			MAX-ACCESS read-only
			STATUS current
			DESCRIPTION
				"Description."
			::= { sleAlarmReportControl 4 }

		
--   1.3.6.1.4.1.6296.101.4.3.3.5
-- 1.3.6.1.4.1.6296.101.4.3.3.5
		-- 1.3.6.1.4.1.6296.101.4.3.3.5
		sleAlarmReportControlReqResult OBJECT-TYPE
			SYNTAX SleControlRequestResultType
			MAX-ACCESS read-only
			STATUS current
			DESCRIPTION
				"Description."
			::= { sleAlarmReportControl 5 }

		
--   1.3.6.1.4.1.6296.101.4.3.4
-- 1.3.6.1.4.1.6296.101.4.3.4
		-- 1.3.6.1.4.1.6296.101.4.3.4
		sleAlarmReportNotifications OBJECT IDENTIFIER ::= { sleAlarmReport 4 }

		
--   1.3.6.1.4.1.6296.101.4.3.4.1
-- 1.3.6.1.4.1.6296.101.4.3.4.1
		-- 1.3.6.1.4.1.6296.101.4.3.4.1
		sleAlarmReportCleared NOTIFICATION-TYPE
			OBJECTS { sleAlarmReportControlRequest, sleAlarmReportControlTimeStamp, sleAlarmReportControlReqResult }
			STATUS current
			DESCRIPTION 
				"Description."
			::= { sleAlarmReportNotifications 1 }

		
--   1.3.6.1.4.1.6296.101.4.4
-- 1.3.6.1.4.1.6296.101.4.4
		-- 1.3.6.1.4.1.6296.101.4.4
		sleAlarmHistory OBJECT IDENTIFIER ::= { sleFaultMgmt 4 }

		
--   1.3.6.1.4.1.6296.101.4.4.1
-- 1.3.6.1.4.1.6296.101.4.4.1
		-- 1.3.6.1.4.1.6296.101.4.4.1
		sleAlarmHistoryTable OBJECT-TYPE
			SYNTAX SEQUENCE OF SleAlarmHistoryEntry
			MAX-ACCESS not-accessible
			STATUS current
			DESCRIPTION
				" The alarm severity table.
				The alarm severity table associates
				profile index and AlarmID pairs with severities to be
				used for alarm traps.
				(Note that this table does not apply to cleared alarms). "
			::= { sleAlarmHistory 1 }

		
--   1.3.6.1.4.1.6296.101.4.4.1.1
-- 1.3.6.1.4.1.6296.101.4.4.1.1
		-- 1.3.6.1.4.1.6296.101.4.4.1.1
		sleAlarmHistoryEntry OBJECT-TYPE
			SYNTAX SleAlarmHistoryEntry
			MAX-ACCESS not-accessible
			STATUS current
			DESCRIPTION
				" Entry of the alarm severity table. "
			INDEX { sleAlarmHistoryIndex }
			::= { sleAlarmHistoryTable 1 }

		
		SleAlarmHistoryEntry ::=
			SEQUENCE { 
				sleAlarmHistoryIndex
					INTEGER,
				sleAlarmHistorySpecific
					SpecificNum,
				sleAlarmHistorySeverity
					INTEGER,
				sleAlarmHistoryText
					OCTET STRING,
				sleAlarmHistoryTime
					Integer32,
				sleAlarmHistorySeqNum
					Counter32,
				sleAlarmHistoryPairType
					INTEGER
			 }

--   1.3.6.1.4.1.6296.101.4.4.1.1.1
-- 1.3.6.1.4.1.6296.101.4.4.1.1.1
		-- 1.3.6.1.4.1.6296.101.4.4.1.1.1
		sleAlarmHistoryIndex OBJECT-TYPE
			SYNTAX INTEGER (1..65535)
			MAX-ACCESS read-only
			STATUS current
			DESCRIPTION
				" The OID of alarm. "
			::= { sleAlarmHistoryEntry 1 }

		
--    1.3.6.1.4.1.6296.101.4.4.1.1.2
-- 1.3.6.1.4.1.6296.101.4.4.1.1.2
-- 1.3.6.1.4.1.6296.101.4.4.1.1.2
		-- 1.3.6.1.4.1.6296.101.4.4.1.1.2
		sleAlarmHistorySpecific OBJECT-TYPE
			SYNTAX SpecificNum
			MAX-ACCESS read-only
			STATUS current
			DESCRIPTION
				" The OID of alarm. 
				The following alarms is devided by the specific character, ===============.
				The division basis is that alarms is bounded or released.
				
				001: portDown: To detect whether physical or logical interface's link status is up or down.
				002: portUp: 
				===============
				003: portRemoved: To detect whether physical interface is installed or not.
				004: portInstalled: 
				===============
				005: powerFail: To detect whether power module's operation status is good or not.
						(Without doubt, more than 1 power module should be equipped.)
				006: powerOK: 
				===============
				007: powerRemoved: To detect whether power module is installed or not, through the PLD access.
						   (Without doubt, more than 1 power module should be equipped.)
				008: powerInstalled: 
				===============
				009: fanFail: To detect whether FAN module's operation status is good or not.
				010: fanOK: 
				===============
				011: fanRemoved: To detect whether FAN module is installed or not, through the PLD access.
				012: fanInstalled: 
				===============
				013: moduleRemoved: To detect whether physical interface module is installed or not, through the S/W I2C
				014: moduleInstalled: 
				===============
				015: systemRestart: Network system is restarted by operator. This is not H/W start but S/W start.
				===============
				016: systemStart: Network system is restarted by operator or system status. This is not S/W start but H/W start.
						  (This alarm isn’t used current)
				===============
				017: broadcastOver: To detect the receipt of broadcast packet.
				 			    (This alarm isn’t used current)
				018: broadcastUnder: 
				===============
				019: cpuOverLoad: To detect whether the configured CPU load threshold is less than current CPU load usage or not.
				020: cpuUnderLoad: 
				===============
				021: memoryOverUsed: To detect whether the configured memory threshold is less than current memory usage or not.
				022: memoryUnderUsed: 
				===============
				023: portOverThreshold: To detect whether the configured physical or logical interface threshold is 
							less than delta value of current interface's InOctects or not.
				024: portUnderThreshold: 
				===============
				025: temperatureHigh: To detect whether the configured system's temperature threshold is 
						      less than current temperature or not.
				026: temperatureLow: 
				===============
				027: mfgdBlocked: To detect whether the specific MAC by MAC flood guard is blocked or not.
				028: mfgdReleased: 
				===============
				029: ipConflict: To detect whether the same IP address on different network node is configured or not.
				030: ipUnconflict: 
				===============
				031: dhcpLeaseShortage: To detect whether IP address that can be assigned to subscriber by DHCP server is 
							sufficient or not.
				032: dhcpLeaseSufficient: 
				===============
				033: dhcpOccuredIllegalEntry: To detect whether a subsceiber is using a static IP address or not.
				034: dhcpRemovedIllegalEntry: 
				===============
				035: rmonAlarmRising: To detect whether rising threshold of a specific MO in RMON alarm sampling is 
						      less than current calculated value by alarm sample type or not. But alarm generation 
						      would be issued by means of event type in RMON event.
				036: rmonAlarmNoRising: 
				===============
				037: rmonAlarmFalling: To detect whether falling threshold of a specific MO in RMON alarm sampling is 
						       less than current calculated value by alarm sample type or not. 
						       But alarm generation would be issued by means of event type in RMON event.
				038: rmonAlarmNoFalling: 
				===============
				039: bpduGuardDisabled: To detect whether edge ports is guarded about superior BPDU or not. 
							In case of insertion edge node with 0 or lower priority than priority of current root bridge node, 
							it will be disarrangement during a short time because of recognition a new inserted node 
							as root bridge. 
							So these edge ports is guarded, and then edge ports is blocked about all superior BPDU. 
							So STP reconfiguration doesn't use this edge ports.
				===============
				040: rootGuardDisabled: To detect whether edge ports is guarded about superior BPDU or not. 
							In case of insertion edge node with 0 or lower priority than priority of current root bridge node, 
							it will be disarrangement during a short time because of recognition a new inserted node 
							as root bridge. 
							So, Root guard prevents a new inserted node from being root bridge as well as 
							receiving a superior BPDU from root bridge. 
							but this node participates in STP topology reconfiguration. 
							If root bridge does not send a superior BPDU, then this node acts usually though STP state change.
				===============
				041: portSecurity: To detect whether interface is configured for security or not. 
						   This can be used to prevent MAC from flooding as well as spoofing. 
						   That is, As a result, this will obstruct an attack as like DoS attack.
				===============
				042: userLogin: 
				043: userLogout: 
				===============
				051: igmpGroupJoined: To detect whether a subscriber is joined a multicast group or not.
				052: igmpGroupLeaved: 
				===============
				053: dhcpIpaddressBound: To detect wether a dynamic IP address is assigned to a subscriber or not.
				054: dhcpIpaddressFree: 
				===============
				055: doorOpened: To detect whether outer door is opeded or not, as external alarm.
				056: doorClosed: 
				===============
				057: powerModeChangedPowerToBattery: To detect whether a system is using AC power or battery. 
								     A system is using AC power usually. 
								     If there is any power problems as like a power failure, 
								     a system is using battery instead of AC power. 
				058: powerModeChangedBatteryToPower: 
				===============
				059: batterylowcapacity: To detect whether current battery capacity is less 
							 capacity threshold according to battery usage or not. 
							 The capacity of AC power is 16 voltage and battery is 20. 
							 Capacity threshold is configured by H/W specification.
							 So operator can't change it.
				060: batterynormalcapacity: 
				===============
				061: batteryhighTemperature: To detect whether current temperature of battery is greater than temperature threshold or not. 
				062: batterynormalTemperature: 
				===============
				063: authenticationFail: To detect whether the connected user is authentic or non-authentic.
				064: authenticationNofail: 
				===============
				065: psuAcHighTemperature: To detect whether current temperature of Power Supply Unit is 
							   greater than temperature threshold or not. 
				066: psuAcNormalTemperature: 
				===============
				067: batteryRemoved: To detect whether battery is equipped at network system or not. 
						     Battery is used as redundancy power service. So operator can decide the installation of battery.
				068: batteryEquipped: 
				===============
				069: batteryLowVoltage: To detect whether battery voltage is less than 12.5 volt or not. 
							12.5 volt value is configured by H/W specification. So operator can't change it.
				070: batteryNormalVoltage: 
				===============
				071: adminAccessLogin: To detect whether a operator connects at this network system or not.
				072: adminAccessLogout: 
				===============
				073: cfgdBlocked: To detect whether it is blocked flood to CPU or not.
				074: cfgdReleased: 
				===============
				075: sfgdBlocked: To detect whether it is blocked flood to system or not.
				076: sfgdReleased: 
				===============
				077: swWatchdogAbnormalState: To detect whether a specific process acts normally or not.
				078: swWatchdogNormalState: 
				===============
				079: swWatchdogDetectError: To detect whether a specific process is detected a error related to itself or cleared.
				080: swWatchdogClearError: 
				===============
				081: ppsControlBlocked: To detect whether it is blocked by pps-control or not.
				082: ppsControlReleased: 
				===============
				083: gotDMITempHighOverAlarm: To detect whether internal temperature exceeds high alarm level or not.
				084: gotDMITempHighFallAlarm: 
				===============
				085: gotDMITempLowOverAlarm: To detect whether internal temperature is below low alarm level or not.
				086: gotDMITempLowFallAlarm: 
				===============
				087: gotDMITempHighOverWarning: To detect whether internal temperature exceeds high warning level or not.
				088: gotDMITempHighFallWarning: 
				===============
				089: gotDMITempLowOverWarning: To detect whether internal temperature is below low warning level or not.
				090: gotDMITempLowFallWarning: 
				===============
				091: gotDMIVolHighOverAlarm: To detect whether internal supply voltage exceeds high alarm level or not.
				092: gotDMIVolHighFallAlarm: 
				===============
				093: gotDMIVolLowOverAlarm: To detect whether internal supply voltage is below low alarm level or not.
				094: gotDMIVolLowFallAlarm: 
				===============
				095: gotDMIVolHighOverWarning: To detect whether internal supply voltage exceeds high warning level or not.
				096: gotDMIVolHighFallWarning: 
				===============
				097: gotDMIVolLowOverWarning: To detect whether internal supply voltage is below low warning level or not.
				098: gotDMIVolLowFallWarning: 
				===============
				099: gotDMITxBiasHighOverAlarm: To detect whether TX Bias current exceeds high alarm level or not.
				100: gotDMITxBiasHighFallAlarm: 
				===============
				101: gotDMITxBiasLowOverAlarm: To detect whether TX Bias current is below low alarm level or not.
				102: gotDMITxBiasLowFallAlarm: 
				===============
				103: gotDMITxBiasHighOverWarning: To detect whether TX Bias current exceeds high warning level or not.
				104: gotDMITxBiasHighFallWarning: 
				===============
				105: gotDMITxBiasLowOverWarning: To detect whether TX Bias current is below low warning level or not.
				106: gotDMITxBiasLowFallWarning: 
				===============
				107: gotDMITxPowerHighOverAlarm: To detect whether TX output power exceeds high alarm level or not.
				108: gotDMITxPowerHighFallAlarm: 
				===============
				109: gotDMITxPowerLowOverAlarm: To detect whether TX output power is below low alarm level or not.
				110: gotDMITxPowerLowFallAlarm: 
				===============
				111: gotDMITxPowerHighOverWarning: To detect whether TX output power exceeds high warning level or not.
				112: gotDMITxPowerHighFallWarning: 
				===============
				113: gotDMITxPowerLowOverWarning: To detect whether TX output power is below low warning level or not.
				114: gotDMITxPowerLowFallWarning: 
				===============
				115: gotDMIRxPowerHighOverAlarm: To detect whether RX output power exceeds high alarm level or not.
				116: gotDMIRxPowerHighFallAlarm: 
				===============
				117: gotDMIRxPowerLowOverAlarm: To detect whether RX output power is below low alarm level or not.
				118: gotDMIRxPowerLowFallAlarm: 
				===============
				119: gotDMIRxPowerHighOverWarning: To detect whether RX output power exceeds high warning level or not.
				120: gotDMIRxPowerHighFallWarning: 
				===============
				121: gotDMIRxPowerLowOverWarning: To detect whether RX output power is below low warning level or not.
				122: gotDMIRxPowerLowFallWarning: 
				===============
				123: nosRemoteUpgradeRequest: 
				124: nosRemoteUpgradeSuccess: 
				125: nosRemoteUpgradeFailAbort: 
				126: nosRemoteUpgradeFailHeaderError: 
				127: nosRemoteUpgradeFailDownloadError: 
				128: nosRemoteUpgradeFailFlashError: 
				129: nosRemoteUpgradeStart: 
				===============
				130: systemDyingGasp:
				===============
				133: cliHistory: To detect whether CLI history is detected or not.
				134: cliHistoryNo:
				===============
				135: ntpConnectionFail: To detect whether NTP connection is failed or not.
				136: ntpConnectionFailNo:
				===============
				137: nmsConnectionTypeChanged:  To detect whether NMS connection type is changed.
				===============
				159: clockModuleRemoved:  To detect whether clock module is removed or installed.
				160: clockModuleInstalled:
				161: clockModuleInitFail:  To detect whether clock module initiolization is failed or not.
				162: clockModuleInitOk:
				===============
				163: cliHistoryLog: To detect whether CLI history log is over or not.
				164: cliHistoryLogNo:
				===============
				165: slotActionEvent: To detect whether slot action is changed.
				166: slotStateChange: To detect whether slot state is changed.
				===============
				167: interfaceAdminDown: To detect whether physical or logical interface's admin link status is up or down.
				168: interfaceAdminUp:
				===============
				169: slotPowerMonAbnormal: To detect whether slot power monitor abnormal or normal is detected.
				170: slotPowerMonNormal:
				===============
				171: slotErrorLEDChanged: To detect whether error LED is changed.
				===============
				185: cpuPpsOverThreshold: To detect whether PPS is over threshold or not.
				186: cpuPpsUnderThreshold:
				===============
				199: slotHealthStatusTimeout: To detect whether slot health status is time out or not.
				200: slotHealthStatusTimeoutCleared:
				===============
				201: advaTemperature: To detect whether current chassis temperature is less than chassis temperature threshold or not.
				202: advaTemperatureNo: 
				===============
				203: advaPSUFailure: To detect whether ADVA system's power supply unit has a failure or not.
				204: advaPSUFailureNo: 
				===============
				205: advaFanFailure: To detect whether ADVA system's FAN has a failure or not.
				206: advaFanFailureNo: 
				===============
				207: advaInterfaceReceiveFailure: To detect whether ADVA system's receipt has a failure or not.
				208: advaInterfaceReceiveFailureNo:  
				===============
				209: advaInterfaceOpticalThreshold: To detect whether Adva system's optical receive power level is 
								    less than optical threshold or not.
				210: advaInterfaceOpticalThresholdNo: 
				===============
				211: advaInterfaceTransmitFault: To detect whether ADVA system's transmission has a failure or not.
				212: advaInterfaceTransmitFaultNo: 
				===============
				213: dvaInterfaceMisconfiguration: To detect whether ADVA system's interface is configured rightly or not.
				214: advaInterfaceMisconfigurationNo: 
				===============
				215: advaInterfaceSFPMismatch: To detect whether ADVA system's SFP interface is mismatched or not.
				216: advaInterfaceSFPMismatchNo: 
				===============
				217: advaVoltageLow: To detect whether ADVA system's current voltage is less than voltage threshold or not.
				218: advaVoltageLowNo: 
				===============
				219: advaVoltageHigh: To detect whether ADVA system's current voltage is greater than voltage threshold or not.
				220: advaVoltageHighNo: 
				===============
				301: erpDomainLotp: To detect whether LOTP(Loss of Test Packet) exists a domain of ERP or not. 
						    The Loss of Test Packet defect is defined when a node does not receive 
						    any test packet at any of its ports for a period of 3 times.
				302: erpDomainLotpNo: 
				===============
				303: erpDomainULotp: To detect whether undirectional LOTP(Loss of Test Packet) exists a domain of ERP or not. 
						     The Loss of Test Packet defect is defined when a RM node of one domain does not 
						     receive any test packet at one port for a period of 3 times.
				304: erpDomainULotpNo: 
				===============
				305: erpDomainMultipleRM: To detect whether Multiple RM node is supported or not. 
							  The defect is raised when a RM node receives its own test packets 
							  with an Ack destination address field with a non-zero value.
				306: erpDomainMultipleRMNo: 
				===============
				307: erpDomainRMNodeReacheablity: To detect whether RM reachability is raised or not. 
								  The detection of multiple failures indicates that the ring is segmented and 
							          that the RM Node is unreacheable. 
								  This is only possible at normal ring nodes isolated from the RM node.
				308: erpDomainRMNodeReacheablityNo: 
				===============
				391: startupConfigLoadEnded: To detect whether startup configuration load is ended.
				===============
				401: eponOnuDeregister: To detect whether ONU is registered into OLT or not. 
							That is, ONU that its operation is service on should be sent registration information to OLT. 
				402: eponOnuRegister: 
				===============
				403: eponOnuRegistrationError: To detect whether ONU is failed registeration process into OLT.
				404: eponOnuNoRegistrationError: 
				===============
				405: eponBadEncryptionKey: To detect wwhether the encryption key is valid or not.
							   A message between ONU and OLT is encrypted using random encryption key. 
							   There is that the encryption key is invalid as transmission failure from time to time.
				406: eponNoBadEncryptionKey: 
				===============
				407: eponLlidMistmatch: To detect whether Llid of message between ONU and OLT is valid or not. 
							On registering, ONU informs unique ID to OLT.
							And then, all communication between ONU and OLT must use the unique ID. 
							The unique ID is called Llid.
				408: eponNoLlidMismatch: 
				===============
				409: eponTooManyRegister: To detect whether the registered ONU per 1 OLT is greater than 32 or not. 
							  That is, ONU can be registered from 1 to the maximum 32 at 1 OLT.
				410: eponNoTooManyRegister: 
				===============
				411: eponDyingGASP: To detect whether a ONU is down from dying gasp or not. 
						    A ONU could be changed to down state as a number of reasons.
						    By the way, ONU that is changed to down as dying gasp would be sent dying gasp signal to OLT and 
						    then ONU's link would be changed to down.
				412: eponNoDyingGASP: 
				===============
				413: eponOnuErrFramePeriod: 
				414: eponOnuNoErrFramePeriod: 
				===============
				415: eponOnuErrFrame: 
				416: eponOnuNoErrFrame: 
				===============
				417: eponOnuErrFrameSecondSummary: 
				418: eponOnuNoErrFrameSecondSummary: 
				===============
				419: eponOnuLastOnuDeregister: To detect whether a deregistered ONU is last ONU or not. 
							       If a deregistered ONU is last ONU, the OLT would be changed to serviceable status. 
				420: eponOnuNoLastOnuDeregister: 
				===============
				421: eponOltCableDown: 
				422: eponOltRecoverCableDown: 
				===============
				501: autoCLIStart: To detect whether the scheduled auto CLI is started or not.
				502: autoCLINoStart: 
				===============
				503: autoCLIComplete: To detect whether the scheduled auto CLI is completed or not. 
				504: autoCLINoComplete: 
				===============
				505: autoCLIRemoveOutputFile: To detect whether the result file of the scheduled auto CLI is removed or not.
							      The reason that the result file is removed is that the configured file size for the result  is
							      less than the stored result file size. 
							      If so, the oldest file would be removed before everything.
				506: autoCLINoRemoveOutputFile: 
				===============
				507: autoResetSystem: To detect whether the system is restarted or not. 
						      The conditions that system is restarted is that ping loss threshold is 
						      less than current ping loss count during the configured interval and 
						      that current free memory size is less than configured free memory size.
				508: autoResetNoSystem: 
				===============
				509: autoResetPingReplyLoss: To detect whether ping reply from the designated network node is received or not.
							     Operator designates any gateway system that can communicate to detect 
							     current network environment. 
							     System sends ICMP packet to the designated gateway system periodically. 
							     If  the system doesn't receive ping reply packet within any interval, 
							     operator recognizes that the system can't communicate any more 
							     because of some problems of the system. 
				510: autoResetNoPingReplyLoss: 
				===============
				511: autoResetMemoryLeakDetect: To detect whether current free memory size is 
								less than the configured free memory size or not. 
								Periodically, free memory size is checked to confirm system availability.
				512: autoResetNoMemoryLeakDetect: 
				===============
				601: arulePacketDropDetect: To detect whether it is dropped some packet by arule or not.
				602: arulePacketDropRelease: 
				===============
				620: bME1CardNoDetect: 
				621: clearBME1CardNoDetect: 
				===============
				622: bME1CardAFEerror: 
				623: clearBME1CardAFEerror: 
				===============
				624: bME1CardIFEerror: 
				625: clearBME1CardIFEerror: 
				===============
				626: bME1CardFWerror: 
				627: clearBME1CardFWerror: 
				===============
				628: bME1CardPROVerror: 
				629: clearBME1CardPROVerror: 
				===============
				630: bME1CrashDetect: 
				631: clearBME1CrashDetect: 
				===============
				632: bME2CardNoDetect: 
				633: clearBME2CardNoDetect: 
				===============
				634: bME2CardAFEerror: 
				635: clearBME2CardAFEerror: 
				===============
				636: bME2CardIFEerror: 
				637: clearBME2CardIFEerror: 
				===============
				638: bME2CardFWerror: 
				639: clearBME2CardFWerror: 
				===============
				640: bME2CardPROVerror: 
				641: clearBME2CardPROVerror: 
				===============
				642: bME2CrashDetect: 
				643: clearBME2CrashDetect: 
				===============
				644: bME3CardNoDetect: 
				645: clearBME3CardNoDetect: 
				===============
				646: bME3CardAFEerror: 
				647: clearBME3CardAFEerror: 
				===============
				648: bME3CardIFEerror: 
				649: clearBME3CardIFEerror: 
				===============
				650: bME3CardFWerror: 
				651: clearBME3CardFWerror: 
				===============
				652: bME3CardPROVerror: 
				653: clearBME3CardPROVerror: 
				===============
				654: bME3CrashDetect: 
				655: clearBME3CrashDetect: 
				===============
				656: powerFromBattery: 
				657: clearPowerFromBattery: 
				===============
				658: invalidBatteryStatus: 
				659: clearInvalidBatteryStatus: 
				===============
				660: batteryChargeLow: 
				661: clearBatteryChargeLow: 
				===============
				662: batteryNotPresent: 
				663: clearBatteryNotPresent: 
				===============
				664: voltageLow: 
				665: clearVoltageLow: 
				===============
				666: tempOverThreshold: 
				667: clearTempOverThreshold: 
				===============
				668: tempUnderThreshold: 
				669: clearTempUnderThreshold: 
				===============
				670: cpuOverThreshold: 
				671: clearCpuOverThreshold: 
				===============
				672: trafficOverload: 
				673: clearTrafficOverload: 
				===============
				674: gEPONModuleNotDetect: 
				675: clearGEPONModuleNotDetect:
				===============
				676: gEPONPortOperationDown: 
				677: clearGEPONPortOperationDown: 
				===============
				678: gEPONNoIncomingTraffic: 
				679: clearGEPONNoIncomingTraffic: 
				===============
				680: processCrashDetect: 
				681: clearProcessCrashDetect: 
				===============
				682: memoryLeakDetect: 
				683: clearMemoryLeakDetect: 
				===============
				684: memoryCorrupDetect: 
				685: clearMemoryCorrupDetect: 
				===============
				686: memoryLowDetect: 
				687: clearMemoryLowDetect: 
				===============
				688: dataLineerror: 
				689: clearDataLineerror: 
				===============
				690: addressLineerror: 
				691: clearAddressLineerror: 
				===============
				692: chipsetNotDetcet: 
				693: clearChipsetNotDetcet: 
				===============
				694: pciBuserror: 
				695: clearPciBuserror: 
				===============
				696: securityAdminConnect: 
				697: clearSecurityAdminConnect: 
				===============
				698: oNUPowerDown: 
				699: clearONUPowerDown: 
				===============
				700: oNUNotRegister: 
				701: clearONUNotRegister: 
				===============
				702: oNTOpticPre: 
				703: clearONTOpticPre: 
				===============
				800: switchoverInitiated: 
				===============
				801: switchoverDone: 
				===============
				803: redConfigurationMisMatch: To detect whether redundancy configuration is mismatched.
				===============
				901: gponNoAuthCBU: To detect no auth CBU is detected.
				902: gponDuplicateONU: To detect ONU is duplicated.
				903: gponDyingGasp: To detect dying GASP is detected.
				904: gponUpgradeComplete: To detect upgrade complete is detected.
				905: gponDeregistered: To detect whether deregistered is detected or not.
				906: gponRegistered: 
				907: gponRogueOnu: To detect rogue ONU is detected
				908: gponOnuBatteryEvent: To detect whether ONU battery event is detected or not.
				909: clearGponOnuBetteryEvent:
				910: gponOnuPortOperStatus: To detectONU port operation statue is chagned.
				911: gponTransceiverChanged: To detect transceiver is changed.
				912: gponOltLosOn: To detect whether OLT LOS is on or off
				913: gponOltLosOff:
				914: gponOltLosiOn: To detect whether OLT LOSI is on or off
				915: gponOltLosiOff:
				916: gponDyingGaspOn: To detect whether dying GASP is on or off
				917: gponDyingGaspOff:
				918: gponOntOSUpgradeStatus: To detect ONT OS upgrade status is changed.
				919: gponOntBLUpgradeStatus: To detect BL upgrade status is changed.
				920: gponOltRxPowerLoss: To detect OLT RX power is loss.
				921: gponOltRxPowerDetected: To detect OLT RX power status is changed.
				922: gponOnuTemperatureHighOverThreshold: To detect whether ONU temperature exceeds high threshold or not.
				923: gponOnuTemperatureHighFallThreshold:
				924: gponOnuTemperatureLowOverThreshold: To detect whether ONU temperature belows low threshold or not.
				925: gponOnuTemperatureLowFallThreshold:
				926: gponOnuCpuOverThreshold: To detect whether ONU CPU exceeds threshold or not.
				927: gponOnuCpuFallThreshold: 
				928: gponOnuMemoryOverThreshold: To detect whether memory exceeds threshold or not.
				929: gponOnuMemoryFallThreshold: 
				930: gponOnuI2cFail: To detect ONU L2C fail is detected.
				931: gponOnuRxOpticLowThreshAlarmOn: To detect whether ONU RX optic belows low threshold or not.
				932: gponOnuRxOpticLowThreshAlarmOff: 
				933: gponOnuRxOpticHighThreshAlarmOn: To detect whether ONU RX optic exceeds high threshold or not.
				934: gponOnuRxOpticHighThreshAlarmOff:
				935: gponOltLOFIOn: To detect whether OLT LOFL is on or off
				936: gponOltLOFIOff:
				937: gponOltDOWOn: To detect whether OLT DOW is on or off
				938: gponOltDOWOff:
				939: gponOltSFOn: To detect whether OLT SF is on or off
				940: gponOltSFOff:
				941: gponOltSDOn: To detect whether OLT SD is on or off
				942: gponOltSDOff:
				943: gponOltLCDGIOn: To detect whether OLT LCDGL is on or off
				944: gponOltLCDGIOff:
				945: gponOltRDOn: To detect whether OLT RD is on or off
				946: gponOltRDOff:
				947: gponOltSUFOn: To detect whether OLT SUF is on or off
				948: gponOltSUFOff:
				949: gponOltLOAOn: To detect whether OLT LOA is on or off
				950: gponOltLOAOff:
				951: gponOltLOAMIOn: To detect whether OLT LOAML is on or off
				952: gponOltLOAMIOff:
				953: gponOltMEMOn: To detect whether OLT MEM is on or off
				954: gponOltMEMOff:
				955: gponOltPEEOn: To detect whether OLT PEE is on or off
				956: gponOltPEEOff:
				957: gponOltPSTOn: To detect whether OLT PST is on or off
				958: gponOltPSTOff:
				959: gponOltERROn: To detect whether OLT ERR is on or off
				960: gponOltERROff:
				961: gponOltREIOn: To detect whether OLT REI is on or off
				962: gponOltREIOff:
				963: gponAntiSpoofingDupPortOn: To detect whether anti spoofing port is duplicated or not.
				964: gponAntiSpoofingDupPortOff:
				965: gponRedundancySwitchOver: To detect redundancy switchover is changed.
				966: gponDuplicatedRangingResponse: To detect ranging response is changed.
				967: gponOnuPortOpticModuleRemove: To detect whether ONU port optic module is removed or installed.
				968: gponOnuPortOpticModuleInstall:
				969: gponOnuOMCCProblemDetected: To detect whether ONU OMCC problem is detected or not.
				970: gponOnuOMCCProblemCleared:
				971: gponOltFixedTcontAlarmOn: To detect whether OLT fixed Tcont alarm is on or off.
				972: gponOltFixedTcontAlarmOff:
				973: gponOltDynamicTcontAlarmOn: To detect whether OLT dynamic Tcont alarm is on or off.
				974: gponOltDynamicTcontAlarmOff:
				975: gponOltPortCountAlarmOn: To detect whether OLT port count alarm is on or off.
				976: gponOltPortCountAlarmOff:
				977: gponOltCableDownAlarmOn: To detect whether OLT cable down alarm is on or off.
				978: gponOltCableDownAlarmOff:
				979: gponOltDeactiveMonitorAlarmOn: To detect whether deactive monitor alarm is on or off.
				980: gponOltDeactiveMonitorAlarmOff:
				981: gponOltDfiOn: To detect whether OLT DFI is on or off.
				982: gponOltDfiOff:
				984: gponOltTransceiverPortChanged: To detect OLT transeiver port is changed.
				985: gponOnuPortOperStatusDown: To detect whether ONU port operation status is down or up.
				986: gponOnuPortOperStatusUp::
				===============
				1101: emLogDefectCPUHighOver: To detect whether EM log detect CPU exceeds threshold or not.
				1102: emLogDefectCPUHighUnder:
				1103: emLogTemperHighOver: To detect whether EM log temperature exceeds high threshold or not.
				1104: emLogTemperHighUnder:
				1105: emLogTemperLowUnder: To detect whether EM log CPU belows low threshold or not.
				1106: emLogTemperLowOver:
				1107: emLogMemLowUnder:  To detect whether EM log memory belows low threshold or not.
				1108: emLogMemLowOver:
				1109: emLogFanFail:  To detect whether EM log fan status is failed or not.
				1110: emLogFanFailCleared:
				1111: emLogPhyCRCFail: To detect whether EM log physical CRC is failed or not.
				1112: emLogPhyCRCFailCleared:
				1113: emLogPhyDetectFail: To detect whether EM log physical status is failed or not.
				1114: emLogPhyDetectFailCleared:
				1115: emLogSFUMateInitFail: To detect whether EM log SFU mate initialization is failed or not.
				1116: emLogSFUMateInitFailCleared:
				1117: emLogDaemonHealthBad: To detect whether EM log daemon health is bad or not.
				1118: emLogDaemonHealthBadCleared:
				1119: emLogGPIURavenLinkDown: To detect whether EM log GPIU RAVEN link is down or not.
				1120: emLogGPIURavenLinkDownCleared:
				===============
				1151: slotNosUpgradeStart: To detect whether slot NOS upgrade is started or ended.
				1152: slotNosUpgradeEnd:
				===============
				1331: gponOnuAniVoltageLowThreshAlarmOn: To detect whether ONU ANI voltage belows low threshold or not.
				1332: gponOnuAniVoltageLowThreshAlarmOff:
				1333: gponOnuAniVoltageHighThreshAlarmOn: To detect whether ONU ANI voltage exceeds high threshold or not.
				1334: gponOnuAniVoltageHighThreshAlarmOff:
				1335: gponOnuAniTemperatureLowThreshAlarmOn: To detect whether ONU ANI temperature belows low threshold or not.
				1336: gponOnuAniTemperatureLowThreshAlarmOff:
				1337: gponOnuAniTemperatureHighThreshAlarmOn: To detect whether ONU ANI temperature exceeds high threshold or not.
				1338: gponOnuAniTemperatureHighThreshAlarmOff:
				1339: gponOnuAniTxBiasLowThreshAlarmOn: To detect whether ONU ANI TX bias belows low threshold or not.
				1340: gponOnuAniTxBiasLowThreshAlarmOff:
				1341: gponOnuAniTxBiasHighThreshAlarmOn: To detect whether ONU ANI TX bias exceeds high threshold or not. 
				1342: gponOnuAniTxBiasHighThreshAlarmOff:
				1343: gponOnuAniTxpowerLowThreshAlarmOn: To detect whether ONU ANI TX power belows low threshold or not.
				1344: gponOnuAniTxpowerLowThreshAlarmOff:
				1345: gponOnuAniTxpowerHighThreshAlarmOn: To detect whether ONU ANI TX power exceeds high threshold or not.
				1346: gponOnuAniTxpowerHighThreshAlarmOff:"
			::= { sleAlarmHistoryEntry 2 }

		
--   1.3.6.1.4.1.6296.101.4.4.1.1.3
-- 1.3.6.1.4.1.6296.101.4.4.1.1.3
		-- 1.3.6.1.4.1.6296.101.4.4.1.1.3
		sleAlarmHistorySeverity OBJECT-TYPE
			SYNTAX INTEGER
				{
				critical(1),
				major(2),
				minor(3),
				warning(4),
				intermediate(5)
				}
			MAX-ACCESS read-only
			STATUS current
			DESCRIPTION
				" The severity of alarm. "
			::= { sleAlarmHistoryEntry 3 }

		
--   1.3.6.1.4.1.6296.101.4.4.1.1.4
-- 1.3.6.1.4.1.6296.101.4.4.1.1.4
		-- 1.3.6.1.4.1.6296.101.4.4.1.1.4
		sleAlarmHistoryText OBJECT-TYPE
			SYNTAX OCTET STRING (SIZE (0..255))
			MAX-ACCESS read-only
			STATUS current
			DESCRIPTION
				"Textual description of specific problem reported by alarming.
				To be discussed: Option is to define an alarm for every problem
				"
			::= { sleAlarmHistoryEntry 4 }

		
--   1.3.6.1.4.1.6296.101.4.4.1.1.5
-- 1.3.6.1.4.1.6296.101.4.4.1.1.5
		-- 1.3.6.1.4.1.6296.101.4.4.1.1.5
		sleAlarmHistoryTime OBJECT-TYPE
			SYNTAX Integer32
			MAX-ACCESS read-only
			STATUS current
			DESCRIPTION
				" The severity of alarm. "
			::= { sleAlarmHistoryEntry 5 }

		
--   1.3.6.1.4.1.6296.101.4.4.1.1.6
-- 1.3.6.1.4.1.6296.101.4.4.1.1.6
		-- 1.3.6.1.4.1.6296.101.4.4.1.1.6
		sleAlarmHistorySeqNum OBJECT-TYPE
			SYNTAX Counter32
			MAX-ACCESS read-only
			STATUS current
			DESCRIPTION
				"Sequence number for the alarm synchronization. 
				This value has a number to be used for the next alarm trap."
			::= { sleAlarmHistoryEntry 6 }

		
--  1.3.6.1.4.1.6296.101.4.4.1.1.7
		-- 1.3.6.1.4.1.6296.101.4.4.1.1.7
		sleAlarmHistoryPairType OBJECT-TYPE
			SYNTAX INTEGER
				{
				pair(0),
				mono(1)
				}
			MAX-ACCESS read-only
			STATUS current
			DESCRIPTION
				"The type is whether alarm trap is pair or mono."
			::= { sleAlarmHistoryEntry 7 }

		
--   1.3.6.1.4.1.6296.101.4.4.2
-- 1.3.6.1.4.1.6296.101.4.4.2
		-- 1.3.6.1.4.1.6296.101.4.4.2
		sleAlarmHistoryControl OBJECT IDENTIFIER ::= { sleAlarmHistory 2 }

		
--   1.3.6.1.4.1.6296.101.4.4.2.1
-- 1.3.6.1.4.1.6296.101.4.4.2.1
		-- 1.3.6.1.4.1.6296.101.4.4.2.1
		sleAlarmHistoryControlRequest OBJECT-TYPE
			SYNTAX INTEGER { clearAlarmHistory(1) }
			MAX-ACCESS read-write
			STATUS current
			DESCRIPTION
				" This attribute identifies the control commands.
				updateAlarmList:
				   the NE updates entries of alarms in the sleAlarmListTable
				   after having changed alarm severities of alarms 
				   (due to change profile pointers in
				   managed entities or after modification of alarm severities 
				   in profiles). This command should be applied once after having 
				   finisled modifications of severties.
				modifyAlarmSeverity: 
				   modifies the severity of an alarm in specific profile.
				createAlarmSeverityProfile: 
				   creates a new profile with default severities.
				   The severities then have to be modified with command changeAlarmSeverity.
				deleteAlarmSeverityProfile: 
				   deletes a profile. Profile 1 is not allowed to be deleted.
				 
				Notifications : none "
			::= { sleAlarmHistoryControl 1 }

		
--   1.3.6.1.4.1.6296.101.4.4.2.2
-- 1.3.6.1.4.1.6296.101.4.4.2.2
		-- 1.3.6.1.4.1.6296.101.4.4.2.2
		sleAlarmHistoryControlStatus OBJECT-TYPE
			SYNTAX SleControlStatusType
			MAX-ACCESS read-only
			STATUS current
			DESCRIPTION
				" The status of a control request. "
			::= { sleAlarmHistoryControl 2 }

		
--   1.3.6.1.4.1.6296.101.4.4.2.3
-- 1.3.6.1.4.1.6296.101.4.4.2.3
		-- 1.3.6.1.4.1.6296.101.4.4.2.3
		sleAlarmHistoryControlTimer OBJECT-TYPE
			SYNTAX Unsigned32
			MAX-ACCESS read-write
			STATUS current
			DESCRIPTION
				" The maximum wait time for the manager for command ending.
				For long running commands.
				The manager reads this value from the DSLAM. "
			::= { sleAlarmHistoryControl 3 }

		
--   1.3.6.1.4.1.6296.101.4.4.2.4
-- 1.3.6.1.4.1.6296.101.4.4.2.4
		-- 1.3.6.1.4.1.6296.101.4.4.2.4
		sleAlarmHistoryControlTimeStamp OBJECT-TYPE
			SYNTAX TimeTicks
			MAX-ACCESS read-only
			STATUS current
			DESCRIPTION
				" The time stamp of the last command (end of command). "
			::= { sleAlarmHistoryControl 4 }

		
--   1.3.6.1.4.1.6296.101.4.4.2.5
-- 1.3.6.1.4.1.6296.101.4.4.2.5
		-- 1.3.6.1.4.1.6296.101.4.4.2.5
		sleAlarmHistoryControlReqResult OBJECT-TYPE
			SYNTAX SleControlRequestResultType
			MAX-ACCESS read-only
			STATUS current
			DESCRIPTION
				" The result of the last user command. "
			::= { sleAlarmHistoryControl 5 }

		
--   1.3.6.1.4.1.6296.101.4.4.3
-- 1.3.6.1.4.1.6296.101.4.4.3
		-- 1.3.6.1.4.1.6296.101.4.4.3
		sleAlarmHistoryNotification OBJECT IDENTIFIER ::= { sleAlarmHistory 3 }

		
--   1.3.6.1.4.1.6296.101.4.4.3.1
-- 1.3.6.1.4.1.6296.101.4.4.3.1
		-- 1.3.6.1.4.1.6296.101.4.4.3.1
		sleAlarmHistoryCleared NOTIFICATION-TYPE
			OBJECTS { sleAlarmHistoryControlRequest, sleAlarmHistoryControlTimeStamp, sleAlarmHistoryControlReqResult }
			STATUS current
			DESCRIPTION 
				"Description."
			::= { sleAlarmHistoryNotification 1 }

		
--   1.3.6.1.4.1.6296.101.4.5
-- 1.3.6.1.4.1.6296.101.4.5
		-- 1.3.6.1.4.1.6296.101.4.5
		sleEfmOam OBJECT IDENTIFIER ::= { sleFaultMgmt 5 }

		
--   1.3.6.1.4.1.6296.101.4.5.1
-- 1.3.6.1.4.1.6296.101.4.5.1
		-- 1.3.6.1.4.1.6296.101.4.5.1
		sleEfmOamTable OBJECT-TYPE
			SYNTAX SEQUENCE OF SleEfmOamEntry
			MAX-ACCESS not-accessible
			STATUS current
			DESCRIPTION
				"Description."
			::= { sleEfmOam 1 }

		
--   1.3.6.1.4.1.6296.101.4.5.1.1
-- 1.3.6.1.4.1.6296.101.4.5.1.1
		-- 1.3.6.1.4.1.6296.101.4.5.1.1
		sleEfmOamEntry OBJECT-TYPE
			SYNTAX SleEfmOamEntry
			MAX-ACCESS not-accessible
			STATUS current
			DESCRIPTION
				"Description."
			INDEX { sleOamPortIndex }
			::= { sleEfmOamTable 1 }

		
		SleEfmOamEntry ::=
			SEQUENCE { 
				sleOamPortIndex
					INTEGER,
				sleOamMuxAction
					INTEGER,
				sleOamParAction
					INTEGER,
				sleOamAdminState
					INTEGER,
				sleOamMode
					INTEGER,
				sleOamUnidirectionMode
					INTEGER,
				sleOamFunctionsSupported
					BITS,
				sleOamPeerStatus
					INTEGER,
				sleOamPeerMacAddress
					MacAddress,
				sleOamPeerMode
					INTEGER,
				sleOamPeerFunctionsSupported
					BITS,
				sleOamRemLoopback
					INTEGER,
				sleOamRemLoopbackCnt
					INTEGER,
				sleOamLm
					INTEGER,
				sleOamLmAction
					INTEGER,
				sleOamLmFrameWindow
					INTEGER,
				sleOamLmFrameThresh
					INTEGER,
				sleOamLmFrameTotal
					Counter64,
				sleOamLmFramePeriodWindow
					Integer32,
				sleOamLmFramePeriodThresh
					Integer32,
				sleOamLmFramePeriodTotal
					Counter64,
				sleOamLmFrameSecondSummaryWindow
					Integer32,
				sleOamLmFrameSecondSummaryThresh
					Integer32,
				sleOamLmFrameSecondSummaryTotal
					Counter64,
				sleOamLmSymbolPeriodWindow
					INTEGER,
				sleOamLmSymbolPeriodThresh
					INTEGER,
				sleOamLmSymbolPeriodTotal
					Counter64,
				sleOamLmRemSeqNum
					Integer32,
				sleOamLmRemFrameLength
					Integer32,
				sleOamLmRemFrameTimeStamp
					TimeTicks,
				sleOamLmRemFrameWindow
					Integer32,
				sleOamLmRemFrameThresh
					Integer32,
				sleOamLmRemFrameErrors
					Integer32,
				sleOamLmRemFrameErrorRunTotal
					Counter64,
				sleOamLmRemFrameEventRunTotal
					Integer32,
				sleOamLmRemFramePeriodLength
					Integer32,
				sleOamLmRemFramePeriodTimeStamp
					TimeTicks,
				sleOamLmRemFramePeriodWindow
					Integer32,
				sleOamLmRemFramePeriodThresh
					Integer32,
				sleOamLmRemFramePeriodErrors
					Integer32,
				sleOamLmRemFramePeriodErrorRunTotal
					Counter64,
				sleOamLmRemFramePeriodEventRunTotal
					Integer32,
				sleOamLmRemFrameSecondSummaryLength
					Integer32,
				sleOamLmRemFrameSecondSummaryTimeStamp
					TimeTicks,
				sleOamLmRemFrameSecondSummaryWindow
					Integer32,
				sleOamLmRemFrameSecondSummaryThresh
					Integer32,
				sleOamLmRemFrameSecondSummaryErrors
					Integer32,
				sleOamLmRemFrameSecondSummaryErrorRunTotal
					Integer32,
				sleOamLmRemFrameSecondSummaryEventRunTotal
					Integer32,
				sleOamLmRemSymbolPeriodLength
					Integer32,
				sleOamLmRemSymbolPeriodTimeStamp
					TimeTicks,
				sleOamLmRemSymbolPeriodWindow
					Counter64,
				sleOamLmRemSymbolPeriodThresh
					Counter64,
				sleOamLmRemSymbolPeriodErrors
					Counter64,
				sleOamLmRemSymbolPeriodErrorRunTotal
					Counter64,
				sleOamLmRemSymbolPeriodEventRunTotal
					Counter64
			 }

--   1.3.6.1.4.1.6296.101.4.5.1.1.1
-- 1.3.6.1.4.1.6296.101.4.5.1.1.1
		-- 1.3.6.1.4.1.6296.101.4.5.1.1.1
		sleOamPortIndex OBJECT-TYPE
			SYNTAX INTEGER (1..255)
			MAX-ACCESS read-only
			STATUS current
			DESCRIPTION
				"Description."
			::= { sleEfmOamEntry 1 }

		
--   1.3.6.1.4.1.6296.101.4.5.1.1.2
-- 1.3.6.1.4.1.6296.101.4.5.1.1.2
		-- 1.3.6.1.4.1.6296.101.4.5.1.1.2
		sleOamMuxAction OBJECT-TYPE
			SYNTAX INTEGER
				{
				fwd(1),
				discard(2)
				}
			MAX-ACCESS read-only
			STATUS current
			DESCRIPTION
				"This value governs the flow of frames from 
				the MAC client to the Muliplexer function."
			::= { sleEfmOamEntry 2 }

		
--   1.3.6.1.4.1.6296.101.4.5.1.1.3
-- 1.3.6.1.4.1.6296.101.4.5.1.1.3
		-- 1.3.6.1.4.1.6296.101.4.5.1.1.3
		sleOamParAction OBJECT-TYPE
			SYNTAX INTEGER
				{
				fwd(1),
				lb(2),
				discard(3)
				}
			MAX-ACCESS read-only
			STATUS current
			DESCRIPTION
				"This value governs the flow of non-OAMPDUs 
				within the Parser function."
			::= { sleEfmOamEntry 3 }

		
--   1.3.6.1.4.1.6296.101.4.5.1.1.4
-- 1.3.6.1.4.1.6296.101.4.5.1.1.4
		-- 1.3.6.1.4.1.6296.101.4.5.1.1.4
		sleOamAdminState OBJECT-TYPE
			SYNTAX INTEGER
				{
				disable(0),
				enable(1)
				}
			MAX-ACCESS read-only
			STATUS current
			DESCRIPTION
				"This object is used to provision the default 
				administrative OAM mode for this interface."
			::= { sleEfmOamEntry 4 }

		
--   1.3.6.1.4.1.6296.101.4.5.1.1.5
-- 1.3.6.1.4.1.6296.101.4.5.1.1.5
		-- 1.3.6.1.4.1.6296.101.4.5.1.1.5
		sleOamMode OBJECT-TYPE
			SYNTAX INTEGER
				{
				passive(0),
				active(1)
				}
			MAX-ACCESS read-only
			STATUS current
			DESCRIPTION
				"This object configures the mode of OAM 
				operation for this Ethernet like interface."
			::= { sleEfmOamEntry 5 }

		
--   1.3.6.1.4.1.6296.101.4.5.1.1.6
-- 1.3.6.1.4.1.6296.101.4.5.1.1.6
		-- 1.3.6.1.4.1.6296.101.4.5.1.1.6
		sleOamUnidirectionMode OBJECT-TYPE
			SYNTAX INTEGER
				{
				notAvaliable(-2),
				disable(0),
				enable(1)
				}
			MAX-ACCESS read-only
			STATUS current
			DESCRIPTION
				"Description."
			::= { sleEfmOamEntry 6 }

		
--   1.3.6.1.4.1.6296.101.4.5.1.1.7
-- 1.3.6.1.4.1.6296.101.4.5.1.1.7
		-- 1.3.6.1.4.1.6296.101.4.5.1.1.7
		sleOamFunctionsSupported OBJECT-TYPE
			SYNTAX BITS
				{
				unidirectionalSupport(0),
				loopbackSupport(1),
				eventSupport(2),
				variableSupport(3)
				}
			MAX-ACCESS read-only
			STATUS current
			DESCRIPTION
				"The OAM functions supported on this 
				Ethernet like interface."
			::= { sleEfmOamEntry 7 }

		
--   1.3.6.1.4.1.6296.101.4.5.1.1.8
-- 1.3.6.1.4.1.6296.101.4.5.1.1.8
		-- 1.3.6.1.4.1.6296.101.4.5.1.1.8
		sleOamPeerStatus OBJECT-TYPE
			SYNTAX INTEGER
				{
				inactive(0),
				active(1)
				}
			MAX-ACCESS read-only
			STATUS current
			DESCRIPTION
				"This object indicates whether the information 
				in this row should be considered valid."
			::= { sleEfmOamEntry 8 }

		
--   1.3.6.1.4.1.6296.101.4.5.1.1.9
-- 1.3.6.1.4.1.6296.101.4.5.1.1.9
		-- 1.3.6.1.4.1.6296.101.4.5.1.1.9
		sleOamPeerMacAddress OBJECT-TYPE
			SYNTAX MacAddress
			MAX-ACCESS read-only
			STATUS current
			DESCRIPTION
				"The MAC address of the peer OAM entity."
			::= { sleEfmOamEntry 9 }

		
--   1.3.6.1.4.1.6296.101.4.5.1.1.10
-- 1.3.6.1.4.1.6296.101.4.5.1.1.10
		-- 1.3.6.1.4.1.6296.101.4.5.1.1.10
		sleOamPeerMode OBJECT-TYPE
			SYNTAX INTEGER
				{
				passive(0),
				active(1),
				unknown(2)
				}
			MAX-ACCESS read-only
			STATUS current
			DESCRIPTION
				"The mode Info of the OAM peer as reflected 
				in the latest Information OAMPDU received with 
				a Local Information TLV."
			::= { sleEfmOamEntry 10 }

		
--   1.3.6.1.4.1.6296.101.4.5.1.1.11
-- 1.3.6.1.4.1.6296.101.4.5.1.1.11
		-- 1.3.6.1.4.1.6296.101.4.5.1.1.11
		sleOamPeerFunctionsSupported OBJECT-TYPE
			SYNTAX BITS
				{
				unidirectionalSupport(0),
				loopbackSupport(1),
				eventSupport(2),
				variableSupport(3)
				}
			MAX-ACCESS read-only
			STATUS current
			DESCRIPTION
				"The OAM functions supported on this 
				Ethernet like interface."
			::= { sleEfmOamEntry 11 }

		
--   1.3.6.1.4.1.6296.101.4.5.1.1.12
-- 1.3.6.1.4.1.6296.101.4.5.1.1.12
		-- 1.3.6.1.4.1.6296.101.4.5.1.1.12
		sleOamRemLoopback OBJECT-TYPE
			SYNTAX INTEGER
				{
				disable(0),
				enable(1)
				}
			MAX-ACCESS read-only
			STATUS current
			DESCRIPTION
				"Description."
			::= { sleEfmOamEntry 12 }

		
--   1.3.6.1.4.1.6296.101.4.5.1.1.13
-- 1.3.6.1.4.1.6296.101.4.5.1.1.13
		-- 1.3.6.1.4.1.6296.101.4.5.1.1.13
		sleOamRemLoopbackCnt OBJECT-TYPE
			SYNTAX INTEGER (1..100)
			MAX-ACCESS read-only
			STATUS current
			DESCRIPTION
				"The number of test Packet"
			::= { sleEfmOamEntry 13 }

		
--   1.3.6.1.4.1.6296.101.4.5.1.1.14
-- 1.3.6.1.4.1.6296.101.4.5.1.1.14
		-- 1.3.6.1.4.1.6296.101.4.5.1.1.14
		sleOamLm OBJECT-TYPE
			SYNTAX INTEGER
				{
				disable(0),
				enable(1)
				}
			MAX-ACCESS read-only
			STATUS current
			DESCRIPTION
				"This value indicates whether Link-Monitor supports or not for port index."
			::= { sleEfmOamEntry 14 }

		
--   1.3.6.1.4.1.6296.101.4.5.1.1.15
-- 1.3.6.1.4.1.6296.101.4.5.1.1.15
		-- 1.3.6.1.4.1.6296.101.4.5.1.1.15
		sleOamLmAction OBJECT-TYPE
			SYNTAX INTEGER
				{
				syslog(0),
				snmpTrap(1)
				}
			MAX-ACCESS read-only
			STATUS current
			DESCRIPTION
				"The Action of Link-Monitor for port index."
			::= { sleEfmOamEntry 15 }

		
--   1.3.6.1.4.1.6296.101.4.5.1.1.16
-- 1.3.6.1.4.1.6296.101.4.5.1.1.16
		-- 1.3.6.1.4.1.6296.101.4.5.1.1.16
		sleOamLmFrameWindow OBJECT-TYPE
			SYNTAX INTEGER (10..600)
			UNITS "100 ms"
			MAX-ACCESS read-only
			STATUS current
			DESCRIPTION
				"This value is the Window size of Errored Frame.
				Default : 10, Unit : 100ms
				"
			::= { sleEfmOamEntry 16 }

		
--   1.3.6.1.4.1.6296.101.4.5.1.1.17
-- 1.3.6.1.4.1.6296.101.4.5.1.1.17
		-- 1.3.6.1.4.1.6296.101.4.5.1.1.17
		sleOamLmFrameThresh OBJECT-TYPE
			SYNTAX INTEGER (0..65535)
			MAX-ACCESS read-only
			STATUS current
			DESCRIPTION
				"This value is the Threshold size of Errored Frame.
				Default: 1
				"
			::= { sleEfmOamEntry 17 }

		
--   1.3.6.1.4.1.6296.101.4.5.1.1.18
-- 1.3.6.1.4.1.6296.101.4.5.1.1.18
		-- 1.3.6.1.4.1.6296.101.4.5.1.1.18
		sleOamLmFrameTotal OBJECT-TYPE
			SYNTAX Counter64
			MAX-ACCESS read-only
			STATUS current
			DESCRIPTION
				"Total Count of Errored Frame"
			::= { sleEfmOamEntry 18 }

		
--   1.3.6.1.4.1.6296.101.4.5.1.1.19
-- 1.3.6.1.4.1.6296.101.4.5.1.1.19
		-- 1.3.6.1.4.1.6296.101.4.5.1.1.19
		sleOamLmFramePeriodWindow OBJECT-TYPE
			SYNTAX Integer32 (1000..200000000)
			MAX-ACCESS read-only
			STATUS current
			DESCRIPTION
				"This value is size of Errored Period Window.
				Default : 1000000 frames
				"
			::= { sleEfmOamEntry 19 }

		
--   1.3.6.1.4.1.6296.101.4.5.1.1.20
-- 1.3.6.1.4.1.6296.101.4.5.1.1.20
		-- 1.3.6.1.4.1.6296.101.4.5.1.1.20
		sleOamLmFramePeriodThresh OBJECT-TYPE
			SYNTAX Integer32 (0..65535)
			MAX-ACCESS read-only
			STATUS current
			DESCRIPTION
				"This value is size of Errored Period Threshold.
				Default :  10
				"
			::= { sleEfmOamEntry 20 }

		
--   1.3.6.1.4.1.6296.101.4.5.1.1.21
-- 1.3.6.1.4.1.6296.101.4.5.1.1.21
		-- 1.3.6.1.4.1.6296.101.4.5.1.1.21
		sleOamLmFramePeriodTotal OBJECT-TYPE
			SYNTAX Counter64
			MAX-ACCESS read-only
			STATUS current
			DESCRIPTION
				"Total Count of Errored Period Frame"
			::= { sleEfmOamEntry 21 }

		
--   1.3.6.1.4.1.6296.101.4.5.1.1.22
-- 1.3.6.1.4.1.6296.101.4.5.1.1.22
		-- 1.3.6.1.4.1.6296.101.4.5.1.1.22
		sleOamLmFrameSecondSummaryWindow OBJECT-TYPE
			SYNTAX Integer32 (10..900)
			UNITS "seconds"
			MAX-ACCESS read-only
			STATUS current
			DESCRIPTION
				"This value is the Window size of errored frame in a second
				Default : 60 secs
				"
			::= { sleEfmOamEntry 22 }

		
--   1.3.6.1.4.1.6296.101.4.5.1.1.23
-- 1.3.6.1.4.1.6296.101.4.5.1.1.23
		-- 1.3.6.1.4.1.6296.101.4.5.1.1.23
		sleOamLmFrameSecondSummaryThresh OBJECT-TYPE
			SYNTAX Integer32 (0..900)
			MAX-ACCESS read-only
			STATUS current
			DESCRIPTION
				"This value is the Threshold size of errored frame in a second
				Default: 1
				"
			::= { sleEfmOamEntry 23 }

		
--   1.3.6.1.4.1.6296.101.4.5.1.1.24
-- 1.3.6.1.4.1.6296.101.4.5.1.1.24
		-- 1.3.6.1.4.1.6296.101.4.5.1.1.24
		sleOamLmFrameSecondSummaryTotal OBJECT-TYPE
			SYNTAX Counter64
			MAX-ACCESS read-only
			STATUS current
			DESCRIPTION
				"Total Count of Errored Frame Second"
			::= { sleEfmOamEntry 24 }

		
--   1.3.6.1.4.1.6296.101.4.5.1.1.25
-- 1.3.6.1.4.1.6296.101.4.5.1.1.25
		-- 1.3.6.1.4.1.6296.101.4.5.1.1.25
		sleOamLmSymbolPeriodWindow OBJECT-TYPE
			SYNTAX INTEGER (1..1000000)
			MAX-ACCESS read-only
			STATUS current
			DESCRIPTION
				"This value is the window size of symbol errors.
				Default: 625 millions, Unit: 1 million
				"
			::= { sleEfmOamEntry 25 }

		
--   1.3.6.1.4.1.6296.101.4.5.1.1.26
-- 1.3.6.1.4.1.6296.101.4.5.1.1.26
		-- 1.3.6.1.4.1.6296.101.4.5.1.1.26
		sleOamLmSymbolPeriodThresh OBJECT-TYPE
			SYNTAX INTEGER (0..65535)
			MAX-ACCESS read-only
			STATUS current
			DESCRIPTION
				"This value is the Threshold size of symbol errors
				Default : 1
				"
			::= { sleEfmOamEntry 26 }

		
--   1.3.6.1.4.1.6296.101.4.5.1.1.27
-- 1.3.6.1.4.1.6296.101.4.5.1.1.27
		-- 1.3.6.1.4.1.6296.101.4.5.1.1.27
		sleOamLmSymbolPeriodTotal OBJECT-TYPE
			SYNTAX Counter64
			MAX-ACCESS read-only
			STATUS current
			DESCRIPTION
				"Total Count of Symbol errors"
			::= { sleEfmOamEntry 27 }

		
--   1.3.6.1.4.1.6296.101.4.5.1.1.28
-- 1.3.6.1.4.1.6296.101.4.5.1.1.28
		-- 1.3.6.1.4.1.6296.101.4.5.1.1.28
		sleOamLmRemSeqNum OBJECT-TYPE
			SYNTAX Integer32
			MAX-ACCESS read-only
			STATUS current
			DESCRIPTION
				"This value is the Sequence Number for event"
			::= { sleEfmOamEntry 28 }

		
--   1.3.6.1.4.1.6296.101.4.5.1.1.29
-- 1.3.6.1.4.1.6296.101.4.5.1.1.29
		-- 1.3.6.1.4.1.6296.101.4.5.1.1.29
		sleOamLmRemFrameLength OBJECT-TYPE
			SYNTAX Integer32 (0..255)
			MAX-ACCESS read-only
			STATUS current
			DESCRIPTION
				"This value is the Length of Errored Frame"
			::= { sleEfmOamEntry 29 }

		
--   1.3.6.1.4.1.6296.101.4.5.1.1.30
-- 1.3.6.1.4.1.6296.101.4.5.1.1.30
		-- 1.3.6.1.4.1.6296.101.4.5.1.1.30
		sleOamLmRemFrameTimeStamp OBJECT-TYPE
			SYNTAX TimeTicks
			MAX-ACCESS read-only
			STATUS current
			DESCRIPTION
				"This value is the TimeStamp of Errored Frame"
			::= { sleEfmOamEntry 30 }

		
--   1.3.6.1.4.1.6296.101.4.5.1.1.31
-- 1.3.6.1.4.1.6296.101.4.5.1.1.31
		-- 1.3.6.1.4.1.6296.101.4.5.1.1.31
		sleOamLmRemFrameWindow OBJECT-TYPE
			SYNTAX Integer32
			MAX-ACCESS read-only
			STATUS current
			DESCRIPTION
				"This value is the Window Size of Errored Frame"
			::= { sleEfmOamEntry 31 }

		
--   1.3.6.1.4.1.6296.101.4.5.1.1.32
-- 1.3.6.1.4.1.6296.101.4.5.1.1.32
		-- 1.3.6.1.4.1.6296.101.4.5.1.1.32
		sleOamLmRemFrameThresh OBJECT-TYPE
			SYNTAX Integer32
			MAX-ACCESS read-only
			STATUS current
			DESCRIPTION
				"This value is the Threshold Size of Errored Frame"
			::= { sleEfmOamEntry 32 }

		
--   1.3.6.1.4.1.6296.101.4.5.1.1.33
-- 1.3.6.1.4.1.6296.101.4.5.1.1.33
		-- 1.3.6.1.4.1.6296.101.4.5.1.1.33
		sleOamLmRemFrameErrors OBJECT-TYPE
			SYNTAX Integer32
			MAX-ACCESS read-only
			STATUS current
			DESCRIPTION
				"This value is the Count of Errored Frame"
			::= { sleEfmOamEntry 33 }

		
--   1.3.6.1.4.1.6296.101.4.5.1.1.34
-- 1.3.6.1.4.1.6296.101.4.5.1.1.34
		-- 1.3.6.1.4.1.6296.101.4.5.1.1.34
		sleOamLmRemFrameErrorRunTotal OBJECT-TYPE
			SYNTAX Counter64
			MAX-ACCESS read-only
			STATUS current
			DESCRIPTION
				"This value is the Total Count of Errored Frame"
			::= { sleEfmOamEntry 34 }

		
--   1.3.6.1.4.1.6296.101.4.5.1.1.35
-- 1.3.6.1.4.1.6296.101.4.5.1.1.35
		-- 1.3.6.1.4.1.6296.101.4.5.1.1.35
		sleOamLmRemFrameEventRunTotal OBJECT-TYPE
			SYNTAX Integer32
			MAX-ACCESS read-only
			STATUS current
			DESCRIPTION
				"This value is the Total Count of Errored Frame Event"
			::= { sleEfmOamEntry 35 }

		
--   1.3.6.1.4.1.6296.101.4.5.1.1.36
-- 1.3.6.1.4.1.6296.101.4.5.1.1.36
		-- 1.3.6.1.4.1.6296.101.4.5.1.1.36
		sleOamLmRemFramePeriodLength OBJECT-TYPE
			SYNTAX Integer32 (0..255)
			MAX-ACCESS read-only
			STATUS current
			DESCRIPTION
				"This value is the Length of Errored Frame Period"
			::= { sleEfmOamEntry 36 }

		
--   1.3.6.1.4.1.6296.101.4.5.1.1.37
-- 1.3.6.1.4.1.6296.101.4.5.1.1.37
		-- 1.3.6.1.4.1.6296.101.4.5.1.1.37
		sleOamLmRemFramePeriodTimeStamp OBJECT-TYPE
			SYNTAX TimeTicks
			MAX-ACCESS read-only
			STATUS current
			DESCRIPTION
				"This value is the TimeStamp of Errored Frame Period"
			::= { sleEfmOamEntry 37 }

		
--   1.3.6.1.4.1.6296.101.4.5.1.1.38
-- 1.3.6.1.4.1.6296.101.4.5.1.1.38
		-- 1.3.6.1.4.1.6296.101.4.5.1.1.38
		sleOamLmRemFramePeriodWindow OBJECT-TYPE
			SYNTAX Integer32
			MAX-ACCESS read-only
			STATUS current
			DESCRIPTION
				"This value is the Window Size of Errored Frame Period"
			::= { sleEfmOamEntry 38 }

		
--   1.3.6.1.4.1.6296.101.4.5.1.1.39
-- 1.3.6.1.4.1.6296.101.4.5.1.1.39
		-- 1.3.6.1.4.1.6296.101.4.5.1.1.39
		sleOamLmRemFramePeriodThresh OBJECT-TYPE
			SYNTAX Integer32
			MAX-ACCESS read-only
			STATUS current
			DESCRIPTION
				"This value is the Threshold Size of Errored Frame Period"
			::= { sleEfmOamEntry 39 }

		
--   1.3.6.1.4.1.6296.101.4.5.1.1.40
-- 1.3.6.1.4.1.6296.101.4.5.1.1.40
		-- 1.3.6.1.4.1.6296.101.4.5.1.1.40
		sleOamLmRemFramePeriodErrors OBJECT-TYPE
			SYNTAX Integer32
			MAX-ACCESS read-only
			STATUS current
			DESCRIPTION
				"This value is the Count of Errored Frame Period"
			::= { sleEfmOamEntry 40 }

		
--   1.3.6.1.4.1.6296.101.4.5.1.1.41
-- 1.3.6.1.4.1.6296.101.4.5.1.1.41
		-- 1.3.6.1.4.1.6296.101.4.5.1.1.41
		sleOamLmRemFramePeriodErrorRunTotal OBJECT-TYPE
			SYNTAX Counter64
			MAX-ACCESS read-only
			STATUS current
			DESCRIPTION
				"This value is the Total Count of Errored Frame Period"
			::= { sleEfmOamEntry 41 }

		
--   1.3.6.1.4.1.6296.101.4.5.1.1.42
-- 1.3.6.1.4.1.6296.101.4.5.1.1.42
		-- 1.3.6.1.4.1.6296.101.4.5.1.1.42
		sleOamLmRemFramePeriodEventRunTotal OBJECT-TYPE
			SYNTAX Integer32
			MAX-ACCESS read-only
			STATUS current
			DESCRIPTION
				"This value is the Total Count of Errored Frame Period Event"
			::= { sleEfmOamEntry 42 }

		
--   1.3.6.1.4.1.6296.101.4.5.1.1.43
-- 1.3.6.1.4.1.6296.101.4.5.1.1.43
		-- 1.3.6.1.4.1.6296.101.4.5.1.1.43
		sleOamLmRemFrameSecondSummaryLength OBJECT-TYPE
			SYNTAX Integer32 (0..255)
			MAX-ACCESS read-only
			STATUS current
			DESCRIPTION
				"This value is the Length of Errored Frame Second Summary"
			::= { sleEfmOamEntry 43 }

		
--   1.3.6.1.4.1.6296.101.4.5.1.1.44
-- 1.3.6.1.4.1.6296.101.4.5.1.1.44
		-- 1.3.6.1.4.1.6296.101.4.5.1.1.44
		sleOamLmRemFrameSecondSummaryTimeStamp OBJECT-TYPE
			SYNTAX TimeTicks
			MAX-ACCESS read-only
			STATUS current
			DESCRIPTION
				"This value is the TimeStamp of Errored Frame Second Summary"
			::= { sleEfmOamEntry 44 }

		
--   1.3.6.1.4.1.6296.101.4.5.1.1.45
-- 1.3.6.1.4.1.6296.101.4.5.1.1.45
		-- 1.3.6.1.4.1.6296.101.4.5.1.1.45
		sleOamLmRemFrameSecondSummaryWindow OBJECT-TYPE
			SYNTAX Integer32
			MAX-ACCESS read-only
			STATUS current
			DESCRIPTION
				"This value is the Window size of Errored Frame Second Summary"
			::= { sleEfmOamEntry 45 }

		
--   1.3.6.1.4.1.6296.101.4.5.1.1.46
-- 1.3.6.1.4.1.6296.101.4.5.1.1.46
		-- 1.3.6.1.4.1.6296.101.4.5.1.1.46
		sleOamLmRemFrameSecondSummaryThresh OBJECT-TYPE
			SYNTAX Integer32
			MAX-ACCESS read-only
			STATUS current
			DESCRIPTION
				"This value is the Threshold size of Errored Frame Second Summary"
			::= { sleEfmOamEntry 46 }

		
--   1.3.6.1.4.1.6296.101.4.5.1.1.47
-- 1.3.6.1.4.1.6296.101.4.5.1.1.47
		-- 1.3.6.1.4.1.6296.101.4.5.1.1.47
		sleOamLmRemFrameSecondSummaryErrors OBJECT-TYPE
			SYNTAX Integer32
			MAX-ACCESS read-only
			STATUS current
			DESCRIPTION
				"This value is the Count of Errored Frame Second Summary"
			::= { sleEfmOamEntry 47 }

		
--   1.3.6.1.4.1.6296.101.4.5.1.1.48
-- 1.3.6.1.4.1.6296.101.4.5.1.1.48
		-- 1.3.6.1.4.1.6296.101.4.5.1.1.48
		sleOamLmRemFrameSecondSummaryErrorRunTotal OBJECT-TYPE
			SYNTAX Integer32
			MAX-ACCESS read-only
			STATUS current
			DESCRIPTION
				"This value is the Total Count of Errored Frame Second Summary"
			::= { sleEfmOamEntry 48 }

		
--   1.3.6.1.4.1.6296.101.4.5.1.1.49
-- 1.3.6.1.4.1.6296.101.4.5.1.1.49
		-- 1.3.6.1.4.1.6296.101.4.5.1.1.49
		sleOamLmRemFrameSecondSummaryEventRunTotal OBJECT-TYPE
			SYNTAX Integer32
			MAX-ACCESS read-only
			STATUS current
			DESCRIPTION
				"This value is the Total Count of Errored Frame Second Summary Event"
			::= { sleEfmOamEntry 49 }

		
--   1.3.6.1.4.1.6296.101.4.5.1.1.50
-- 1.3.6.1.4.1.6296.101.4.5.1.1.50
		-- 1.3.6.1.4.1.6296.101.4.5.1.1.50
		sleOamLmRemSymbolPeriodLength OBJECT-TYPE
			SYNTAX Integer32
			MAX-ACCESS read-only
			STATUS current
			DESCRIPTION
				"This value is the Length of Errored Symbols"
			::= { sleEfmOamEntry 50 }

		
--   1.3.6.1.4.1.6296.101.4.5.1.1.51
-- 1.3.6.1.4.1.6296.101.4.5.1.1.51
		-- 1.3.6.1.4.1.6296.101.4.5.1.1.51
		sleOamLmRemSymbolPeriodTimeStamp OBJECT-TYPE
			SYNTAX TimeTicks
			MAX-ACCESS read-only
			STATUS current
			DESCRIPTION
				"This value is the TimeStamp of Errored Symbols"
			::= { sleEfmOamEntry 51 }

		
--   1.3.6.1.4.1.6296.101.4.5.1.1.52
-- 1.3.6.1.4.1.6296.101.4.5.1.1.52
		-- 1.3.6.1.4.1.6296.101.4.5.1.1.52
		sleOamLmRemSymbolPeriodWindow OBJECT-TYPE
			SYNTAX Counter64
			MAX-ACCESS read-only
			STATUS current
			DESCRIPTION
				"This value is the Window size of Errored Symbols"
			::= { sleEfmOamEntry 52 }

		
--   1.3.6.1.4.1.6296.101.4.5.1.1.53
-- 1.3.6.1.4.1.6296.101.4.5.1.1.53
		-- 1.3.6.1.4.1.6296.101.4.5.1.1.53
		sleOamLmRemSymbolPeriodThresh OBJECT-TYPE
			SYNTAX Counter64
			MAX-ACCESS read-only
			STATUS current
			DESCRIPTION
				"This value is the Threshold size of Errored Symbols"
			::= { sleEfmOamEntry 53 }

		
--   1.3.6.1.4.1.6296.101.4.5.1.1.54
-- 1.3.6.1.4.1.6296.101.4.5.1.1.54
		-- 1.3.6.1.4.1.6296.101.4.5.1.1.54
		sleOamLmRemSymbolPeriodErrors OBJECT-TYPE
			SYNTAX Counter64
			MAX-ACCESS read-only
			STATUS current
			DESCRIPTION
				"This value is the Count of Errored Symbols"
			::= { sleEfmOamEntry 54 }

		
--   1.3.6.1.4.1.6296.101.4.5.1.1.55
-- 1.3.6.1.4.1.6296.101.4.5.1.1.55
		-- 1.3.6.1.4.1.6296.101.4.5.1.1.55
		sleOamLmRemSymbolPeriodErrorRunTotal OBJECT-TYPE
			SYNTAX Counter64
			MAX-ACCESS read-only
			STATUS current
			DESCRIPTION
				"This value is the Total Count of Errored Symbols"
			::= { sleEfmOamEntry 55 }

		
--   1.3.6.1.4.1.6296.101.4.5.1.1.56
-- 1.3.6.1.4.1.6296.101.4.5.1.1.56
		-- 1.3.6.1.4.1.6296.101.4.5.1.1.56
		sleOamLmRemSymbolPeriodEventRunTotal OBJECT-TYPE
			SYNTAX Counter64
			MAX-ACCESS read-only
			STATUS current
			DESCRIPTION
				"This value is the Total Count of Errored Symbols Event"
			::= { sleEfmOamEntry 56 }

		
--   1.3.6.1.4.1.6296.101.4.5.2
-- 1.3.6.1.4.1.6296.101.4.5.2
		-- 1.3.6.1.4.1.6296.101.4.5.2
		sleEfmOamControl OBJECT IDENTIFIER ::= { sleEfmOam 2 }

		
--   1.3.6.1.4.1.6296.101.4.5.2.1
-- 1.3.6.1.4.1.6296.101.4.5.2.1
		-- 1.3.6.1.4.1.6296.101.4.5.2.1
		sleOamControlRequest OBJECT-TYPE
			SYNTAX INTEGER
				{
				setEfmOamPortProfile(1),
				setEfmOamPortRemLoopback(2),
				setEfmOamPortLinkMonitor(3)
				}
			MAX-ACCESS read-write
			STATUS current
			DESCRIPTION
				"The MIB object for the user command.."
			::= { sleEfmOamControl 1 }

		
--   1.3.6.1.4.1.6296.101.4.5.2.2
-- 1.3.6.1.4.1.6296.101.4.5.2.2
		-- 1.3.6.1.4.1.6296.101.4.5.2.2
		sleOamControlStatus OBJECT-TYPE
			SYNTAX SleControlStatusType
			MAX-ACCESS read-only
			STATUS current
			DESCRIPTION
				"Describes the status of a user command group, 
				used for block commands while a command execution in process."
			::= { sleEfmOamControl 2 }

		
--   1.3.6.1.4.1.6296.101.4.5.2.3
-- 1.3.6.1.4.1.6296.101.4.5.2.3
		-- 1.3.6.1.4.1.6296.101.4.5.2.3
		sleOamControlTimer OBJECT-TYPE
			SYNTAX Gauge32
			MAX-ACCESS read-write
			STATUS current
			DESCRIPTION
				"Maximum command duration time in case of long running"
			::= { sleEfmOamControl 3 }

		
--   1.3.6.1.4.1.6296.101.4.5.2.4
-- 1.3.6.1.4.1.6296.101.4.5.2.4
		-- 1.3.6.1.4.1.6296.101.4.5.2.4
		sleOamControlTimeStamp OBJECT-TYPE
			SYNTAX TimeStamp
			MAX-ACCESS read-only
			STATUS current
			DESCRIPTION
				"Time stamp attribute set at end of command."
			::= { sleEfmOamControl 4 }

		
--   1.3.6.1.4.1.6296.101.4.5.2.5
-- 1.3.6.1.4.1.6296.101.4.5.2.5
		-- 1.3.6.1.4.1.6296.101.4.5.2.5
		sleOamControlReqResult OBJECT-TYPE
			SYNTAX SleControlRequestResultType
			MAX-ACCESS read-only
			STATUS current
			DESCRIPTION
				"Command result attribute"
			::= { sleEfmOamControl 5 }

		
--   1.3.6.1.4.1.6296.101.4.5.2.6
-- 1.3.6.1.4.1.6296.101.4.5.2.6
		-- 1.3.6.1.4.1.6296.101.4.5.2.6
		sleOamControlIndex OBJECT-TYPE
			SYNTAX Integer32
			MAX-ACCESS read-write
			STATUS current
			DESCRIPTION
				"Description."
			::= { sleEfmOamControl 6 }

		
--   1.3.6.1.4.1.6296.101.4.5.2.7
-- 1.3.6.1.4.1.6296.101.4.5.2.7
		-- 1.3.6.1.4.1.6296.101.4.5.2.7
		sleOamControlPortAdminState OBJECT-TYPE
			SYNTAX INTEGER
				{
				disable(0),
				enable(1)
				}
			MAX-ACCESS read-write
			STATUS current
			DESCRIPTION
				"This object is used to provision the default 
				administrative OAM mode for this interface."
			::= { sleEfmOamControl 7 }

		
--   1.3.6.1.4.1.6296.101.4.5.2.8
-- 1.3.6.1.4.1.6296.101.4.5.2.8
		-- 1.3.6.1.4.1.6296.101.4.5.2.8
		sleOamControlPortMode OBJECT-TYPE
			SYNTAX INTEGER
				{
				passive(0),
				active(1)
				}
			MAX-ACCESS read-write
			STATUS current
			DESCRIPTION
				"This object configures the mode of OAM 
				operation for this Ethernet like interface."
			::= { sleEfmOamControl 8 }

		
--   1.3.6.1.4.1.6296.101.4.5.2.9
-- 1.3.6.1.4.1.6296.101.4.5.2.9
		-- 1.3.6.1.4.1.6296.101.4.5.2.9
		sleOamControlPortUnidirectionMode OBJECT-TYPE
			SYNTAX INTEGER
				{
				notAvaliable(-2),
				disable(0),
				enable(1)
				}
			MAX-ACCESS read-write
			STATUS current
			DESCRIPTION
				"Description."
			::= { sleEfmOamControl 9 }

		
--   1.3.6.1.4.1.6296.101.4.5.2.10
-- 1.3.6.1.4.1.6296.101.4.5.2.10
		-- 1.3.6.1.4.1.6296.101.4.5.2.10
		sleOamControlPortRemLoopback OBJECT-TYPE
			SYNTAX INTEGER
				{
				disable(0),
				enable(1),
				start(2)
				}
			MAX-ACCESS read-write
			STATUS current
			DESCRIPTION
				"The value indicates an optional data link 
				layer frame-level loopback mode, which is 
				controlled remotely."
			::= { sleEfmOamControl 10 }

		
--   1.3.6.1.4.1.6296.101.4.5.2.11
-- 1.3.6.1.4.1.6296.101.4.5.2.11
		-- 1.3.6.1.4.1.6296.101.4.5.2.11
		sleOamControlRemLoopbackPkCnt OBJECT-TYPE
			SYNTAX Integer32 (1..100)
			MAX-ACCESS read-write
			STATUS current
			DESCRIPTION
				"The number of test Packet"
			::= { sleEfmOamControl 11 }

		
--   1.3.6.1.4.1.6296.101.4.5.2.12
-- 1.3.6.1.4.1.6296.101.4.5.2.12
		-- 1.3.6.1.4.1.6296.101.4.5.2.12
		sleOamControlLm OBJECT-TYPE
			SYNTAX INTEGER
				{
				disable(0),
				enable(1)
				}
			MAX-ACCESS read-write
			STATUS current
			DESCRIPTION
				"This value indicates whether Link-Monitor supports or not for port index."
			::= { sleEfmOamControl 12 }

		
--   1.3.6.1.4.1.6296.101.4.5.2.13
-- 1.3.6.1.4.1.6296.101.4.5.2.13
		-- 1.3.6.1.4.1.6296.101.4.5.2.13
		sleOamControlLmAction OBJECT-TYPE
			SYNTAX INTEGER
				{
				syslog(0),
				snmpTrap(1)
				}
			MAX-ACCESS read-write
			STATUS current
			DESCRIPTION
				"The Action of Link-Monitor for port index."
			::= { sleEfmOamControl 13 }

		
--   1.3.6.1.4.1.6296.101.4.5.2.14
-- 1.3.6.1.4.1.6296.101.4.5.2.14
		-- 1.3.6.1.4.1.6296.101.4.5.2.14
		sleOamControlLmFrameWindow OBJECT-TYPE
			SYNTAX INTEGER (10..600)
			UNITS "seconds"
			MAX-ACCESS read-write
			STATUS current
			DESCRIPTION
				"This value is the Window size of Errored Frame.
				Default : 30 secs
				"
			::= { sleEfmOamControl 14 }

		
--   1.3.6.1.4.1.6296.101.4.5.2.15
-- 1.3.6.1.4.1.6296.101.4.5.2.15
		-- 1.3.6.1.4.1.6296.101.4.5.2.15
		sleOamControlLmFrameThresh OBJECT-TYPE
			SYNTAX INTEGER (0..65535)
			MAX-ACCESS read-write
			STATUS current
			DESCRIPTION
				"This value is the Threshold size of Errored Frame.
				Default: 1
				"
			::= { sleEfmOamControl 15 }

		
--   1.3.6.1.4.1.6296.101.4.5.2.16
-- 1.3.6.1.4.1.6296.101.4.5.2.16
		-- 1.3.6.1.4.1.6296.101.4.5.2.16
		sleOamControlLmFramePeriodWindow OBJECT-TYPE
			SYNTAX INTEGER (1000..200000000)
			MAX-ACCESS read-write
			STATUS current
			DESCRIPTION
				"This value is size of Errored Period Window.
				Default : 1000000 frames
				"
			::= { sleEfmOamControl 16 }

		
--   1.3.6.1.4.1.6296.101.4.5.2.17
-- 1.3.6.1.4.1.6296.101.4.5.2.17
		-- 1.3.6.1.4.1.6296.101.4.5.2.17
		sleOamControlLmFramePeriodThresh OBJECT-TYPE
			SYNTAX INTEGER (0..65535)
			MAX-ACCESS read-write
			STATUS current
			DESCRIPTION
				"This value is size of Errored Period Threshold.
				Default :  10
				"
			::= { sleEfmOamControl 17 }

		
--   1.3.6.1.4.1.6296.101.4.5.2.18
-- 1.3.6.1.4.1.6296.101.4.5.2.18
		-- 1.3.6.1.4.1.6296.101.4.5.2.18
		sleOamControlLmFrameSecondSummaryWindow OBJECT-TYPE
			SYNTAX INTEGER (10..900)
			UNITS "seconds"
			MAX-ACCESS read-write
			STATUS current
			DESCRIPTION
				"This value is the Window size of errored frame in a second
				Default : 60 secs
				"
			::= { sleEfmOamControl 18 }

		
--   1.3.6.1.4.1.6296.101.4.5.2.19
-- 1.3.6.1.4.1.6296.101.4.5.2.19
		-- 1.3.6.1.4.1.6296.101.4.5.2.19
		sleOamControlLmFrameSecondSummaryThresh OBJECT-TYPE
			SYNTAX INTEGER (0..900)
			MAX-ACCESS read-write
			STATUS current
			DESCRIPTION
				"This value is the Threshold size of errored frame in a second
				Default: 1
				"
			::= { sleEfmOamControl 19 }

		
--   1.3.6.1.4.1.6296.101.4.5.2.20
-- 1.3.6.1.4.1.6296.101.4.5.2.20
		-- 1.3.6.1.4.1.6296.101.4.5.2.20
		sleOamControlLmSymbolPeriodWindow OBJECT-TYPE
			SYNTAX INTEGER (1..1000000)
			MAX-ACCESS read-write
			STATUS current
			DESCRIPTION
				"This value is the window size of symbol errors.
				Default: 625 millions, Unit: 1 million
				"
			::= { sleEfmOamControl 20 }

		
--   1.3.6.1.4.1.6296.101.4.5.2.21
-- 1.3.6.1.4.1.6296.101.4.5.2.21
		-- 1.3.6.1.4.1.6296.101.4.5.2.21
		sleOamControlLmSymbolPeriodThresh OBJECT-TYPE
			SYNTAX INTEGER (0..65535)
			MAX-ACCESS read-write
			STATUS current
			DESCRIPTION
				"This value is the Threshold size of symbol errors
				Default : 1
				
				"
			::= { sleEfmOamControl 21 }

		
--   1.3.6.1.4.1.6296.101.4.5.3
-- 1.3.6.1.4.1.6296.101.4.5.3
		-- 1.3.6.1.4.1.6296.101.4.5.3
		sleEfmOamNotification OBJECT IDENTIFIER ::= { sleEfmOam 3 }

		
--   1.3.6.1.4.1.6296.101.4.5.3.1
-- 1.3.6.1.4.1.6296.101.4.5.3.1
		-- 1.3.6.1.4.1.6296.101.4.5.3.1
		sleEfmOamPortProfileChanged NOTIFICATION-TYPE
			OBJECTS { sleOamControlReqResult, sleOamControlTimeStamp, sleOamControlRequest, sleOamAdminState, sleOamMode, 
				sleOamUnidirectionMode }
			STATUS current
			DESCRIPTION 
				" "
			::= { sleEfmOamNotification 1 }

		
--   1.3.6.1.4.1.6296.101.4.5.3.2
-- 1.3.6.1.4.1.6296.101.4.5.3.2
		-- 1.3.6.1.4.1.6296.101.4.5.3.2
		sleEfmOamPortRemLoopback NOTIFICATION-TYPE
			OBJECTS { sleOamControlRequest, sleOamControlReqResult, sleOamControlTimeStamp, sleOamRemLoopback, sleOamControlRemLoopbackPkCnt
				 }
			STATUS current
			DESCRIPTION 
				"Description."
			::= { sleEfmOamNotification 2 }

		
--   1.3.6.1.4.1.6296.101.4.5.3.3
-- 1.3.6.1.4.1.6296.101.4.5.3.3
		-- 1.3.6.1.4.1.6296.101.4.5.3.3
		sleEfmOamPortLinkMonitorChanged NOTIFICATION-TYPE
			OBJECTS { sleOamControlRequest, sleOamControlReqResult, sleOamControlTimeStamp, sleOamLmFramePeriodThresh, sleOamLmFramePeriodWindow, 
				sleOamLmFrameThresh, sleOamLmFrameWindow, sleOamLmAction, sleOamLmSymbolPeriodThresh, sleOamLmSymbolPeriodWindow, 
				sleOamLmFrameSecondSummaryThresh, sleOamLmFrameSecondSummaryWindow, sleOamLm, sleOamPortIndex }
			STATUS current
			DESCRIPTION 
				"Description."
			::= { sleEfmOamNotification 3 }

		
--   1.3.6.1.4.1.6296.101.4.6
-- 1.3.6.1.4.1.6296.101.4.6
		-- 1.3.6.1.4.1.6296.101.4.6
		sleAdvaSystem OBJECT IDENTIFIER ::= { sleFaultMgmt 6 }

		
--   1.3.6.1.4.1.6296.101.4.6.1
-- 1.3.6.1.4.1.6296.101.4.6.1
		-- 1.3.6.1.4.1.6296.101.4.6.1
		sleAdvaSystemTable OBJECT-TYPE
			SYNTAX SEQUENCE OF SleAdvaSystemEntry
			MAX-ACCESS not-accessible
			STATUS current
			DESCRIPTION
				"Description."
			::= { sleAdvaSystem 1 }

		
--   1.3.6.1.4.1.6296.101.4.6.1.1
-- 1.3.6.1.4.1.6296.101.4.6.1.1
		-- 1.3.6.1.4.1.6296.101.4.6.1.1
		sleAdvaSystemEntry OBJECT-TYPE
			SYNTAX SleAdvaSystemEntry
			MAX-ACCESS not-accessible
			STATUS current
			DESCRIPTION
				"Description."
			INDEX { sleOamPortIndex }
			::= { sleAdvaSystemTable 1 }

		
		SleAdvaSystemEntry ::=
			SEQUENCE { 
				sleAdvaFSPOperationMode
					INTEGER,
				sleAdvaActiveNetworkInterface
					INTEGER,
				sleAdvaForceNetworkInterface
					INTEGER,
				sleAdvaReportingInterval
					INTEGER,
				sleAdvaNEMIFitted
					INTEGER,
				sleAdvaForceReset
					INTEGER,
				sleAdvaManagerAddress
					IpAddress,
				sleAdvaMinRailVoltageThreshold
					INTEGER,
				sleAdvaMaxRailVoltageThreshold
					INTEGER,
				sleAdvaTemperatureThreshold
					INTEGER,
				sleAdvaPartNumber
					OCTET STRING,
				sleAdvaSerialNumber
					OCTET STRING,
				sleAdvaFirmwareVersion
					OCTET STRING,
				sleAdvaFPGAVersion
					OCTET STRING,
				sleAdvaHardwareRevision
					OCTET STRING,
				sleAdvaCLEICode
					OCTET STRING,
				sleAdvaTemperature
					INTEGER,
				sleAdvaRailVoltage
					INTEGER,
				sleAdvaPSUStates
					INTEGER,
				sleAdvaPSUType
					INTEGER,
				sleAdvaFansFitted
					INTEGER,
				sleAdvaFanState
					INTEGER,
				sleAdvaTransmitMode
					INTEGER
			 }

--   1.3.6.1.4.1.6296.101.4.6.1.1.1
-- 1.3.6.1.4.1.6296.101.4.6.1.1.1
		-- 1.3.6.1.4.1.6296.101.4.6.1.1.1
		sleAdvaFSPOperationMode OBJECT-TYPE
			SYNTAX INTEGER
				{
				master(1),
				slave(2)
				}
			MAX-ACCESS read-only
			STATUS current
			DESCRIPTION
				"Mode in which the FSP 150 is to operate"
			::= { sleAdvaSystemEntry 1 }

		
--   1.3.6.1.4.1.6296.101.4.6.1.1.2
-- 1.3.6.1.4.1.6296.101.4.6.1.1.2
		-- 1.3.6.1.4.1.6296.101.4.6.1.1.2
		sleAdvaActiveNetworkInterface OBJECT-TYPE
			SYNTAX INTEGER
				{
				both(0),
				portA(1),
				portB(2)
				}
			MAX-ACCESS read-only
			STATUS current
			DESCRIPTION
				"Which of the network interfaces is the active one"
			::= { sleAdvaSystemEntry 2 }

		
--   1.3.6.1.4.1.6296.101.4.6.1.1.3
-- 1.3.6.1.4.1.6296.101.4.6.1.1.3
		-- 1.3.6.1.4.1.6296.101.4.6.1.1.3
		sleAdvaForceNetworkInterface OBJECT-TYPE
			SYNTAX INTEGER
				{
				unforced(0),
				forceA(1),
				forceB(2)
				}
			MAX-ACCESS read-only
			STATUS current
			DESCRIPTION
				"Description."
			::= { sleAdvaSystemEntry 3 }

		
--   1.3.6.1.4.1.6296.101.4.6.1.1.4
-- 1.3.6.1.4.1.6296.101.4.6.1.1.4
		-- 1.3.6.1.4.1.6296.101.4.6.1.1.4
		sleAdvaReportingInterval OBJECT-TYPE
			SYNTAX INTEGER (0..255)
			MAX-ACCESS read-only
			STATUS current
			DESCRIPTION
				"Repeat period in 1/10th seconds for Organisation Specific Alarm 
				Status OAMPDU.  If non-zero and there are any alarms active, 
				repeat the last-sent AS after this interval from when it was 
				last sent.If zero then only send on changes.As a special action, 
				writing zero to this will cause the Alarm Status OAMPDU to be sent (poll)."
			::= { sleAdvaSystemEntry 4 }

		
--   1.3.6.1.4.1.6296.101.4.6.1.1.5
-- 1.3.6.1.4.1.6296.101.4.6.1.1.5
		-- 1.3.6.1.4.1.6296.101.4.6.1.1.5
		sleAdvaNEMIFitted OBJECT-TYPE
			SYNTAX INTEGER (0..1)
			MAX-ACCESS read-only
			STATUS current
			DESCRIPTION
				"Indicator as to whether a NEMI is fitted."
			::= { sleAdvaSystemEntry 5 }

		
--   1.3.6.1.4.1.6296.101.4.6.1.1.6
-- 1.3.6.1.4.1.6296.101.4.6.1.1.6
		-- 1.3.6.1.4.1.6296.101.4.6.1.1.6
		sleAdvaForceReset OBJECT-TYPE
			SYNTAX INTEGER (0..1)
			MAX-ACCESS read-only
			STATUS current
			DESCRIPTION
				"Writing True (1) causes the system to be reset."
			::= { sleAdvaSystemEntry 6 }

		
--   1.3.6.1.4.1.6296.101.4.6.1.1.7
-- 1.3.6.1.4.1.6296.101.4.6.1.1.7
		-- 1.3.6.1.4.1.6296.101.4.6.1.1.7
		sleAdvaManagerAddress OBJECT-TYPE
			SYNTAX IpAddress
			MAX-ACCESS read-only
			STATUS current
			DESCRIPTION
				"The IP address of the Management station monitoring this sytem."
			::= { sleAdvaSystemEntry 7 }

		
--   1.3.6.1.4.1.6296.101.4.6.1.1.8
-- 1.3.6.1.4.1.6296.101.4.6.1.1.8
		-- 1.3.6.1.4.1.6296.101.4.6.1.1.8
		sleAdvaMinRailVoltageThreshold OBJECT-TYPE
			SYNTAX INTEGER (0..65535)
			MAX-ACCESS read-only
			STATUS current
			DESCRIPTION
				"Threshold in mV below which the Voltage low alarm will be 
				activated. (Alarm Configuration)"
			::= { sleAdvaSystemEntry 8 }

		
--   1.3.6.1.4.1.6296.101.4.6.1.1.9
-- 1.3.6.1.4.1.6296.101.4.6.1.1.9
		-- 1.3.6.1.4.1.6296.101.4.6.1.1.9
		sleAdvaMaxRailVoltageThreshold OBJECT-TYPE
			SYNTAX INTEGER (0..65535)
			MAX-ACCESS read-only
			STATUS current
			DESCRIPTION
				"Threshold in mV above which the Voltage high alarm will be activated. 
				(Alarm Configuration)"
			::= { sleAdvaSystemEntry 9 }

		
--   1.3.6.1.4.1.6296.101.4.6.1.1.10
-- 1.3.6.1.4.1.6296.101.4.6.1.1.10
		-- 1.3.6.1.4.1.6296.101.4.6.1.1.10
		sleAdvaTemperatureThreshold OBJECT-TYPE
			SYNTAX INTEGER (0..255)
			MAX-ACCESS read-only
			STATUS current
			DESCRIPTION
				"Threshold in C above which the Temperature alarm will be activated. (Alarm Configuration)"
			::= { sleAdvaSystemEntry 10 }

		
--   1.3.6.1.4.1.6296.101.4.6.1.1.11
-- 1.3.6.1.4.1.6296.101.4.6.1.1.11
		-- 1.3.6.1.4.1.6296.101.4.6.1.1.11
		sleAdvaPartNumber OBJECT-TYPE
			SYNTAX OCTET STRING (SIZE (0..32))
			MAX-ACCESS read-only
			STATUS current
			DESCRIPTION
				"Part number for the chassis. (Chassis)"
			::= { sleAdvaSystemEntry 11 }

		
--   1.3.6.1.4.1.6296.101.4.6.1.1.12
-- 1.3.6.1.4.1.6296.101.4.6.1.1.12
		-- 1.3.6.1.4.1.6296.101.4.6.1.1.12
		sleAdvaSerialNumber OBJECT-TYPE
			SYNTAX OCTET STRING (SIZE (0..32))
			MAX-ACCESS read-only
			STATUS current
			DESCRIPTION
				"Serial number for the chassis. (Chassis)"
			::= { sleAdvaSystemEntry 12 }

		
--   1.3.6.1.4.1.6296.101.4.6.1.1.13
-- 1.3.6.1.4.1.6296.101.4.6.1.1.13
		-- 1.3.6.1.4.1.6296.101.4.6.1.1.13
		sleAdvaFirmwareVersion OBJECT-TYPE
			SYNTAX OCTET STRING (SIZE (0..32))
			MAX-ACCESS read-only
			STATUS current
			DESCRIPTION
				"Firmware version for the chassis. (Chassis)
				(0-length string if unknown)."
			::= { sleAdvaSystemEntry 13 }

		
--   1.3.6.1.4.1.6296.101.4.6.1.1.14
-- 1.3.6.1.4.1.6296.101.4.6.1.1.14
		-- 1.3.6.1.4.1.6296.101.4.6.1.1.14
		sleAdvaFPGAVersion OBJECT-TYPE
			SYNTAX OCTET STRING (SIZE (0..32))
			MAX-ACCESS read-only
			STATUS current
			DESCRIPTION
				"FPGA version for the chassis. (Chassis)
				(0-length string if unknown)."
			::= { sleAdvaSystemEntry 14 }

		
--   1.3.6.1.4.1.6296.101.4.6.1.1.15
-- 1.3.6.1.4.1.6296.101.4.6.1.1.15
		-- 1.3.6.1.4.1.6296.101.4.6.1.1.15
		sleAdvaHardwareRevision OBJECT-TYPE
			SYNTAX OCTET STRING (SIZE (0..4))
			MAX-ACCESS read-only
			STATUS current
			DESCRIPTION
				"Hardware revision for the chassis. 
				(Chassis)(0-length string if unknown)."
			::= { sleAdvaSystemEntry 15 }

		
--   1.3.6.1.4.1.6296.101.4.6.1.1.16
-- 1.3.6.1.4.1.6296.101.4.6.1.1.16
		-- 1.3.6.1.4.1.6296.101.4.6.1.1.16
		sleAdvaCLEICode OBJECT-TYPE
			SYNTAX OCTET STRING (SIZE (0..14))
			MAX-ACCESS read-only
			STATUS current
			DESCRIPTION
				"CLEI for the chassis. (Chassis)"
			::= { sleAdvaSystemEntry 16 }

		
--   1.3.6.1.4.1.6296.101.4.6.1.1.17
-- 1.3.6.1.4.1.6296.101.4.6.1.1.17
		-- 1.3.6.1.4.1.6296.101.4.6.1.1.17
		sleAdvaTemperature OBJECT-TYPE
			SYNTAX INTEGER (0..255)
			MAX-ACCESS read-only
			STATUS current
			DESCRIPTION
				"Current chassis temperature in degrees C. (Chassis)"
			::= { sleAdvaSystemEntry 17 }

		
--   1.3.6.1.4.1.6296.101.4.6.1.1.18
-- 1.3.6.1.4.1.6296.101.4.6.1.1.18
		-- 1.3.6.1.4.1.6296.101.4.6.1.1.18
		sleAdvaRailVoltage OBJECT-TYPE
			SYNTAX INTEGER (0..65535)
			MAX-ACCESS read-only
			STATUS current
			DESCRIPTION
				"Current DC power rail voltage (mV). (Chassis)"
			::= { sleAdvaSystemEntry 18 }

		
--   1.3.6.1.4.1.6296.101.4.6.1.1.19
-- 1.3.6.1.4.1.6296.101.4.6.1.1.19
		-- 1.3.6.1.4.1.6296.101.4.6.1.1.19
		sleAdvaPSUStates OBJECT-TYPE
			SYNTAX INTEGER (0..255)
			MAX-ACCESS read-only
			STATUS current
			DESCRIPTION
				"Bit-mask representing the state of the PSUs.  
				Starting at the LSB, each failed PSU is indicated 
				by a bit set to '1'. (Chassis)"
			::= { sleAdvaSystemEntry 19 }

		
--   1.3.6.1.4.1.6296.101.4.6.1.1.20
-- 1.3.6.1.4.1.6296.101.4.6.1.1.20
		-- 1.3.6.1.4.1.6296.101.4.6.1.1.20
		sleAdvaPSUType OBJECT-TYPE
			SYNTAX INTEGER
				{
				ac(1),
				dc(2)
				}
			MAX-ACCESS read-only
			STATUS current
			DESCRIPTION
				"Type of PSUs fitted. (Chassis)"
			::= { sleAdvaSystemEntry 20 }

		
--   1.3.6.1.4.1.6296.101.4.6.1.1.21
-- 1.3.6.1.4.1.6296.101.4.6.1.1.21
		-- 1.3.6.1.4.1.6296.101.4.6.1.1.21
		sleAdvaFansFitted OBJECT-TYPE
			SYNTAX INTEGER (0..255)
			MAX-ACCESS read-only
			STATUS current
			DESCRIPTION
				"Bit-mask representing which fans are fitted.  
				Starting at the LSB, each bit set to '1' indicates a fitted fan.  
				Knowledge of which fans ought to be fitted is assumed. (Chassis)"
			::= { sleAdvaSystemEntry 21 }

		
--   1.3.6.1.4.1.6296.101.4.6.1.1.22
-- 1.3.6.1.4.1.6296.101.4.6.1.1.22
		-- 1.3.6.1.4.1.6296.101.4.6.1.1.22
		sleAdvaFanState OBJECT-TYPE
			SYNTAX INTEGER (0..255)
			MAX-ACCESS read-only
			STATUS current
			DESCRIPTION
				"Bit-mask representing the state of the fan.  
				Starting at the LSB, each failed fan is indicated by a 
				bit set to '1'. (Chassis)"
			::= { sleAdvaSystemEntry 22 }

		
--   1.3.6.1.4.1.6296.101.4.6.1.1.23
-- 1.3.6.1.4.1.6296.101.4.6.1.1.23
		-- 1.3.6.1.4.1.6296.101.4.6.1.1.23
		sleAdvaTransmitMode OBJECT-TYPE
			SYNTAX INTEGER
				{
				halfDuplex(0),
				fullDuplex(1)
				}
			MAX-ACCESS read-only
			STATUS current
			DESCRIPTION
				"Electrical Interface for remote instance 4"
			::= { sleAdvaSystemEntry 23 }

		
--   1.3.6.1.4.1.6296.101.4.6.2
-- 1.3.6.1.4.1.6296.101.4.6.2
		-- 1.3.6.1.4.1.6296.101.4.6.2
		sleAdvaSystemControl OBJECT IDENTIFIER ::= { sleAdvaSystem 2 }

		
--   1.3.6.1.4.1.6296.101.4.6.2.1
-- 1.3.6.1.4.1.6296.101.4.6.2.1
		-- 1.3.6.1.4.1.6296.101.4.6.2.1
		sleAdvaSystemControlRequest OBJECT-TYPE
			SYNTAX INTEGER
				{
				setAdvaSystemProfile(1),
				setAdvaAlarmProfile(2),
				setAdvaElectricalInterface(3)
				}
			MAX-ACCESS read-write
			STATUS current
			DESCRIPTION
				"The MIB object for the user command.."
			::= { sleAdvaSystemControl 1 }

		
--   1.3.6.1.4.1.6296.101.4.6.2.2
-- 1.3.6.1.4.1.6296.101.4.6.2.2
		-- 1.3.6.1.4.1.6296.101.4.6.2.2
		sleAdvaSystemControlStatus OBJECT-TYPE
			SYNTAX SleControlStatusType
			MAX-ACCESS read-only
			STATUS current
			DESCRIPTION
				"Describes the status of a user command group, 
				used for block commands while a command execution in process."
			::= { sleAdvaSystemControl 2 }

		
--   1.3.6.1.4.1.6296.101.4.6.2.3
-- 1.3.6.1.4.1.6296.101.4.6.2.3
		-- 1.3.6.1.4.1.6296.101.4.6.2.3
		sleAdvaSystemControlTimer OBJECT-TYPE
			SYNTAX Gauge32
			MAX-ACCESS read-write
			STATUS current
			DESCRIPTION
				"Description."
			::= { sleAdvaSystemControl 3 }

		
--   1.3.6.1.4.1.6296.101.4.6.2.4
-- 1.3.6.1.4.1.6296.101.4.6.2.4
		-- 1.3.6.1.4.1.6296.101.4.6.2.4
		sleAdvaSystemControlTimeStamp OBJECT-TYPE
			SYNTAX TimeTicks
			MAX-ACCESS read-write
			STATUS current
			DESCRIPTION
				"Description."
			::= { sleAdvaSystemControl 4 }

		
--   1.3.6.1.4.1.6296.101.4.6.2.5
-- 1.3.6.1.4.1.6296.101.4.6.2.5
		-- 1.3.6.1.4.1.6296.101.4.6.2.5
		sleAdvaSystemControlReqResult OBJECT-TYPE
			SYNTAX SleControlRequestResultType
			MAX-ACCESS read-write
			STATUS current
			DESCRIPTION
				"Description."
			::= { sleAdvaSystemControl 5 }

		
--   1.3.6.1.4.1.6296.101.4.6.2.6
-- 1.3.6.1.4.1.6296.101.4.6.2.6
		-- 1.3.6.1.4.1.6296.101.4.6.2.6
		sleAdvaSystemControlPortIndex OBJECT-TYPE
			SYNTAX INTEGER (1..255)
			MAX-ACCESS read-write
			STATUS current
			DESCRIPTION
				"Description."
			::= { sleAdvaSystemControl 6 }

		
--   1.3.6.1.4.1.6296.101.4.6.2.7
-- 1.3.6.1.4.1.6296.101.4.6.2.7
		-- 1.3.6.1.4.1.6296.101.4.6.2.7
		sleAdvaSystemControlFSPOperationMode OBJECT-TYPE
			SYNTAX INTEGER
				{
				master(1),
				save(2)
				}
			MAX-ACCESS read-write
			STATUS current
			DESCRIPTION
				"Description."
			::= { sleAdvaSystemControl 7 }

		
--   1.3.6.1.4.1.6296.101.4.6.2.8
-- 1.3.6.1.4.1.6296.101.4.6.2.8
		-- 1.3.6.1.4.1.6296.101.4.6.2.8
		sleAdvaSystemControlForceNetworkInterface OBJECT-TYPE
			SYNTAX INTEGER
				{
				unforced(0),
				forceA(1),
				forceB(2)
				}
			MAX-ACCESS read-write
			STATUS current
			DESCRIPTION
				"Description."
			::= { sleAdvaSystemControl 8 }

		
--   1.3.6.1.4.1.6296.101.4.6.2.9
-- 1.3.6.1.4.1.6296.101.4.6.2.9
		-- 1.3.6.1.4.1.6296.101.4.6.2.9
		sleAdvaSystemControlReportingInterval OBJECT-TYPE
			SYNTAX INTEGER (0..255)
			MAX-ACCESS read-write
			STATUS current
			DESCRIPTION
				"Description."
			::= { sleAdvaSystemControl 9 }

		
--   1.3.6.1.4.1.6296.101.4.6.2.10
-- 1.3.6.1.4.1.6296.101.4.6.2.10
		-- 1.3.6.1.4.1.6296.101.4.6.2.10
		sleAdvaSystemControlForceReset OBJECT-TYPE
			SYNTAX INTEGER (0..1)
			MAX-ACCESS read-write
			STATUS current
			DESCRIPTION
				"Description."
			::= { sleAdvaSystemControl 10 }

		
--   1.3.6.1.4.1.6296.101.4.6.2.11
-- 1.3.6.1.4.1.6296.101.4.6.2.11
		-- 1.3.6.1.4.1.6296.101.4.6.2.11
		sleAdvaSystemControlMinRailVoltageThreshold OBJECT-TYPE
			SYNTAX INTEGER (0..65535)
			MAX-ACCESS read-write
			STATUS current
			DESCRIPTION
				"Description."
			::= { sleAdvaSystemControl 11 }

		
--   1.3.6.1.4.1.6296.101.4.6.2.12
-- 1.3.6.1.4.1.6296.101.4.6.2.12
		-- 1.3.6.1.4.1.6296.101.4.6.2.12
		sleAdvaSystemControlMaxRailVoltageThreshold OBJECT-TYPE
			SYNTAX INTEGER (0..65535)
			MAX-ACCESS read-write
			STATUS current
			DESCRIPTION
				"Description."
			::= { sleAdvaSystemControl 12 }

		
--   1.3.6.1.4.1.6296.101.4.6.2.13
-- 1.3.6.1.4.1.6296.101.4.6.2.13
		-- 1.3.6.1.4.1.6296.101.4.6.2.13
		sleAdvaSystemControlTemperatureThreshold OBJECT-TYPE
			SYNTAX INTEGER (0..255)
			MAX-ACCESS read-write
			STATUS current
			DESCRIPTION
				"Description."
			::= { sleAdvaSystemControl 13 }

		
--   1.3.6.1.4.1.6296.101.4.6.2.14
-- 1.3.6.1.4.1.6296.101.4.6.2.14
		-- 1.3.6.1.4.1.6296.101.4.6.2.14
		sleAdvaSystemControlTransmitMode OBJECT-TYPE
			SYNTAX INTEGER
				{
				halfDuplex(0),
				fullDuplex(1)
				}
			MAX-ACCESS read-write
			STATUS current
			DESCRIPTION
				"Description."
			::= { sleAdvaSystemControl 14 }

		
--   1.3.6.1.4.1.6296.101.4.6.3
-- 1.3.6.1.4.1.6296.101.4.6.3
		-- 1.3.6.1.4.1.6296.101.4.6.3
		sleAdvaSystemNotification OBJECT IDENTIFIER ::= { sleAdvaSystem 3 }

		
--   1.3.6.1.4.1.6296.101.4.6.3.1
-- 1.3.6.1.4.1.6296.101.4.6.3.1
		-- 1.3.6.1.4.1.6296.101.4.6.3.1
		sleAdvaSystemProfileChanged NOTIFICATION-TYPE
			OBJECTS { sleAdvaSystemControlRequest, sleAdvaSystemControlReqResult, sleAdvaSystemControlTimeStamp, sleAdvaFSPOperationMode, sleAdvaForceNetworkInterface, 
				sleAdvaReportingInterval, sleAdvaForceReset }
			STATUS current
			DESCRIPTION 
				"Description."
			::= { sleAdvaSystemNotification 1 }

		
--   1.3.6.1.4.1.6296.101.4.6.3.2
-- 1.3.6.1.4.1.6296.101.4.6.3.2
		-- 1.3.6.1.4.1.6296.101.4.6.3.2
		sleAdvaAlarmProfileChanged NOTIFICATION-TYPE
			OBJECTS { sleAdvaSystemControlRequest, sleAdvaSystemControlReqResult, sleAdvaSystemControlTimeStamp, sleAdvaMinRailVoltageThreshold, sleAdvaMaxRailVoltageThreshold, 
				sleAdvaTemperatureThreshold }
			STATUS current
			DESCRIPTION 
				"Description."
			::= { sleAdvaSystemNotification 2 }

		
--   1.3.6.1.4.1.6296.101.4.6.3.3
-- 1.3.6.1.4.1.6296.101.4.6.3.3
		-- 1.3.6.1.4.1.6296.101.4.6.3.3
		sleAdvaElectricalInterfaceChanged NOTIFICATION-TYPE
			OBJECTS { sleAdvaSystemControlRequest, sleAdvaSystemControlReqResult, sleAdvaSystemControlTimeStamp, sleAdvaTransmitMode }
			STATUS current
			DESCRIPTION 
				"Description."
			::= { sleAdvaSystemNotification 3 }

		
--   1.3.6.1.4.1.6296.101.4.7
-- 1.3.6.1.4.1.6296.101.4.7
		-- 1.3.6.1.4.1.6296.101.4.7
		sleAdvaGeneral OBJECT IDENTIFIER ::= { sleFaultMgmt 7 }

		
--   1.3.6.1.4.1.6296.101.4.7.1
-- 1.3.6.1.4.1.6296.101.4.7.1
		-- 1.3.6.1.4.1.6296.101.4.7.1
		sleAdvaGeneralTable OBJECT-TYPE
			SYNTAX SEQUENCE OF SleAdvaGeneralEntry
			MAX-ACCESS not-accessible
			STATUS current
			DESCRIPTION
				"Description."
			::= { sleAdvaGeneral 1 }

		
--   1.3.6.1.4.1.6296.101.4.7.1.1
-- 1.3.6.1.4.1.6296.101.4.7.1.1
		-- 1.3.6.1.4.1.6296.101.4.7.1.1
		sleAdvaGeneralEntry OBJECT-TYPE
			SYNTAX SleAdvaGeneralEntry
			MAX-ACCESS not-accessible
			STATUS current
			DESCRIPTION
				"Description."
			INDEX { sleOamPortIndex, sleAdvaRemInstance }
			::= { sleAdvaGeneralTable 1 }

		
		SleAdvaGeneralEntry ::=
			SEQUENCE { 
				sleAdvaRemInstance
					INTEGER,
				sleAdvaOperationalStatus
					INTEGER,
				sleAdvaLineSpeed
					Integer32,
				sleAdvaMACAddress
					MacAddress,
				sleAdvaConnectorType
					INTEGER,
				sleAdvaAutonegiotation
					INTEGER,
				sleAdvaLinkLossForwarding
					INTEGER,
				sleAdvaAdminState
					INTEGER,
				sleAdvaRemoteInterfaceIndex
					INTEGER,
				sleAdvaUserDefinedString
					OCTET STRING,
				sleAdvaRemoteSignalling
					INTEGER,
				sleAdvaConfiguration
					INTEGER,
				sleAdvaLocalTechnologyAbility
					BITS,
				sleAdvaAdvertisedTechnologyAbility
					BITS,
				sleAdvaReceivedTechnologyAbility
					BITS,
				sleAdvaLocalSectorAbility
					BITS,
				sleAdvaAdvertisedSectorAbility
					BITS,
				sleAdvaReceivedSectorAbility
					BITS,
				sleAdvaDuplexCapabilities
					INTEGER,
				sleAdvaPHYType
					INTEGER,
				sleAdvaPHYTypeList
					BITS,
				sleAdvaMIIDetect
					INTEGER,
				sleAdvaPHYState
					INTEGER,
				sleAdvaGoodFramesTransmitted
					Integer32,
				sleAdvaSingleCollisionFrames
					Integer32,
				sleAdvaMultipleCollisionFrames
					Integer32,
				sleAdvaGoodFramesReceived
					Integer32,
				sleAdvaFCSErrors
					Integer32,
				sleAdvaAlignmentErrors
					Integer32,
				sleAdvaFramesTooLong
					Integer32,
				sleAdvaBytesTransmitted
					Integer32,
				sleAdvaBytesReceived
					Integer32,
				sleAdvaSymbolErrors
					Integer32
			 }

--   1.3.6.1.4.1.6296.101.4.7.1.1.1
-- 1.3.6.1.4.1.6296.101.4.7.1.1.1
		-- 1.3.6.1.4.1.6296.101.4.7.1.1.1
		sleAdvaRemInstance OBJECT-TYPE
			SYNTAX INTEGER (0..4)
			MAX-ACCESS read-only
			STATUS current
			DESCRIPTION
				"Description."
			::= { sleAdvaGeneralEntry 1 }

		
--   1.3.6.1.4.1.6296.101.4.7.1.1.2
-- 1.3.6.1.4.1.6296.101.4.7.1.1.2
		-- 1.3.6.1.4.1.6296.101.4.7.1.1.2
		sleAdvaOperationalStatus OBJECT-TYPE
			SYNTAX INTEGER
				{
				up(1),
				down(2),
				outofservice(3),
				unknown(4)
				}
			MAX-ACCESS read-only
			STATUS current
			DESCRIPTION
				"encoding TBD. (General)"
			::= { sleAdvaGeneralEntry 2 }

		
--   1.3.6.1.4.1.6296.101.4.7.1.1.3
-- 1.3.6.1.4.1.6296.101.4.7.1.1.3
		-- 1.3.6.1.4.1.6296.101.4.7.1.1.3
		sleAdvaLineSpeed OBJECT-TYPE
			SYNTAX Integer32
			MAX-ACCESS read-only
			STATUS current
			DESCRIPTION
				"Line speed in kbit/s. (General)"
			::= { sleAdvaGeneralEntry 3 }

		
--   1.3.6.1.4.1.6296.101.4.7.1.1.4
-- 1.3.6.1.4.1.6296.101.4.7.1.1.4
		-- 1.3.6.1.4.1.6296.101.4.7.1.1.4
		sleAdvaMACAddress OBJECT-TYPE
			SYNTAX MacAddress
			MAX-ACCESS read-only
			STATUS current
			DESCRIPTION
				"The Ethernet address of the interface. (General)"
			::= { sleAdvaGeneralEntry 4 }

		
--   1.3.6.1.4.1.6296.101.4.7.1.1.5
-- 1.3.6.1.4.1.6296.101.4.7.1.1.5
		-- 1.3.6.1.4.1.6296.101.4.7.1.1.5
		sleAdvaConnectorType OBJECT-TYPE
			SYNTAX INTEGER
				{
				sc(1),
				fc(2),
				mu(3),
				rj45(4),
				lu(5)
				}
			MAX-ACCESS read-only
			STATUS current
			DESCRIPTION
				"encoding TBD. (General)"
			::= { sleAdvaGeneralEntry 5 }

		
--   1.3.6.1.4.1.6296.101.4.7.1.1.6
-- 1.3.6.1.4.1.6296.101.4.7.1.1.6
		-- 1.3.6.1.4.1.6296.101.4.7.1.1.6
		sleAdvaAutonegiotation OBJECT-TYPE
			SYNTAX INTEGER
				{
				enable(1),
				disable(2)
				}
			MAX-ACCESS read-only
			STATUS current
			DESCRIPTION
				"Autonegiotation package - aAutoNegAdminState. (General)Enabled or disabled.	"
			::= { sleAdvaGeneralEntry 6 }

		
--   1.3.6.1.4.1.6296.101.4.7.1.1.7
-- 1.3.6.1.4.1.6296.101.4.7.1.1.7
		-- 1.3.6.1.4.1.6296.101.4.7.1.1.7
		sleAdvaLinkLossForwarding OBJECT-TYPE
			SYNTAX INTEGER (0..1)
			MAX-ACCESS read-only
			STATUS current
			DESCRIPTION
				"When enabled access interface is brought down, when both network interfaces are down. (General)"
			::= { sleAdvaGeneralEntry 7 }

		
--   1.3.6.1.4.1.6296.101.4.7.1.1.8
-- 1.3.6.1.4.1.6296.101.4.7.1.1.8
		-- 1.3.6.1.4.1.6296.101.4.7.1.1.8
		sleAdvaAdminState OBJECT-TYPE
			SYNTAX INTEGER
				{
				up(1),
				down(2)
				}
			MAX-ACCESS read-only
			STATUS current
			DESCRIPTION
				"Whether the interface is available. (General)"
			::= { sleAdvaGeneralEntry 8 }

		
--   1.3.6.1.4.1.6296.101.4.7.1.1.9
-- 1.3.6.1.4.1.6296.101.4.7.1.1.9
		-- 1.3.6.1.4.1.6296.101.4.7.1.1.9
		sleAdvaRemoteInterfaceIndex OBJECT-TYPE
			SYNTAX INTEGER (0..255)
			MAX-ACCESS read-only
			STATUS current
			DESCRIPTION
				"The index of the remote interface the interface is connected to. (General)"
			::= { sleAdvaGeneralEntry 9 }

		
--   1.3.6.1.4.1.6296.101.4.7.1.1.10
-- 1.3.6.1.4.1.6296.101.4.7.1.1.10
		-- 1.3.6.1.4.1.6296.101.4.7.1.1.10
		sleAdvaUserDefinedString OBJECT-TYPE
			SYNTAX OCTET STRING (SIZE (0..32))
			MAX-ACCESS read-only
			STATUS current
			DESCRIPTION
				"User definable string associated with interface. (General)"
			::= { sleAdvaGeneralEntry 10 }

		
--   1.3.6.1.4.1.6296.101.4.7.1.1.11
-- 1.3.6.1.4.1.6296.101.4.7.1.1.11
		-- 1.3.6.1.4.1.6296.101.4.7.1.1.11
		sleAdvaRemoteSignalling OBJECT-TYPE
			SYNTAX INTEGER
				{
				detected(1),
				notdetected(2)
				}
			MAX-ACCESS read-only
			STATUS current
			DESCRIPTION
				"Autonegiotation package - aAutoNegRemoteSignalling. (AutoNego)"
			::= { sleAdvaGeneralEntry 11 }

		
--   1.3.6.1.4.1.6296.101.4.7.1.1.12
-- 1.3.6.1.4.1.6296.101.4.7.1.1.12
		-- 1.3.6.1.4.1.6296.101.4.7.1.1.12
		sleAdvaConfiguration OBJECT-TYPE
			SYNTAX INTEGER
				{
				other(1),
				configuring(2),
				completed(3),
				disabled(4),
				parallelDetectFail(5)
				}
			MAX-ACCESS read-only
			STATUS current
			DESCRIPTION
				"Autonegiotation package - aAutoNegConfig. 
				(AutoNego)Indicates whether Auto-Negotiation 
				signaling is in progress or has completed."
			::= { sleAdvaGeneralEntry 12 }

		
--   1.3.6.1.4.1.6296.101.4.7.1.1.13
-- 1.3.6.1.4.1.6296.101.4.7.1.1.13
		-- 1.3.6.1.4.1.6296.101.4.7.1.1.13
		sleAdvaLocalTechnologyAbility OBJECT-TYPE
			SYNTAX BITS
				{
				global(0),
				unknown(1),
				base10T(2),
				base10TFD(3),
				base100T4(4),
				base100TX(5),
				base100TXFD(6),
				fdxpause(7),
				fdxapause(8),
				fdxspause(9),
				fdxbpause(10),
				base100T2(11),
				base100T2FD(12),
				base1000X(13),
				base1000XFD(14),
				base1000T(15),
				base1000TFD(16),
				remFault1(17),
				remFault2(18),
				isoEthernet(19)
				}
			MAX-ACCESS read-only
			STATUS current
			DESCRIPTION
				"Autonegiotation package - aAutoNegLocalTechnologyAbility. 
				(AutoNego)This indicates the technology ability of the local device"
			::= { sleAdvaGeneralEntry 13 }

		
--   1.3.6.1.4.1.6296.101.4.7.1.1.14
-- 1.3.6.1.4.1.6296.101.4.7.1.1.14
		-- 1.3.6.1.4.1.6296.101.4.7.1.1.14
		sleAdvaAdvertisedTechnologyAbility OBJECT-TYPE
			SYNTAX BITS
				{
				global(0),
				unknown(1),
				base10T(2),
				base10TFD(3),
				base100T4(4),
				base100TX(5),
				base100TXFD(6),
				fdxpause(7),
				fdxapause(8),
				fdxspause(9),
				fdxbpause(10),
				base100T2(11),
				base100T2FD(12),
				base1000X(13),
				base1000XFD(14),
				base1000T(15),
				base1000TFD(16),
				remFault1(17),
				remFault2(18),
				isoEthernet(19)
				}
			MAX-ACCESS read-only
			STATUS current
			DESCRIPTION
				"Autonegiotation package - aAutoNegAdvertisedTechnologyAbility. 
				(AutoNego)The advertised technology ability of the local device."
			::= { sleAdvaGeneralEntry 14 }

		
--   1.3.6.1.4.1.6296.101.4.7.1.1.15
-- 1.3.6.1.4.1.6296.101.4.7.1.1.15
		-- 1.3.6.1.4.1.6296.101.4.7.1.1.15
		sleAdvaReceivedTechnologyAbility OBJECT-TYPE
			SYNTAX BITS
				{
				global(0),
				unknown(1),
				base10T(2),
				base10TFD(3),
				base100T4(4),
				base100TX(5),
				base100TXFD(6),
				fdxpause(7),
				fdxapause(8),
				fdxspause(9),
				fdxbpause(10),
				base100T2(11),
				base100T2FD(12),
				base1000X(13),
				base1000XFD(14),
				base1000T(15),
				base1000TFD(16),
				remFault1(17),
				remFault2(18),
				isoEthernet(19)
				}
			MAX-ACCESS read-only
			STATUS current
			DESCRIPTION
				"Autonegiotation package - aAutoNegReceivedTechnologyAbility. 
				(AutoNego)Indicates the advertised technology ability of the 
				remote hardware."
			::= { sleAdvaGeneralEntry 15 }

		
--   1.3.6.1.4.1.6296.101.4.7.1.1.16
-- 1.3.6.1.4.1.6296.101.4.7.1.1.16
		-- 1.3.6.1.4.1.6296.101.4.7.1.1.16
		sleAdvaLocalSectorAbility OBJECT-TYPE
			SYNTAX BITS
				{
				other(0),
				ethernet(1),
				isoethernet(2)
				}
			MAX-ACCESS read-only
			STATUS current
			DESCRIPTION
				"Autonegiotation package - aAutoNegLocalSectorAbility. (AutoNego)"
			::= { sleAdvaGeneralEntry 16 }

		
--   1.3.6.1.4.1.6296.101.4.7.1.1.17
-- 1.3.6.1.4.1.6296.101.4.7.1.1.17
		-- 1.3.6.1.4.1.6296.101.4.7.1.1.17
		sleAdvaAdvertisedSectorAbility OBJECT-TYPE
			SYNTAX BITS
				{
				other(0),
				ethernet(1),
				isoethernet(2)
				}
			MAX-ACCESS read-only
			STATUS current
			DESCRIPTION
				"Autonegiotation package - aAutoNegLocalSectorAbility. (AutoNego)"
			::= { sleAdvaGeneralEntry 17 }

		
--   1.3.6.1.4.1.6296.101.4.7.1.1.18
-- 1.3.6.1.4.1.6296.101.4.7.1.1.18
		-- 1.3.6.1.4.1.6296.101.4.7.1.1.18
		sleAdvaReceivedSectorAbility OBJECT-TYPE
			SYNTAX BITS
				{
				other(0),
				ethernet(1),
				isoethernet(2)
				}
			MAX-ACCESS read-only
			STATUS current
			DESCRIPTION
				"Autonegiotation package - aAutoNegLocalSectorAbility. (AutoNego)"
			::= { sleAdvaGeneralEntry 18 }

		
--   1.3.6.1.4.1.6296.101.4.7.1.1.19
-- 1.3.6.1.4.1.6296.101.4.7.1.1.19
		-- 1.3.6.1.4.1.6296.101.4.7.1.1.19
		sleAdvaDuplexCapabilities OBJECT-TYPE
			SYNTAX INTEGER
				{
				halfduplex(0),
				fullduplex(1)
				}
			MAX-ACCESS read-only
			STATUS current
			DESCRIPTION
				"Mandatory package - aMacCapabilities. 
				(PHY)The modes of duplex the access interface can support"
			::= { sleAdvaGeneralEntry 19 }

		
--   1.3.6.1.4.1.6296.101.4.7.1.1.20
-- 1.3.6.1.4.1.6296.101.4.7.1.1.20
		-- 1.3.6.1.4.1.6296.101.4.7.1.1.20
		sleAdvaPHYType OBJECT-TYPE
			SYNTAX INTEGER
				{
				other(1),
				unknown(2),
				none(3),
				base10(4),
				base100T4(5),
				base100X(6),
				base100T2(7),
				base1000X(8),
				base1000T(9)
				}
			MAX-ACCESS read-only
			STATUS current
			DESCRIPTION
				"Basic Package - aPhyType. (PHY)"
			::= { sleAdvaGeneralEntry 20 }

		
--   1.3.6.1.4.1.6296.101.4.7.1.1.21
-- 1.3.6.1.4.1.6296.101.4.7.1.1.21
		-- 1.3.6.1.4.1.6296.101.4.7.1.1.21
		sleAdvaPHYTypeList OBJECT-TYPE
			SYNTAX BITS
				{
				other(0),
				unknown(1),
				none(2),
				base10(3),
				base100T4(4),
				base100X(5),
				base100T2(6),
				base1000X(7),
				base1000T(8)
				}
			MAX-ACCESS read-only
			STATUS current
			DESCRIPTION
				"Basic Package - aPhyTypeList. (PHY)"
			::= { sleAdvaGeneralEntry 21 }

		
--   1.3.6.1.4.1.6296.101.4.7.1.1.22
-- 1.3.6.1.4.1.6296.101.4.7.1.1.22
		-- 1.3.6.1.4.1.6296.101.4.7.1.1.22
		sleAdvaMIIDetect OBJECT-TYPE
			SYNTAX INTEGER
				{
				unknown(1),
				nothingConnected(2),
				connected(3),
				absent(4)
				}
			MAX-ACCESS read-only
			STATUS current
			DESCRIPTION
				"Basic Package - aMIIDetect. (PHY)"
			::= { sleAdvaGeneralEntry 22 }

		
--   1.3.6.1.4.1.6296.101.4.7.1.1.23
-- 1.3.6.1.4.1.6296.101.4.7.1.1.23
		-- 1.3.6.1.4.1.6296.101.4.7.1.1.23
		sleAdvaPHYState OBJECT-TYPE
			SYNTAX INTEGER
				{
				enable(1),
				disable(2)
				}
			MAX-ACCESS read-only
			STATUS current
			DESCRIPTION
				"Description."
			::= { sleAdvaGeneralEntry 23 }

		
--   1.3.6.1.4.1.6296.101.4.7.1.1.24
-- 1.3.6.1.4.1.6296.101.4.7.1.1.24
		-- 1.3.6.1.4.1.6296.101.4.7.1.1.24
		sleAdvaGoodFramesTransmitted OBJECT-TYPE
			SYNTAX Integer32
			MAX-ACCESS read-only
			STATUS current
			DESCRIPTION
				"Mandatory package - aFramesTransmittedOK. (PHY)Non-resettable, 
				wrapping count of good frames transmitted since OAM enabled."
			::= { sleAdvaGeneralEntry 24 }

		
--   1.3.6.1.4.1.6296.101.4.7.1.1.25
-- 1.3.6.1.4.1.6296.101.4.7.1.1.25
		-- 1.3.6.1.4.1.6296.101.4.7.1.1.25
		sleAdvaSingleCollisionFrames OBJECT-TYPE
			SYNTAX Integer32
			MAX-ACCESS read-only
			STATUS current
			DESCRIPTION
				"Mandatory package - aSingleCollisionFrames. (PHY)Non-resettable, 
				wrapping count of single collisions since OAM enabled."
			::= { sleAdvaGeneralEntry 25 }

		
--   1.3.6.1.4.1.6296.101.4.7.1.1.26
-- 1.3.6.1.4.1.6296.101.4.7.1.1.26
		-- 1.3.6.1.4.1.6296.101.4.7.1.1.26
		sleAdvaMultipleCollisionFrames OBJECT-TYPE
			SYNTAX Integer32
			MAX-ACCESS read-only
			STATUS current
			DESCRIPTION
				"Mandatory package - aMultipleCollisionFrames. (PHY)Non-resettable, 
				wrapping count of multiple collisions since OAM enabled."
			::= { sleAdvaGeneralEntry 26 }

		
--   1.3.6.1.4.1.6296.101.4.7.1.1.27
-- 1.3.6.1.4.1.6296.101.4.7.1.1.27
		-- 1.3.6.1.4.1.6296.101.4.7.1.1.27
		sleAdvaGoodFramesReceived OBJECT-TYPE
			SYNTAX Integer32
			MAX-ACCESS read-only
			STATUS current
			DESCRIPTION
				"Mandatory package - aFramesReceivedOKNon-resettable, 
				wrapping count of good frames received since OAM enabled"
			::= { sleAdvaGeneralEntry 27 }

		
--   1.3.6.1.4.1.6296.101.4.7.1.1.28
-- 1.3.6.1.4.1.6296.101.4.7.1.1.28
		-- 1.3.6.1.4.1.6296.101.4.7.1.1.28
		sleAdvaFCSErrors OBJECT-TYPE
			SYNTAX Integer32
			MAX-ACCESS read-only
			STATUS current
			DESCRIPTION
				"Mandatory package - aFrameCheckSequenceErrors. (PHY)Non-resettable, 
				wrapping count of frames received with frame check sequence 
				error since OAM enabled."
			::= { sleAdvaGeneralEntry 28 }

		
--   1.3.6.1.4.1.6296.101.4.7.1.1.29
-- 1.3.6.1.4.1.6296.101.4.7.1.1.29
		-- 1.3.6.1.4.1.6296.101.4.7.1.1.29
		sleAdvaAlignmentErrors OBJECT-TYPE
			SYNTAX Integer32
			MAX-ACCESS read-only
			STATUS current
			DESCRIPTION
				"Mandatory package - aAlignmentErrors. (PHY)Non-resettable, 
				wrapping count of frames received with alignment error since OAM enabled."
			::= { sleAdvaGeneralEntry 29 }

		
--   1.3.6.1.4.1.6296.101.4.7.1.1.30
-- 1.3.6.1.4.1.6296.101.4.7.1.1.30
		-- 1.3.6.1.4.1.6296.101.4.7.1.1.30
		sleAdvaFramesTooLong OBJECT-TYPE
			SYNTAX Integer32
			MAX-ACCESS read-only
			STATUS current
			DESCRIPTION
				"aFrameTooLongErrors. (PHY)Non-resettable, wrapping count 
				of frames received longer than maxFrameSize"
			::= { sleAdvaGeneralEntry 30 }

		
--   1.3.6.1.4.1.6296.101.4.7.1.1.31
-- 1.3.6.1.4.1.6296.101.4.7.1.1.31
		-- 1.3.6.1.4.1.6296.101.4.7.1.1.31
		sleAdvaBytesTransmitted OBJECT-TYPE
			SYNTAX Integer32
			MAX-ACCESS read-only
			STATUS current
			DESCRIPTION
				"Non-resettable, wrapping count of bytes transmitted 
				since OAM enabled. (PHY)"
			::= { sleAdvaGeneralEntry 31 }

		
--   1.3.6.1.4.1.6296.101.4.7.1.1.32
-- 1.3.6.1.4.1.6296.101.4.7.1.1.32
		-- 1.3.6.1.4.1.6296.101.4.7.1.1.32
		sleAdvaBytesReceived OBJECT-TYPE
			SYNTAX Integer32
			MAX-ACCESS read-only
			STATUS current
			DESCRIPTION
				"Non-resettable, wrapping count of bytes received since OAM enabled. (PHY)"
			::= { sleAdvaGeneralEntry 32 }

		
--   1.3.6.1.4.1.6296.101.4.7.1.1.33
-- 1.3.6.1.4.1.6296.101.4.7.1.1.33
		-- 1.3.6.1.4.1.6296.101.4.7.1.1.33
		sleAdvaSymbolErrors OBJECT-TYPE
			SYNTAX Integer32
			MAX-ACCESS read-only
			STATUS current
			DESCRIPTION
				"Non-resettable, wrapping count of symbol errors received.  
				Note: some interfaces may only report one symbol error per frame. (PHY)"
			::= { sleAdvaGeneralEntry 33 }

		
--   1.3.6.1.4.1.6296.101.4.7.2
-- 1.3.6.1.4.1.6296.101.4.7.2
		-- 1.3.6.1.4.1.6296.101.4.7.2
		sleAdvaGeneralControl OBJECT IDENTIFIER ::= { sleAdvaGeneral 2 }

		
--   1.3.6.1.4.1.6296.101.4.7.2.1
-- 1.3.6.1.4.1.6296.101.4.7.2.1
		-- 1.3.6.1.4.1.6296.101.4.7.2.1
		sleAdvaGeneralControlRequest OBJECT-TYPE
			SYNTAX INTEGER
				{
				setAdvaGeneralProfile(1),
				setAdvaAutonegProfile(2)
				}
			MAX-ACCESS read-write
			STATUS current
			DESCRIPTION
				"Description."
			::= { sleAdvaGeneralControl 1 }

		
--   1.3.6.1.4.1.6296.101.4.7.2.2
-- 1.3.6.1.4.1.6296.101.4.7.2.2
		-- 1.3.6.1.4.1.6296.101.4.7.2.2
		sleAdvaGeneralControlStatus OBJECT-TYPE
			SYNTAX SleControlStatusType
			MAX-ACCESS read-only
			STATUS current
			DESCRIPTION
				"Description."
			::= { sleAdvaGeneralControl 2 }

		
--   1.3.6.1.4.1.6296.101.4.7.2.3
-- 1.3.6.1.4.1.6296.101.4.7.2.3
		-- 1.3.6.1.4.1.6296.101.4.7.2.3
		sleAdvaGeneralControlTimer OBJECT-TYPE
			SYNTAX Gauge32
			MAX-ACCESS read-write
			STATUS current
			DESCRIPTION
				"Description."
			::= { sleAdvaGeneralControl 3 }

		
--   1.3.6.1.4.1.6296.101.4.7.2.4
-- 1.3.6.1.4.1.6296.101.4.7.2.4
		-- 1.3.6.1.4.1.6296.101.4.7.2.4
		sleAdvaGeneralControlTimeStamp OBJECT-TYPE
			SYNTAX TimeTicks
			MAX-ACCESS read-write
			STATUS current
			DESCRIPTION
				"Description."
			::= { sleAdvaGeneralControl 4 }

		
--   1.3.6.1.4.1.6296.101.4.7.2.5
-- 1.3.6.1.4.1.6296.101.4.7.2.5
		-- 1.3.6.1.4.1.6296.101.4.7.2.5
		sleAdvaGeneralControlReqResult OBJECT-TYPE
			SYNTAX SleControlRequestResultType
			MAX-ACCESS read-write
			STATUS current
			DESCRIPTION
				"Description."
			::= { sleAdvaGeneralControl 5 }

		
--   1.3.6.1.4.1.6296.101.4.7.2.6
-- 1.3.6.1.4.1.6296.101.4.7.2.6
		-- 1.3.6.1.4.1.6296.101.4.7.2.6
		sleAdvaGeneralControlPortIndex OBJECT-TYPE
			SYNTAX INTEGER (1..255)
			MAX-ACCESS read-write
			STATUS current
			DESCRIPTION
				"Description."
			::= { sleAdvaGeneralControl 6 }

		
--   1.3.6.1.4.1.6296.101.4.7.2.7
-- 1.3.6.1.4.1.6296.101.4.7.2.7
		-- 1.3.6.1.4.1.6296.101.4.7.2.7
		sleAdvaGeneralControlRemInstance OBJECT-TYPE
			SYNTAX INTEGER (1..4)
			MAX-ACCESS read-write
			STATUS current
			DESCRIPTION
				"Description."
			::= { sleAdvaGeneralControl 7 }

		
--   1.3.6.1.4.1.6296.101.4.7.2.8
-- 1.3.6.1.4.1.6296.101.4.7.2.8
		-- 1.3.6.1.4.1.6296.101.4.7.2.8
		sleAdvaGeneralControlLineSpeed OBJECT-TYPE
			SYNTAX Integer32
			MAX-ACCESS read-write
			STATUS current
			DESCRIPTION
				"Description."
			::= { sleAdvaGeneralControl 8 }

		
--   1.3.6.1.4.1.6296.101.4.7.2.9
-- 1.3.6.1.4.1.6296.101.4.7.2.9
		-- 1.3.6.1.4.1.6296.101.4.7.2.9
		sleAdvaGeneralControlAutonegiotation OBJECT-TYPE
			SYNTAX INTEGER
				{
				enable(1),
				disable(2)
				}
			MAX-ACCESS read-write
			STATUS current
			DESCRIPTION
				"Description."
			::= { sleAdvaGeneralControl 9 }

		
--   1.3.6.1.4.1.6296.101.4.7.2.10
-- 1.3.6.1.4.1.6296.101.4.7.2.10
		-- 1.3.6.1.4.1.6296.101.4.7.2.10
		sleAdvaGeneralControlLinkLossForwarding OBJECT-TYPE
			SYNTAX INTEGER (0..1)
			MAX-ACCESS read-write
			STATUS current
			DESCRIPTION
				"Description."
			::= { sleAdvaGeneralControl 10 }

		
--   1.3.6.1.4.1.6296.101.4.7.2.11
-- 1.3.6.1.4.1.6296.101.4.7.2.11
		-- 1.3.6.1.4.1.6296.101.4.7.2.11
		sleAdvaGeneralControlUserDefinedString OBJECT-TYPE
			SYNTAX OCTET STRING (SIZE (0..32))
			MAX-ACCESS read-write
			STATUS current
			DESCRIPTION
				"Description."
			::= { sleAdvaGeneralControl 11 }

		
--   1.3.6.1.4.1.6296.101.4.7.2.12
-- 1.3.6.1.4.1.6296.101.4.7.2.12
		-- 1.3.6.1.4.1.6296.101.4.7.2.12
		sleAdvaGeneralControlAdvertisedTechnologyAbility OBJECT-TYPE
			SYNTAX BITS
				{
				global(0),
				unknown(1),
				base10T(2),
				base10TFD(3),
				base100T4(4),
				base100TX(5),
				base100TXFD(6),
				fdxpause(7),
				fdxapause(8),
				fdxspause(9),
				fdxbpause(10),
				base100T2(11),
				base100T2FD(12),
				base1000X(13),
				base1000XFD(14),
				base1000T(15),
				base1000TFD(16),
				remFault1(17),
				remFault2(18),
				isoEthernet(19)
				}
			MAX-ACCESS read-write
			STATUS current
			DESCRIPTION
				"Description."
			::= { sleAdvaGeneralControl 12 }

		
--   1.3.6.1.4.1.6296.101.4.7.2.13
-- 1.3.6.1.4.1.6296.101.4.7.2.13
		-- 1.3.6.1.4.1.6296.101.4.7.2.13
		sleAdvaGeneralControlAdvertisedSectorAbility OBJECT-TYPE
			SYNTAX BITS
				{
				other(0),
				ethernet(1),
				isoethernet(2)
				}
			MAX-ACCESS read-write
			STATUS current
			DESCRIPTION
				"Description."
			::= { sleAdvaGeneralControl 13 }

		
--   1.3.6.1.4.1.6296.101.4.7.3
-- 1.3.6.1.4.1.6296.101.4.7.3
		-- 1.3.6.1.4.1.6296.101.4.7.3
		sleAdvaGeneralNotification OBJECT IDENTIFIER ::= { sleAdvaGeneral 3 }

		
--   1.3.6.1.4.1.6296.101.4.7.3.1
-- 1.3.6.1.4.1.6296.101.4.7.3.1
		-- 1.3.6.1.4.1.6296.101.4.7.3.1
		sleAdvaGeneralProfileChanged NOTIFICATION-TYPE
			OBJECTS { sleAdvaGeneralControlRequest, sleAdvaGeneralControlReqResult, sleAdvaGeneralControlTimeStamp, sleAdvaLineSpeed, sleAdvaAutonegiotation, 
				sleAdvaLinkLossForwarding, sleAdvaUserDefinedString }
			STATUS current
			DESCRIPTION 
				"Description."
			::= { sleAdvaGeneralNotification 1 }

		
--   1.3.6.1.4.1.6296.101.4.7.3.2
-- 1.3.6.1.4.1.6296.101.4.7.3.2
		-- 1.3.6.1.4.1.6296.101.4.7.3.2
		sleAdvaAutonegProfileChanged NOTIFICATION-TYPE
			OBJECTS { sleAdvaGeneralControlRequest, sleAdvaGeneralControlReqResult, sleAdvaGeneralControlTimeStamp, sleAdvaAdvertisedTechnologyAbility, sleAdvaAdvertisedSectorAbility
				 }
			STATUS current
			DESCRIPTION 
				"Description."
			::= { sleAdvaGeneralNotification 2 }

		
--   1.3.6.1.4.1.6296.101.4.8
-- 1.3.6.1.4.1.6296.101.4.8
		-- 1.3.6.1.4.1.6296.101.4.8
		sleAdvaModule OBJECT IDENTIFIER ::= { sleFaultMgmt 8 }

		
--   1.3.6.1.4.1.6296.101.4.8.1
-- 1.3.6.1.4.1.6296.101.4.8.1
		-- 1.3.6.1.4.1.6296.101.4.8.1
		sleAdvaModuleTable OBJECT-TYPE
			SYNTAX SEQUENCE OF SleAdvaModuleEntry
			MAX-ACCESS not-accessible
			STATUS current
			DESCRIPTION
				"Description."
			::= { sleAdvaModule 1 }

		
--   1.3.6.1.4.1.6296.101.4.8.1.1
-- 1.3.6.1.4.1.6296.101.4.8.1.1
		-- 1.3.6.1.4.1.6296.101.4.8.1.1
		sleAdvaModuleEntry OBJECT-TYPE
			SYNTAX SleAdvaModuleEntry
			MAX-ACCESS not-accessible
			STATUS current
			DESCRIPTION
				"Description."
			INDEX { sleOamPortIndex, sleAdvaRemInstance }
			::= { sleAdvaModuleTable 1 }

		
		SleAdvaModuleEntry ::=
			SEQUENCE { 
				sleAdvaModuleType
					INTEGER,
				sleAdvaModulePartNumber
					OCTET STRING,
				sleAdvaModuleSerialNumber
					OCTET STRING,
				sleAdvaModuleFirmwareVersion
					OCTET STRING,
				sleAdvaModuleSoftwareVersion
					OCTET STRING,
				sleAdvaModuleHardwareRevision
					OCTET STRING,
				sleAdvaModuleCLEICode
					OCTET STRING
			 }

--   1.3.6.1.4.1.6296.101.4.8.1.1.1
-- 1.3.6.1.4.1.6296.101.4.8.1.1.1
		-- 1.3.6.1.4.1.6296.101.4.8.1.1.1
		sleAdvaModuleType OBJECT-TYPE
			SYNTAX INTEGER
				{
				sfp(1),
				nemi(2),
				other(3)
				}
			MAX-ACCESS read-only
			STATUS current
			DESCRIPTION
				"encoding TBD"
			::= { sleAdvaModuleEntry 1 }

		
--   1.3.6.1.4.1.6296.101.4.8.1.1.2
-- 1.3.6.1.4.1.6296.101.4.8.1.1.2
		-- 1.3.6.1.4.1.6296.101.4.8.1.1.2
		sleAdvaModulePartNumber OBJECT-TYPE
			SYNTAX OCTET STRING (SIZE (0..16))
			MAX-ACCESS read-only
			STATUS current
			DESCRIPTION
				"Part number for the module"
			::= { sleAdvaModuleEntry 2 }

		
--   1.3.6.1.4.1.6296.101.4.8.1.1.3
-- 1.3.6.1.4.1.6296.101.4.8.1.1.3
		-- 1.3.6.1.4.1.6296.101.4.8.1.1.3
		sleAdvaModuleSerialNumber OBJECT-TYPE
			SYNTAX OCTET STRING (SIZE (0..16))
			MAX-ACCESS read-only
			STATUS current
			DESCRIPTION
				"Serial number for the module"
			::= { sleAdvaModuleEntry 3 }

		
--   1.3.6.1.4.1.6296.101.4.8.1.1.4
-- 1.3.6.1.4.1.6296.101.4.8.1.1.4
		-- 1.3.6.1.4.1.6296.101.4.8.1.1.4
		sleAdvaModuleFirmwareVersion OBJECT-TYPE
			SYNTAX OCTET STRING (SIZE (0..16))
			MAX-ACCESS read-only
			STATUS current
			DESCRIPTION
				"Firmware version for the module."
			::= { sleAdvaModuleEntry 4 }

		
--   1.3.6.1.4.1.6296.101.4.8.1.1.5
-- 1.3.6.1.4.1.6296.101.4.8.1.1.5
		-- 1.3.6.1.4.1.6296.101.4.8.1.1.5
		sleAdvaModuleSoftwareVersion OBJECT-TYPE
			SYNTAX OCTET STRING (SIZE (0..16))
			MAX-ACCESS read-only
			STATUS current
			DESCRIPTION
				"Software version for the module"
			::= { sleAdvaModuleEntry 5 }

		
--   1.3.6.1.4.1.6296.101.4.8.1.1.6
-- 1.3.6.1.4.1.6296.101.4.8.1.1.6
		-- 1.3.6.1.4.1.6296.101.4.8.1.1.6
		sleAdvaModuleHardwareRevision OBJECT-TYPE
			SYNTAX OCTET STRING (SIZE (0..4))
			MAX-ACCESS read-only
			STATUS current
			DESCRIPTION
				"Hardware revision for the module."
			::= { sleAdvaModuleEntry 6 }

		
--   1.3.6.1.4.1.6296.101.4.8.1.1.7
-- 1.3.6.1.4.1.6296.101.4.8.1.1.7
		-- 1.3.6.1.4.1.6296.101.4.8.1.1.7
		sleAdvaModuleCLEICode OBJECT-TYPE
			SYNTAX OCTET STRING (SIZE (0..14))
			MAX-ACCESS read-only
			STATUS current
			DESCRIPTION
				"CLEI for the module."
			::= { sleAdvaModuleEntry 7 }

		
--   1.3.6.1.4.1.6296.101.4.9
-- 1.3.6.1.4.1.6296.101.4.9
		-- 1.3.6.1.4.1.6296.101.4.9
		sleAdvaOptical OBJECT IDENTIFIER ::= { sleFaultMgmt 9 }

		
--   1.3.6.1.4.1.6296.101.4.9.1
-- 1.3.6.1.4.1.6296.101.4.9.1
		-- 1.3.6.1.4.1.6296.101.4.9.1
		sleAdvaOpticalTable OBJECT-TYPE
			SYNTAX SEQUENCE OF SleAdvaOpticalEntry
			MAX-ACCESS not-accessible
			STATUS current
			DESCRIPTION
				"Description."
			::= { sleAdvaOptical 1 }

		
--   1.3.6.1.4.1.6296.101.4.9.1.1
-- 1.3.6.1.4.1.6296.101.4.9.1.1
		-- 1.3.6.1.4.1.6296.101.4.9.1.1
		sleAdvaOpticalEntry OBJECT-TYPE
			SYNTAX SleAdvaOpticalEntry
			MAX-ACCESS not-accessible
			STATUS current
			DESCRIPTION
				"Description."
			INDEX { sleOamPortIndex, sleAdvaRemInstance }
			::= { sleAdvaOpticalTable 1 }

		
		SleAdvaOpticalEntry ::=
			SEQUENCE { 
				sleAdvaOpticalThresholdLevel
					INTEGER,
				sleAdvaLinkLength1
					INTEGER,
				sleAdvaLinkLength2
					INTEGER,
				sleAdvaLinkLength3
					INTEGER,
				sleAdvaLinkLength4
					INTEGER,
				sleAdvaLinkLengthCu
					INTEGER,
				sleAdvaWaveLength
					INTEGER,
				sleAdvaLaserBias
					INTEGER,
				sleAdvaTransmitPower
					INTEGER,
				sleAdvaReceivePower
					INTEGER,
				sleAdvaLaserTxTemperature
					INTEGER
			 }

--   1.3.6.1.4.1.6296.101.4.9.1.1.1
-- 1.3.6.1.4.1.6296.101.4.9.1.1.1
		-- 1.3.6.1.4.1.6296.101.4.9.1.1.1
		sleAdvaOpticalThresholdLevel OBJECT-TYPE
			SYNTAX INTEGER (0..65535)
			MAX-ACCESS read-only
			STATUS current
			DESCRIPTION
				"Threshold for the receive power level in dBm below which 
				the Interface optical threshold alarm will be activated.Per interface."
			::= { sleAdvaOpticalEntry 1 }

		
--   1.3.6.1.4.1.6296.101.4.9.1.1.2
-- 1.3.6.1.4.1.6296.101.4.9.1.1.2
		-- 1.3.6.1.4.1.6296.101.4.9.1.1.2
		sleAdvaLinkLength1 OBJECT-TYPE
			SYNTAX INTEGER (0..255)
			MAX-ACCESS read-only
			STATUS current
			DESCRIPTION
				"Link length supported for 9/125 mm fiber, units of km"
			::= { sleAdvaOpticalEntry 2 }

		
--   1.3.6.1.4.1.6296.101.4.9.1.1.3
-- 1.3.6.1.4.1.6296.101.4.9.1.1.3
		-- 1.3.6.1.4.1.6296.101.4.9.1.1.3
		sleAdvaLinkLength2 OBJECT-TYPE
			SYNTAX INTEGER (0..255)
			MAX-ACCESS read-only
			STATUS current
			DESCRIPTION
				"Link length supported for 9/125 mm fiber, units of 100 m"
			::= { sleAdvaOpticalEntry 3 }

		
--   1.3.6.1.4.1.6296.101.4.9.1.1.4
-- 1.3.6.1.4.1.6296.101.4.9.1.1.4
		-- 1.3.6.1.4.1.6296.101.4.9.1.1.4
		sleAdvaLinkLength3 OBJECT-TYPE
			SYNTAX INTEGER (0..255)
			MAX-ACCESS read-only
			STATUS current
			DESCRIPTION
				"Link length supported for 50/125 mm fiber, units of 10 m"
			::= { sleAdvaOpticalEntry 4 }

		
--   1.3.6.1.4.1.6296.101.4.9.1.1.5
-- 1.3.6.1.4.1.6296.101.4.9.1.1.5
		-- 1.3.6.1.4.1.6296.101.4.9.1.1.5
		sleAdvaLinkLength4 OBJECT-TYPE
			SYNTAX INTEGER (0..255)
			MAX-ACCESS read-only
			STATUS current
			DESCRIPTION
				"Link length supported for 62.5/125 mm fiber, units of 10 m"
			::= { sleAdvaOpticalEntry 5 }

		
--   1.3.6.1.4.1.6296.101.4.9.1.1.6
-- 1.3.6.1.4.1.6296.101.4.9.1.1.6
		-- 1.3.6.1.4.1.6296.101.4.9.1.1.6
		sleAdvaLinkLengthCu OBJECT-TYPE
			SYNTAX INTEGER (0..255)
			MAX-ACCESS read-only
			STATUS current
			DESCRIPTION
				"Link length supported for copper, units of meters"
			::= { sleAdvaOpticalEntry 6 }

		
--   1.3.6.1.4.1.6296.101.4.9.1.1.7
-- 1.3.6.1.4.1.6296.101.4.9.1.1.7
		-- 1.3.6.1.4.1.6296.101.4.9.1.1.7
		sleAdvaWaveLength OBJECT-TYPE
			SYNTAX INTEGER (0..65535)
			MAX-ACCESS read-only
			STATUS current
			DESCRIPTION
				"Nominal wavelength in nm"
			::= { sleAdvaOpticalEntry 7 }

		
--   1.3.6.1.4.1.6296.101.4.9.1.1.8
-- 1.3.6.1.4.1.6296.101.4.9.1.1.8
		-- 1.3.6.1.4.1.6296.101.4.9.1.1.8
		sleAdvaLaserBias OBJECT-TYPE
			SYNTAX INTEGER (0..65535)
			MAX-ACCESS read-only
			STATUS current
			DESCRIPTION
				"Current laser bias current in mA."
			::= { sleAdvaOpticalEntry 8 }

		
--   1.3.6.1.4.1.6296.101.4.9.1.1.9
-- 1.3.6.1.4.1.6296.101.4.9.1.1.9
		-- 1.3.6.1.4.1.6296.101.4.9.1.1.9
		sleAdvaTransmitPower OBJECT-TYPE
			SYNTAX INTEGER (0..65535)
			MAX-ACCESS read-only
			STATUS current
			DESCRIPTION
				"Current transmit power in dBm as reported by optics."
			::= { sleAdvaOpticalEntry 9 }

		
--   1.3.6.1.4.1.6296.101.4.9.1.1.10
-- 1.3.6.1.4.1.6296.101.4.9.1.1.10
		-- 1.3.6.1.4.1.6296.101.4.9.1.1.10
		sleAdvaReceivePower OBJECT-TYPE
			SYNTAX INTEGER (0..65535)
			MAX-ACCESS read-only
			STATUS current
			DESCRIPTION
				"Current receive power in dBm as reported by optics.  "
			::= { sleAdvaOpticalEntry 10 }

		
--   1.3.6.1.4.1.6296.101.4.9.1.1.11
-- 1.3.6.1.4.1.6296.101.4.9.1.1.11
		-- 1.3.6.1.4.1.6296.101.4.9.1.1.11
		sleAdvaLaserTxTemperature OBJECT-TYPE
			SYNTAX INTEGER (0..65535)
			MAX-ACCESS read-only
			STATUS current
			DESCRIPTION
				"Current temperature of laser in degrees C."
			::= { sleAdvaOpticalEntry 11 }

		
--   1.3.6.1.4.1.6296.101.4.9.2
-- 1.3.6.1.4.1.6296.101.4.9.2
		-- 1.3.6.1.4.1.6296.101.4.9.2
		sleAdvaOpticalControl OBJECT IDENTIFIER ::= { sleAdvaOptical 2 }

		
--   1.3.6.1.4.1.6296.101.4.9.2.1
-- 1.3.6.1.4.1.6296.101.4.9.2.1
		-- 1.3.6.1.4.1.6296.101.4.9.2.1
		sleAdvaOpticalControlRequest OBJECT-TYPE
			SYNTAX INTEGER { setAdvaOpticalAlarm(1) }
			MAX-ACCESS read-write
			STATUS current
			DESCRIPTION
				"Description."
			::= { sleAdvaOpticalControl 1 }

		
--   1.3.6.1.4.1.6296.101.4.9.2.2
-- 1.3.6.1.4.1.6296.101.4.9.2.2
		-- 1.3.6.1.4.1.6296.101.4.9.2.2
		sleAdvaOpticalControlStatus OBJECT-TYPE
			SYNTAX SleControlStatusType
			MAX-ACCESS read-only
			STATUS current
			DESCRIPTION
				"Description."
			::= { sleAdvaOpticalControl 2 }

		
--   1.3.6.1.4.1.6296.101.4.9.2.3
-- 1.3.6.1.4.1.6296.101.4.9.2.3
		-- 1.3.6.1.4.1.6296.101.4.9.2.3
		sleAdvaOpticalControlTimer OBJECT-TYPE
			SYNTAX Gauge32
			MAX-ACCESS read-write
			STATUS current
			DESCRIPTION
				"Description."
			::= { sleAdvaOpticalControl 3 }

		
--   1.3.6.1.4.1.6296.101.4.9.2.4
-- 1.3.6.1.4.1.6296.101.4.9.2.4
		-- 1.3.6.1.4.1.6296.101.4.9.2.4
		sleAdvaOpticalControlTimeStamp OBJECT-TYPE
			SYNTAX TimeTicks
			MAX-ACCESS read-write
			STATUS current
			DESCRIPTION
				"Description."
			::= { sleAdvaOpticalControl 4 }

		
--   1.3.6.1.4.1.6296.101.4.9.2.5
-- 1.3.6.1.4.1.6296.101.4.9.2.5
		-- 1.3.6.1.4.1.6296.101.4.9.2.5
		sleAdvaOpticalControlReqResult OBJECT-TYPE
			SYNTAX SleControlRequestResultType
			MAX-ACCESS read-write
			STATUS current
			DESCRIPTION
				"Description."
			::= { sleAdvaOpticalControl 5 }

		
--   1.3.6.1.4.1.6296.101.4.9.2.6
-- 1.3.6.1.4.1.6296.101.4.9.2.6
		-- 1.3.6.1.4.1.6296.101.4.9.2.6
		sleAdvaOpticalControlPortIndex OBJECT-TYPE
			SYNTAX INTEGER (1..255)
			MAX-ACCESS read-write
			STATUS current
			DESCRIPTION
				"Description."
			::= { sleAdvaOpticalControl 6 }

		
--   1.3.6.1.4.1.6296.101.4.9.2.7
-- 1.3.6.1.4.1.6296.101.4.9.2.7
		-- 1.3.6.1.4.1.6296.101.4.9.2.7
		sleAdvaOpticalControlRemInstance OBJECT-TYPE
			SYNTAX INTEGER (1..3)
			MAX-ACCESS read-write
			STATUS current
			DESCRIPTION
				"Description."
			::= { sleAdvaOpticalControl 7 }

		
--   1.3.6.1.4.1.6296.101.4.9.2.8
-- 1.3.6.1.4.1.6296.101.4.9.2.8
		-- 1.3.6.1.4.1.6296.101.4.9.2.8
		sleAdvaOpticalControlThresholdLevel OBJECT-TYPE
			SYNTAX INTEGER (0..65535)
			MAX-ACCESS read-write
			STATUS current
			DESCRIPTION
				"Description."
			::= { sleAdvaOpticalControl 8 }

		
--   1.3.6.1.4.1.6296.101.4.9.3
-- 1.3.6.1.4.1.6296.101.4.9.3
		-- 1.3.6.1.4.1.6296.101.4.9.3
		sleAdvaOpticalNotification OBJECT IDENTIFIER ::= { sleAdvaOptical 3 }

		
--   1.3.6.1.4.1.6296.101.4.9.3.1
-- 1.3.6.1.4.1.6296.101.4.9.3.1
		-- 1.3.6.1.4.1.6296.101.4.9.3.1
		sleAdvaOpticalAlarmChanged NOTIFICATION-TYPE
			OBJECTS { sleAdvaOpticalControlRequest, sleAdvaOpticalControlReqResult, sleAdvaOpticalControlTimeStamp, sleAdvaOpticalThresholdLevel }
			STATUS current
			DESCRIPTION 
				"Description."
			::= { sleAdvaOpticalNotification 1 }

		
--   1.3.6.1.4.1.6296.101.4.10
-- 1.3.6.1.4.1.6296.101.4.10
		-- 1.3.6.1.4.1.6296.101.4.10
		sleAdvaOam OBJECT IDENTIFIER ::= { sleFaultMgmt 10 }

		
--   1.3.6.1.4.1.6296.101.4.10.1
-- 1.3.6.1.4.1.6296.101.4.10.1
		-- 1.3.6.1.4.1.6296.101.4.10.1
		sleAdvaOamTable OBJECT-TYPE
			SYNTAX SEQUENCE OF SleAdvaOamEntry
			MAX-ACCESS not-accessible
			STATUS current
			DESCRIPTION
				"Description."
			::= { sleAdvaOam 1 }

		
--   1.3.6.1.4.1.6296.101.4.10.1.1
-- 1.3.6.1.4.1.6296.101.4.10.1.1
		-- 1.3.6.1.4.1.6296.101.4.10.1.1
		sleAdvaOamEntry OBJECT-TYPE
			SYNTAX SleAdvaOamEntry
			MAX-ACCESS not-accessible
			STATUS current
			DESCRIPTION
				"Description."
			INDEX { sleOamPortIndex, sleAdvaRemInstance }
			::= { sleAdvaOamTable 1 }

		
		SleAdvaOamEntry ::=
			SEQUENCE { 
				sleAdvaAdminStatus
					INTEGER,
				sleAdvaMode
					INTEGER,
				sleAdvaRemMACAddress
					OCTET STRING,
				sleAdvaRemConfig
					BITS,
				sleAdvaRemPduConfig
					INTEGER,
				sleAdvaLocFlags
					BITS,
				sleAdvaRemFlags
					BITS,
				sleAdvaRemState
					BITS,
				sleAdvaRemVendorOUI
					INTEGER,
				sleAdvaRemDeviceNumber
					INTEGER,
				sleAdvaRemVendorVersion
					INTEGER,
				sleAdvaLocErrSymbolPeriodEventConfig
					INTEGER,
				sleAdvaLocErrFrameEventConfig
					INTEGER,
				sleAdvaLocErrFramePeriodEventConfig
					INTEGER,
				sleAdvaLocErrFrameSecsSummaryEventConfig
					INTEGER,
				sleAdvaPDUsTx
					Integer32,
				sleAdvaPDUsRx
					Integer32,
				sleAdvaUnsupportedCodesRx
					Integer32,
				sleAdvaInfoPDUsTx
					Integer32,
				sleAdvaInfoPDUsRx
					Integer32,
				sleAdvaEventNotificationPDUsTx
					Integer32,
				sleAdvaUniqueEventNotificationPDUsTx
					Integer32,
				sleAdvaDupEventNotificationPDUsTx
					Integer32,
				sleAdvaLoopbackControlPDUsTx
					Integer32,
				sleAdvaLoopbackControlPDUsRx
					Integer32,
				sleAdvaVariableRequestPDUsTx
					Integer32,
				sleAdvaVariableRequestPDUsRx
					Integer32,
				sleAdvaVariableResponsePDUsTx
					Integer32,
				sleAdvaVariableResponsePDUsRx
					Integer32,
				sleAdvaVendorPDUsTx
					Integer32,
				sleAdvaVendorPDUsRx
					Integer32,
				sleAdvaRemFramesLostDuetoOAMErr
					Integer32,
				sleAdvaLocErrSymbolPeriodEvent
					Integer32,
				sleAdvaLocErrFrameSecsEvent
					Integer32,
				sleAdvaLocErrFramePeriodEvent
					Integer32,
				sleAdvaLocErrFrameSecsSummaryEvent
					Integer32,
				sleAdvaRemErrSymbolPeriodEvent
					Integer32,
				sleAdvaRemErrFrameSecsEvent
					Integer32,
				sleAdvaRemoteErrorFramePeriodEvent
					Integer32,
				sleAdvaRemoteErrorFrameSecsSummaryEvent
					Integer32
			 }

--   1.3.6.1.4.1.6296.101.4.10.1.1.1
-- 1.3.6.1.4.1.6296.101.4.10.1.1.1
		-- 1.3.6.1.4.1.6296.101.4.10.1.1.1
		sleAdvaAdminStatus OBJECT-TYPE
			SYNTAX INTEGER
				{
				disable(0),
				enable(1)
				}
			MAX-ACCESS read-only
			STATUS current
			DESCRIPTION
				"OAM package - aOAMAdminState (Configuration)Whether 
				the OAM sublayer is enabled or disabled."
			::= { sleAdvaOamEntry 1 }

		
--   1.3.6.1.4.1.6296.101.4.10.1.1.2
-- 1.3.6.1.4.1.6296.101.4.10.1.1.2
		-- 1.3.6.1.4.1.6296.101.4.10.1.1.2
		sleAdvaMode OBJECT-TYPE
			SYNTAX INTEGER
				{
				passive(0),
				active(1)
				}
			MAX-ACCESS read-only
			STATUS current
			DESCRIPTION
				"OAM package - aOAMMode. (Configuration)Mode of the OAM client"
			::= { sleAdvaOamEntry 2 }

		
--   1.3.6.1.4.1.6296.101.4.10.1.1.3
-- 1.3.6.1.4.1.6296.101.4.10.1.1.3
		-- 1.3.6.1.4.1.6296.101.4.10.1.1.3
		sleAdvaRemMACAddress OBJECT-TYPE
			SYNTAX OCTET STRING
			MAX-ACCESS read-only
			STATUS current
			DESCRIPTION
				"OAM package - aOAMRemoteMACAddress. (Configuration)"
			::= { sleAdvaOamEntry 3 }

		
--   1.3.6.1.4.1.6296.101.4.10.1.1.4
-- 1.3.6.1.4.1.6296.101.4.10.1.1.4
		-- 1.3.6.1.4.1.6296.101.4.10.1.1.4
		sleAdvaRemConfig OBJECT-TYPE
			SYNTAX BITS
				{
				unidirSupport(0),
				loopbackSupport(1),
				linkEvents(2),
				variableRetrieval(3),
				orgSpecific(4),
				orgSpecificEvents(5),
				orgSpecificInfoTLV(6)
				}
			MAX-ACCESS read-only
			STATUS current
			DESCRIPTION
				"OAM package - aOAMRemoteConfiguration. (Configuration)Bit-mask 
				corresponding to the OAM configuration field:"
			::= { sleAdvaOamEntry 4 }

		
--   1.3.6.1.4.1.6296.101.4.10.1.1.5
-- 1.3.6.1.4.1.6296.101.4.10.1.1.5
		-- 1.3.6.1.4.1.6296.101.4.10.1.1.5
		sleAdvaRemPduConfig OBJECT-TYPE
			SYNTAX INTEGER (0..65535)
			MAX-ACCESS read-only
			STATUS current
			DESCRIPTION
				"OAM package - aOAMRemotePDUConfiguration. (Configuration)The maximum 
				PDU size supported"
			::= { sleAdvaOamEntry 5 }

		
--   1.3.6.1.4.1.6296.101.4.10.1.1.6
-- 1.3.6.1.4.1.6296.101.4.10.1.1.6
		-- 1.3.6.1.4.1.6296.101.4.10.1.1.6
		sleAdvaLocFlags OBJECT-TYPE
			SYNTAX BITS
				{
				linkFault(0),
				dyingGasp(1),
				criticalEvent(2),
				localStableDiscovering(3),
				localStable(4),
				remoteStableDiscovering(5),
				remoteStable(6)
				}
			MAX-ACCESS read-only
			STATUS current
			DESCRIPTION
				"OAM package - aOAMLocalFlags. (Configuration)Bit-mask corresponding 
				to the OAM flag field transmitted:"
			::= { sleAdvaOamEntry 6 }

		
--   1.3.6.1.4.1.6296.101.4.10.1.1.7
-- 1.3.6.1.4.1.6296.101.4.10.1.1.7
		-- 1.3.6.1.4.1.6296.101.4.10.1.1.7
		sleAdvaRemFlags OBJECT-TYPE
			SYNTAX BITS
				{
				linkFault(0),
				dyingGasp(1),
				criticalEvent(2),
				localStableDiscovering(3),
				localStable(4),
				remoteStableDiscovering(5),
				remoteStable(6)
				}
			MAX-ACCESS read-only
			STATUS current
			DESCRIPTION
				"OAM package - aOAMRemoteFlags. (Configuration)Bit-mask corresponding 
				to the OAM flag field received"
			::= { sleAdvaOamEntry 7 }

		
--   1.3.6.1.4.1.6296.101.4.10.1.1.8
-- 1.3.6.1.4.1.6296.101.4.10.1.1.8
		-- 1.3.6.1.4.1.6296.101.4.10.1.1.8
		sleAdvaRemState OBJECT-TYPE
			SYNTAX BITS
				{
				reserved(0),
				parserAction1(1),
				parserAction2(2),
				muxAction(3)
				}
			MAX-ACCESS read-only
			STATUS current
			DESCRIPTION
				"OAM package - aOAMRemoteState. (Configuration)Bit-mask corresponding 
				to the OAM State field received"
			::= { sleAdvaOamEntry 8 }

		
--   1.3.6.1.4.1.6296.101.4.10.1.1.9
-- 1.3.6.1.4.1.6296.101.4.10.1.1.9
		-- 1.3.6.1.4.1.6296.101.4.10.1.1.9
		sleAdvaRemVendorOUI OBJECT-TYPE
			SYNTAX INTEGER (0..65535)
			MAX-ACCESS read-only
			STATUS current
			DESCRIPTION
				"OAM package - aOAMRemoteVendorOUI. (Configuration)The value of 
				the OUI from the remote end of the OAM link."
			::= { sleAdvaOamEntry 9 }

		
--   1.3.6.1.4.1.6296.101.4.10.1.1.10
-- 1.3.6.1.4.1.6296.101.4.10.1.1.10
		-- 1.3.6.1.4.1.6296.101.4.10.1.1.10
		sleAdvaRemDeviceNumber OBJECT-TYPE
			SYNTAX INTEGER (0..65535)
			MAX-ACCESS read-only
			STATUS current
			DESCRIPTION
				"OAM package - aOAMRemoteVendorIdDeviceNumber. (Configuration)
				The value of the Device Identifier  from the remote end of the OAM link."
			::= { sleAdvaOamEntry 10 }

		
--   1.3.6.1.4.1.6296.101.4.10.1.1.11
-- 1.3.6.1.4.1.6296.101.4.10.1.1.11
		-- 1.3.6.1.4.1.6296.101.4.10.1.1.11
		sleAdvaRemVendorVersion OBJECT-TYPE
			SYNTAX INTEGER (0..65535)
			MAX-ACCESS read-only
			STATUS current
			DESCRIPTION
				"OAM package - aOAMRemoteVendorIdVersion. (Configuration)
				The value of the Version Identifier from the remote end of the OAM link."
			::= { sleAdvaOamEntry 11 }

		
--   1.3.6.1.4.1.6296.101.4.10.1.1.12
-- 1.3.6.1.4.1.6296.101.4.10.1.1.12
		-- 1.3.6.1.4.1.6296.101.4.10.1.1.12
		sleAdvaLocErrSymbolPeriodEventConfig OBJECT-TYPE
			SYNTAX INTEGER (0..65535)
			MAX-ACCESS read-only
			STATUS current
			DESCRIPTION
				"OAM package - aOAMLocalErrSymPeriodConfig. (Configuration) 
				Configuration for the event indicating the duration of 
				the period and the number of symbols that must be exceeded."
			::= { sleAdvaOamEntry 12 }

		
--   1.3.6.1.4.1.6296.101.4.10.1.1.13
-- 1.3.6.1.4.1.6296.101.4.10.1.1.13
		-- 1.3.6.1.4.1.6296.101.4.10.1.1.13
		sleAdvaLocErrFrameEventConfig OBJECT-TYPE
			SYNTAX INTEGER (0..65535)
			MAX-ACCESS read-only
			STATUS current
			DESCRIPTION
				"OAM package - aOAMLocalErrFrameConfig. (Configuration)
				Configuration for the event indicating the duration and 
				the number of errored frames that must be exceeded."
			::= { sleAdvaOamEntry 13 }

		
--   1.3.6.1.4.1.6296.101.4.10.1.1.14
-- 1.3.6.1.4.1.6296.101.4.10.1.1.14
		-- 1.3.6.1.4.1.6296.101.4.10.1.1.14
		sleAdvaLocErrFramePeriodEventConfig OBJECT-TYPE
			SYNTAX INTEGER (0..65535)
			MAX-ACCESS read-only
			STATUS current
			DESCRIPTION
				"OAM package - aOAMLocalErrFramePeriodConfig. (Configuration)
				Configuration for the event indicating the durationin terms of 
				minFrameSize that can be transmitted and that number of errored 
				frames that must be exceeded."
			::= { sleAdvaOamEntry 14 }

		
--   1.3.6.1.4.1.6296.101.4.10.1.1.15
-- 1.3.6.1.4.1.6296.101.4.10.1.1.15
		-- 1.3.6.1.4.1.6296.101.4.10.1.1.15
		sleAdvaLocErrFrameSecsSummaryEventConfig OBJECT-TYPE
			SYNTAX INTEGER (0..65535)
			MAX-ACCESS read-only
			STATUS current
			DESCRIPTION
				"OAM package - aOAMLocalErrFrameSecsSummaryConfig. (Configuration)
				Configuration for the evert indicating duration window and number 
				of errored frame seconds in that duration that must be exceeded."
			::= { sleAdvaOamEntry 15 }

		
--   1.3.6.1.4.1.6296.101.4.10.1.1.16
-- 1.3.6.1.4.1.6296.101.4.10.1.1.16
		-- 1.3.6.1.4.1.6296.101.4.10.1.1.16
		sleAdvaPDUsTx OBJECT-TYPE
			SYNTAX Integer32
			MAX-ACCESS read-only
			STATUS current
			DESCRIPTION
				"OAM package - aOAMPDUTx. (PDU Performance)Non-resettable, 
				wrapping count of OAM PDUs transmitted since OAM enabled."
			::= { sleAdvaOamEntry 16 }

		
--   1.3.6.1.4.1.6296.101.4.10.1.1.17
-- 1.3.6.1.4.1.6296.101.4.10.1.1.17
		-- 1.3.6.1.4.1.6296.101.4.10.1.1.17
		sleAdvaPDUsRx OBJECT-TYPE
			SYNTAX Integer32
			MAX-ACCESS read-only
			STATUS current
			DESCRIPTION
				"OAM package - aOAMPDURx. (PDU Performance)Non-resettable, 
				wrapping count of OAM PDUs received since OAM enabled."
			::= { sleAdvaOamEntry 17 }

		
--   1.3.6.1.4.1.6296.101.4.10.1.1.18
-- 1.3.6.1.4.1.6296.101.4.10.1.1.18
		-- 1.3.6.1.4.1.6296.101.4.10.1.1.18
		sleAdvaUnsupportedCodesRx OBJECT-TYPE
			SYNTAX Integer32
			MAX-ACCESS read-only
			STATUS current
			DESCRIPTION
				"OAM package - aOAMUnsupportedCodesRx. (PDU Performance)Non-resettable, 
				wrapping count of OAM PDUs received that are not supported by device 
				since OAM enabled."
			::= { sleAdvaOamEntry 18 }

		
--   1.3.6.1.4.1.6296.101.4.10.1.1.19
-- 1.3.6.1.4.1.6296.101.4.10.1.1.19
		-- 1.3.6.1.4.1.6296.101.4.10.1.1.19
		sleAdvaInfoPDUsTx OBJECT-TYPE
			SYNTAX Integer32
			MAX-ACCESS read-only
			STATUS current
			DESCRIPTION
				"OAM package - aOAMInformationTx. (PDU Performance)Non-resettable, 
				wrapping count of OAM Info PDUs transmitted since OAM enabled."
			::= { sleAdvaOamEntry 19 }

		
--   1.3.6.1.4.1.6296.101.4.10.1.1.20
-- 1.3.6.1.4.1.6296.101.4.10.1.1.20
		-- 1.3.6.1.4.1.6296.101.4.10.1.1.20
		sleAdvaInfoPDUsRx OBJECT-TYPE
			SYNTAX Integer32
			MAX-ACCESS read-only
			STATUS current
			DESCRIPTION
				"OAM package - aOAMInformationRx. (PDU Performance)Non-resettable, 
				wrapping count of OAM Info PDUs received since OAM enabled."
			::= { sleAdvaOamEntry 20 }

		
--   1.3.6.1.4.1.6296.101.4.10.1.1.21
-- 1.3.6.1.4.1.6296.101.4.10.1.1.21
		-- 1.3.6.1.4.1.6296.101.4.10.1.1.21
		sleAdvaEventNotificationPDUsTx OBJECT-TYPE
			SYNTAX Integer32
			MAX-ACCESS read-only
			STATUS current
			DESCRIPTION
				"OAM package - aOAMEventNotificationTx. (PDU Performance)Non-resettable, 
				wrapping count of OAM Event PDUs transmitted since OAM enabled."
			::= { sleAdvaOamEntry 21 }

		
--   1.3.6.1.4.1.6296.101.4.10.1.1.22
-- 1.3.6.1.4.1.6296.101.4.10.1.1.22
		-- 1.3.6.1.4.1.6296.101.4.10.1.1.22
		sleAdvaUniqueEventNotificationPDUsTx OBJECT-TYPE
			SYNTAX Integer32
			MAX-ACCESS read-only
			STATUS current
			DESCRIPTION
				"OAM package - aOAMUniqueEventNotificationTx. (PDU Performance)
				Non-resettable, wrapping count of OAM Event PDUs received with 
				a different sequence number than previously since OAM enabled."
			::= { sleAdvaOamEntry 22 }

		
--   1.3.6.1.4.1.6296.101.4.10.1.1.23
-- 1.3.6.1.4.1.6296.101.4.10.1.1.23
		-- 1.3.6.1.4.1.6296.101.4.10.1.1.23
		sleAdvaDupEventNotificationPDUsTx OBJECT-TYPE
			SYNTAX Integer32
			MAX-ACCESS read-only
			STATUS current
			DESCRIPTION
				"OAM package - aOAMDuplicateEventNotificationTx. (PDU Performance)
				Non-resettable, wrapping count of OAM Event PDUs received with the 
				same sequence number as previously since OAM enabled."
			::= { sleAdvaOamEntry 23 }

		
--   1.3.6.1.4.1.6296.101.4.10.1.1.24
-- 1.3.6.1.4.1.6296.101.4.10.1.1.24
		-- 1.3.6.1.4.1.6296.101.4.10.1.1.24
		sleAdvaLoopbackControlPDUsTx OBJECT-TYPE
			SYNTAX Integer32
			MAX-ACCESS read-only
			STATUS current
			DESCRIPTION
				"OAM package - aOAMLoopbackControlTx. (PDU Performance)
				Non-resettable, wrapping count of OAM Loopback Control PDUs 
				transmitted since OAM enabled."
			::= { sleAdvaOamEntry 24 }

		
--   1.3.6.1.4.1.6296.101.4.10.1.1.25
-- 1.3.6.1.4.1.6296.101.4.10.1.1.25
		-- 1.3.6.1.4.1.6296.101.4.10.1.1.25
		sleAdvaLoopbackControlPDUsRx OBJECT-TYPE
			SYNTAX Integer32
			MAX-ACCESS read-only
			STATUS current
			DESCRIPTION
				"OAM package - aOAMLoopbackControlRx. (PDU Performance)
				Non-resettable, wrapping count of OAM Loopback Control PDUs 
				received since OAM enabled."
			::= { sleAdvaOamEntry 25 }

		
--   1.3.6.1.4.1.6296.101.4.10.1.1.26
-- 1.3.6.1.4.1.6296.101.4.10.1.1.26
		-- 1.3.6.1.4.1.6296.101.4.10.1.1.26
		sleAdvaVariableRequestPDUsTx OBJECT-TYPE
			SYNTAX Integer32
			MAX-ACCESS read-only
			STATUS current
			DESCRIPTION
				"OAM package - aOAMVariableRequestTx. (PDU Performance)
				Non-resettable, wrapping count of OAM Variable Request PDUs 
				transmitted since OAM enabled."
			::= { sleAdvaOamEntry 26 }

		
--   1.3.6.1.4.1.6296.101.4.10.1.1.27
-- 1.3.6.1.4.1.6296.101.4.10.1.1.27
		-- 1.3.6.1.4.1.6296.101.4.10.1.1.27
		sleAdvaVariableRequestPDUsRx OBJECT-TYPE
			SYNTAX Integer32
			MAX-ACCESS read-only
			STATUS current
			DESCRIPTION
				"OAM package - aOAMVariableRequestRx. (PDU Performance)
				Non-resettable, wrapping count of OAM Variable Request PDUs 
				received since OAM enabled."
			::= { sleAdvaOamEntry 27 }

		
--   1.3.6.1.4.1.6296.101.4.10.1.1.28
-- 1.3.6.1.4.1.6296.101.4.10.1.1.28
		-- 1.3.6.1.4.1.6296.101.4.10.1.1.28
		sleAdvaVariableResponsePDUsTx OBJECT-TYPE
			SYNTAX Integer32
			MAX-ACCESS read-only
			STATUS current
			DESCRIPTION
				"OAM package - aOAMVariableResponseTx. (PDU Performance)
				Non-resettable, wrapping count of OAM Variable Response PDUs 
				transmitted since OAM enabled."
			::= { sleAdvaOamEntry 28 }

		
--   1.3.6.1.4.1.6296.101.4.10.1.1.29
-- 1.3.6.1.4.1.6296.101.4.10.1.1.29
		-- 1.3.6.1.4.1.6296.101.4.10.1.1.29
		sleAdvaVariableResponsePDUsRx OBJECT-TYPE
			SYNTAX Integer32
			MAX-ACCESS read-only
			STATUS current
			DESCRIPTION
				"OAM package - aOAMVariableResponseRx. (PDU Performance)
				Non-resettable, wrapping count of OAM Variable Response PDUs 
				received since OAM enabled"
			::= { sleAdvaOamEntry 29 }

		
--   1.3.6.1.4.1.6296.101.4.10.1.1.30
-- 1.3.6.1.4.1.6296.101.4.10.1.1.30
		-- 1.3.6.1.4.1.6296.101.4.10.1.1.30
		sleAdvaVendorPDUsTx OBJECT-TYPE
			SYNTAX Integer32
			MAX-ACCESS read-only
			STATUS current
			DESCRIPTION
				"OAM package - aOAMOrganizationSpecificTx . (PDU Performance)
				Non-resettable, wrapping count of OAM Vendor PDUs transmitted 
				since OAM enabled."
			::= { sleAdvaOamEntry 30 }

		
--   1.3.6.1.4.1.6296.101.4.10.1.1.31
-- 1.3.6.1.4.1.6296.101.4.10.1.1.31
		-- 1.3.6.1.4.1.6296.101.4.10.1.1.31
		sleAdvaVendorPDUsRx OBJECT-TYPE
			SYNTAX Integer32
			MAX-ACCESS read-only
			STATUS current
			DESCRIPTION
				"OAM package - aOAMOrganizationSpecificRx. (PDU Performance)"
			::= { sleAdvaOamEntry 31 }

		
--   1.3.6.1.4.1.6296.101.4.10.1.1.32
-- 1.3.6.1.4.1.6296.101.4.10.1.1.32
		-- 1.3.6.1.4.1.6296.101.4.10.1.1.32
		sleAdvaRemFramesLostDuetoOAMErr OBJECT-TYPE
			SYNTAX Integer32
			MAX-ACCESS read-only
			STATUS current
			DESCRIPTION
				"OAM package - aFramesLostDueToOAMError. (PDU Performance)
				Non-resettable, wrapping count of frames that would have been 
				transmitted but for an OAM sublayer error."
			::= { sleAdvaOamEntry 32 }

		
--   1.3.6.1.4.1.6296.101.4.10.1.1.33
-- 1.3.6.1.4.1.6296.101.4.10.1.1.33
		-- 1.3.6.1.4.1.6296.101.4.10.1.1.33
		sleAdvaLocErrSymbolPeriodEvent OBJECT-TYPE
			SYNTAX Integer32
			MAX-ACCESS read-only
			STATUS current
			DESCRIPTION
				"The most recently transmitted event of this type. (Error)"
			::= { sleAdvaOamEntry 33 }

		
--   1.3.6.1.4.1.6296.101.4.10.1.1.34
-- 1.3.6.1.4.1.6296.101.4.10.1.1.34
		-- 1.3.6.1.4.1.6296.101.4.10.1.1.34
		sleAdvaLocErrFrameSecsEvent OBJECT-TYPE
			SYNTAX Integer32
			MAX-ACCESS read-only
			STATUS current
			DESCRIPTION
				"The most recently transmitted event of this type. (Error)"
			::= { sleAdvaOamEntry 34 }

		
--   1.3.6.1.4.1.6296.101.4.10.1.1.35
-- 1.3.6.1.4.1.6296.101.4.10.1.1.35
		-- 1.3.6.1.4.1.6296.101.4.10.1.1.35
		sleAdvaLocErrFramePeriodEvent OBJECT-TYPE
			SYNTAX Integer32
			MAX-ACCESS read-only
			STATUS current
			DESCRIPTION
				"The most recently transmitted event of this type. (Error)"
			::= { sleAdvaOamEntry 35 }

		
--   1.3.6.1.4.1.6296.101.4.10.1.1.36
-- 1.3.6.1.4.1.6296.101.4.10.1.1.36
		-- 1.3.6.1.4.1.6296.101.4.10.1.1.36
		sleAdvaLocErrFrameSecsSummaryEvent OBJECT-TYPE
			SYNTAX Integer32
			MAX-ACCESS read-only
			STATUS current
			DESCRIPTION
				"The most recently transmitted event of this type. (Error)"
			::= { sleAdvaOamEntry 36 }

		
--   1.3.6.1.4.1.6296.101.4.10.1.1.37
-- 1.3.6.1.4.1.6296.101.4.10.1.1.37
		-- 1.3.6.1.4.1.6296.101.4.10.1.1.37
		sleAdvaRemErrSymbolPeriodEvent OBJECT-TYPE
			SYNTAX Integer32
			MAX-ACCESS read-only
			STATUS current
			DESCRIPTION
				"The most recently received event of this type. (Error)"
			::= { sleAdvaOamEntry 37 }

		
--   1.3.6.1.4.1.6296.101.4.10.1.1.38
-- 1.3.6.1.4.1.6296.101.4.10.1.1.38
		-- 1.3.6.1.4.1.6296.101.4.10.1.1.38
		sleAdvaRemErrFrameSecsEvent OBJECT-TYPE
			SYNTAX Integer32
			MAX-ACCESS read-only
			STATUS current
			DESCRIPTION
				"The most recently received event of this type. (Error)"
			::= { sleAdvaOamEntry 38 }

		
--   1.3.6.1.4.1.6296.101.4.10.1.1.39
-- 1.3.6.1.4.1.6296.101.4.10.1.1.39
		-- 1.3.6.1.4.1.6296.101.4.10.1.1.39
		sleAdvaRemoteErrorFramePeriodEvent OBJECT-TYPE
			SYNTAX Integer32
			MAX-ACCESS read-only
			STATUS current
			DESCRIPTION
				"The most recently received event of this type. (Error)"
			::= { sleAdvaOamEntry 39 }

		
--   1.3.6.1.4.1.6296.101.4.10.1.1.40
-- 1.3.6.1.4.1.6296.101.4.10.1.1.40
		-- 1.3.6.1.4.1.6296.101.4.10.1.1.40
		sleAdvaRemoteErrorFrameSecsSummaryEvent OBJECT-TYPE
			SYNTAX Integer32
			MAX-ACCESS read-only
			STATUS current
			DESCRIPTION
				"The most recently received event of this type. (Error)"
			::= { sleAdvaOamEntry 40 }

		
--   1.3.6.1.4.1.6296.101.4.10.2
-- 1.3.6.1.4.1.6296.101.4.10.2
		-- 1.3.6.1.4.1.6296.101.4.10.2
		sleAdvaOamControl OBJECT IDENTIFIER ::= { sleAdvaOam 2 }

		
--   1.3.6.1.4.1.6296.101.4.10.2.1
-- 1.3.6.1.4.1.6296.101.4.10.2.1
		-- 1.3.6.1.4.1.6296.101.4.10.2.1
		sleAdvaOamControlRequest OBJECT-TYPE
			SYNTAX INTEGER { setAdvaOamProfile(1) }
			MAX-ACCESS read-write
			STATUS current
			DESCRIPTION
				"Description."
			::= { sleAdvaOamControl 1 }

		
--   1.3.6.1.4.1.6296.101.4.10.2.2
-- 1.3.6.1.4.1.6296.101.4.10.2.2
		-- 1.3.6.1.4.1.6296.101.4.10.2.2
		sleAdvaOamControlStatus OBJECT-TYPE
			SYNTAX SleControlStatusType
			MAX-ACCESS read-only
			STATUS current
			DESCRIPTION
				"Description."
			::= { sleAdvaOamControl 2 }

		
--   1.3.6.1.4.1.6296.101.4.10.2.3
-- 1.3.6.1.4.1.6296.101.4.10.2.3
		-- 1.3.6.1.4.1.6296.101.4.10.2.3
		sleAdvaOamControlTimer OBJECT-TYPE
			SYNTAX Gauge32
			MAX-ACCESS read-write
			STATUS current
			DESCRIPTION
				"Description."
			::= { sleAdvaOamControl 3 }

		
--   1.3.6.1.4.1.6296.101.4.10.2.4
-- 1.3.6.1.4.1.6296.101.4.10.2.4
		-- 1.3.6.1.4.1.6296.101.4.10.2.4
		sleAdvaOamControlTimeStamp OBJECT-TYPE
			SYNTAX TimeTicks
			MAX-ACCESS read-write
			STATUS current
			DESCRIPTION
				"Description."
			::= { sleAdvaOamControl 4 }

		
--   1.3.6.1.4.1.6296.101.4.10.2.5
-- 1.3.6.1.4.1.6296.101.4.10.2.5
		-- 1.3.6.1.4.1.6296.101.4.10.2.5
		sleAdvaOamControlReqResult OBJECT-TYPE
			SYNTAX SleControlRequestResultType
			MAX-ACCESS read-write
			STATUS current
			DESCRIPTION
				"Description."
			::= { sleAdvaOamControl 5 }

		
--   1.3.6.1.4.1.6296.101.4.10.2.6
-- 1.3.6.1.4.1.6296.101.4.10.2.6
		-- 1.3.6.1.4.1.6296.101.4.10.2.6
		sleAdvaOamControlPortIndex OBJECT-TYPE
			SYNTAX INTEGER (1..255)
			MAX-ACCESS read-write
			STATUS current
			DESCRIPTION
				"Description."
			::= { sleAdvaOamControl 6 }

		
--   1.3.6.1.4.1.6296.101.4.10.2.7
-- 1.3.6.1.4.1.6296.101.4.10.2.7
		-- 1.3.6.1.4.1.6296.101.4.10.2.7
		sleAdvaOamControlRemInstance OBJECT-TYPE
			SYNTAX INTEGER (1..2)
			MAX-ACCESS read-write
			STATUS current
			DESCRIPTION
				"Description."
			::= { sleAdvaOamControl 7 }

		
--   1.3.6.1.4.1.6296.101.4.10.2.8
-- 1.3.6.1.4.1.6296.101.4.10.2.8
		-- 1.3.6.1.4.1.6296.101.4.10.2.8
		sleAdvaOamControlAdminStatus OBJECT-TYPE
			SYNTAX INTEGER
				{
				disable(0),
				enable(1)
				}
			MAX-ACCESS read-write
			STATUS current
			DESCRIPTION
				"Description."
			::= { sleAdvaOamControl 8 }

		
--   1.3.6.1.4.1.6296.101.4.10.2.9
-- 1.3.6.1.4.1.6296.101.4.10.2.9
		-- 1.3.6.1.4.1.6296.101.4.10.2.9
		sleAdvaOamControlMode OBJECT-TYPE
			SYNTAX INTEGER
				{
				passive(0),
				active(1)
				}
			MAX-ACCESS read-write
			STATUS current
			DESCRIPTION
				"Description."
			::= { sleAdvaOamControl 9 }

		
--   1.3.6.1.4.1.6296.101.4.10.3
-- 1.3.6.1.4.1.6296.101.4.10.3
		-- 1.3.6.1.4.1.6296.101.4.10.3
		sleAdvaOamNotification OBJECT IDENTIFIER ::= { sleAdvaOam 3 }

		
--   1.3.6.1.4.1.6296.101.4.10.3.1
-- 1.3.6.1.4.1.6296.101.4.10.3.1
		-- 1.3.6.1.4.1.6296.101.4.10.3.1
		setAdvaOamProfileChanged NOTIFICATION-TYPE
			OBJECTS { sleAdvaOamControlRequest, sleAdvaOamControlReqResult, sleAdvaOamControlTimeStamp, sleAdvaAdminStatus, sleAdvaMode
				 }
			STATUS current
			DESCRIPTION 
				"Description."
			::= { sleAdvaOamNotification 1 }

		
--   1.3.6.1.4.1.6296.101.4.11
-- 1.3.6.1.4.1.6296.101.4.11
		-- 1.3.6.1.4.1.6296.101.4.11
		sleAlarmLED OBJECT IDENTIFIER ::= { sleFaultMgmt 11 }

		
--   1.3.6.1.4.1.6296.101.4.11.1
-- 1.3.6.1.4.1.6296.101.4.11.1
		-- 1.3.6.1.4.1.6296.101.4.11.1
		sleAlarmLEDTable OBJECT-TYPE
			SYNTAX SEQUENCE OF SleAlarmLEDEntry
			MAX-ACCESS not-accessible
			STATUS current
			DESCRIPTION
				"Description."
			::= { sleAlarmLED 1 }

		
--   1.3.6.1.4.1.6296.101.4.11.1.1
-- 1.3.6.1.4.1.6296.101.4.11.1.1
		-- 1.3.6.1.4.1.6296.101.4.11.1.1
		sleAlarmLEDEntry OBJECT-TYPE
			SYNTAX SleAlarmLEDEntry
			MAX-ACCESS not-accessible
			STATUS current
			DESCRIPTION
				"Description."
			INDEX { sleAlarmLEDType }
			::= { sleAlarmLEDTable 1 }

		
		SleAlarmLEDEntry ::=
			SEQUENCE { 
				sleAlarmLEDType
					INTEGER,
				sleAlarmLEDStatus
					INTEGER,
				sleAlarmLEDLevel
					INTEGER
			 }

--   1.3.6.1.4.1.6296.101.4.11.1.1.1
-- 1.3.6.1.4.1.6296.101.4.11.1.1.1
		-- 1.3.6.1.4.1.6296.101.4.11.1.1.1
		sleAlarmLEDType OBJECT-TYPE
			SYNTAX INTEGER
				{
				fanFail(1),
				fanRemove(2),
				memoryOver(3),
				moduleRemove(4),
				portLinkDown(5),
				portRemove(6),
				portThreadOver(7),
				powerFail(8),
				powerRemove(9),
				temperatureHigh(10)
				}
			MAX-ACCESS read-only
			STATUS current
			DESCRIPTION
				"The alarm that LED indicate."
			::= { sleAlarmLEDEntry 1 }

		
--   1.3.6.1.4.1.6296.101.4.11.1.1.2
-- 1.3.6.1.4.1.6296.101.4.11.1.1.2
		-- 1.3.6.1.4.1.6296.101.4.11.1.1.2
		sleAlarmLEDStatus OBJECT-TYPE
			SYNTAX INTEGER
				{
				enable(1),
				disable(2),
				unknown(255)
				}
			MAX-ACCESS read-only
			STATUS current
			DESCRIPTION
				"The status of alarm LED."
			::= { sleAlarmLEDEntry 2 }

		
--   1.3.6.1.4.1.6296.101.4.11.1.1.3
-- 1.3.6.1.4.1.6296.101.4.11.1.1.3
		-- 1.3.6.1.4.1.6296.101.4.11.1.1.3
		sleAlarmLEDLevel OBJECT-TYPE
			SYNTAX INTEGER
				{
				critical(1),
				major(2),
				minor(3),
				unrated(255)
				}
			MAX-ACCESS read-only
			STATUS current
			DESCRIPTION
				"The Level of alarm LED."
			::= { sleAlarmLEDEntry 3 }

		
--   1.3.6.1.4.1.6296.101.4.11.2
-- 1.3.6.1.4.1.6296.101.4.11.2
		-- 1.3.6.1.4.1.6296.101.4.11.2
		sleAlarmLEDLevelTable OBJECT-TYPE
			SYNTAX SEQUENCE OF SleAlarmLEDLevelEntry
			MAX-ACCESS not-accessible
			STATUS current
			DESCRIPTION
				"Description."
			::= { sleAlarmLED 2 }

		
--   1.3.6.1.4.1.6296.101.4.11.2.1
-- 1.3.6.1.4.1.6296.101.4.11.2.1
		-- 1.3.6.1.4.1.6296.101.4.11.2.1
		sleAlarmLEDLevelEntry OBJECT-TYPE
			SYNTAX SleAlarmLEDLevelEntry
			MAX-ACCESS not-accessible
			STATUS current
			DESCRIPTION
				"Description."
			INDEX { sleAlarmLEDLevelIndex }
			::= { sleAlarmLEDLevelTable 1 }

		
		SleAlarmLEDLevelEntry ::=
			SEQUENCE { 
				sleAlarmLEDLevelIndex
					INTEGER,
				sleAlarmLEDLevelBlock
					INTEGER,
				sleAlarmLEDLevelOperStatus
					INTEGER
			 }

--   1.3.6.1.4.1.6296.101.4.11.2.1.1
-- 1.3.6.1.4.1.6296.101.4.11.2.1.1
		-- 1.3.6.1.4.1.6296.101.4.11.2.1.1
		sleAlarmLEDLevelIndex OBJECT-TYPE
			SYNTAX INTEGER
				{
				critical(1),
				major(2),
				minor(3),
				error(4),
				unrated(255)
				}
			MAX-ACCESS read-only
			STATUS current
			DESCRIPTION
				"LED level index."
			::= { sleAlarmLEDLevelEntry 1 }

		
--   1.3.6.1.4.1.6296.101.4.11.2.1.2
-- 1.3.6.1.4.1.6296.101.4.11.2.1.2
		-- 1.3.6.1.4.1.6296.101.4.11.2.1.2
		sleAlarmLEDLevelBlock OBJECT-TYPE
			SYNTAX INTEGER
				{
				unblock(1),
				block(2),
				unknown(255)
				}
			MAX-ACCESS read-only
			STATUS current
			DESCRIPTION
				"LED level block."
			::= { sleAlarmLEDLevelEntry 2 }

		
--   1.3.6.1.4.1.6296.101.4.11.2.1.3
-- 1.3.6.1.4.1.6296.101.4.11.2.1.3
		-- 1.3.6.1.4.1.6296.101.4.11.2.1.3
		sleAlarmLEDLevelOperStatus OBJECT-TYPE
			SYNTAX INTEGER
				{
				on(1),
				off(2)
				}
			MAX-ACCESS read-only
			STATUS current
			DESCRIPTION
				"Alarm current operation status."
			::= { sleAlarmLEDLevelEntry 3 }

		
--   1.3.6.1.4.1.6296.101.4.11.3
-- 1.3.6.1.4.1.6296.101.4.11.3
		-- 1.3.6.1.4.1.6296.101.4.11.3
		sleAlarmLEDControl OBJECT IDENTIFIER ::= { sleAlarmLED 3 }

		
--   1.3.6.1.4.1.6296.101.4.11.3.1
-- 1.3.6.1.4.1.6296.101.4.11.3.1
		-- 1.3.6.1.4.1.6296.101.4.11.3.1
		sleAlarmLEDControlRequest OBJECT-TYPE
			SYNTAX INTEGER
				{
				alarmLedOff(1),
				setAlarmLedLevel(2),
				clearAlarmLed(3),
				alarmLedBlock(4)
				}
			MAX-ACCESS read-write
			STATUS current
			DESCRIPTION
				"Description."
			::= { sleAlarmLEDControl 1 }

		
--   1.3.6.1.4.1.6296.101.4.11.3.2
-- 1.3.6.1.4.1.6296.101.4.11.3.2
		-- 1.3.6.1.4.1.6296.101.4.11.3.2
		sleAlarmLEDControlStatus OBJECT-TYPE
			SYNTAX SleControlStatusType
			MAX-ACCESS read-only
			STATUS current
			DESCRIPTION
				"Description."
			::= { sleAlarmLEDControl 2 }

		
--   1.3.6.1.4.1.6296.101.4.11.3.3
-- 1.3.6.1.4.1.6296.101.4.11.3.3
		-- 1.3.6.1.4.1.6296.101.4.11.3.3
		sleAlarmLEDControlTimer OBJECT-TYPE
			SYNTAX Gauge32
			MAX-ACCESS read-write
			STATUS current
			DESCRIPTION
				"Description."
			::= { sleAlarmLEDControl 3 }

		
--   1.3.6.1.4.1.6296.101.4.11.3.4
-- 1.3.6.1.4.1.6296.101.4.11.3.4
		-- 1.3.6.1.4.1.6296.101.4.11.3.4
		sleAlarmLEDControlTimeStamp OBJECT-TYPE
			SYNTAX TimeTicks
			MAX-ACCESS read-only
			STATUS current
			DESCRIPTION
				"Description."
			::= { sleAlarmLEDControl 4 }

		
--   1.3.6.1.4.1.6296.101.4.11.3.5
-- 1.3.6.1.4.1.6296.101.4.11.3.5
		-- 1.3.6.1.4.1.6296.101.4.11.3.5
		sleAlarmLEDControlReqResult OBJECT-TYPE
			SYNTAX SleControlRequestResultType
			MAX-ACCESS read-only
			STATUS current
			DESCRIPTION
				"Description."
			::= { sleAlarmLEDControl 5 }

		
--   1.3.6.1.4.1.6296.101.4.11.3.6
-- 1.3.6.1.4.1.6296.101.4.11.3.6
		-- 1.3.6.1.4.1.6296.101.4.11.3.6
		sleAlarmLEDControlType OBJECT-TYPE
			SYNTAX INTEGER
				{
				fanFail(1),
				fanRemove(2),
				memoryOver(3),
				moduleRemove(4),
				portLinkDown(5),
				portRemove(6),
				portThreadOver(7),
				powerFail(8),
				powerRemove(9),
				temperatureHigh(10)
				}
			MAX-ACCESS read-write
			STATUS current
			DESCRIPTION
				"The alarm that LED indicate."
			::= { sleAlarmLEDControl 6 }

		
--   1.3.6.1.4.1.6296.101.4.11.3.7
-- 1.3.6.1.4.1.6296.101.4.11.3.7
		-- 1.3.6.1.4.1.6296.101.4.11.3.7
		sleAlarmLEDControlLevel OBJECT-TYPE
			SYNTAX INTEGER
				{
				critical(1),
				major(2),
				minor(3),
				all(254)
				}
			MAX-ACCESS read-write
			STATUS current
			DESCRIPTION
				"The Level of alarm LED."
			::= { sleAlarmLEDControl 7 }

		
--   1.3.6.1.4.1.6296.101.4.11.3.8
-- 1.3.6.1.4.1.6296.101.4.11.3.8
		-- 1.3.6.1.4.1.6296.101.4.11.3.8
		sleAlarmLEDControlBlock OBJECT-TYPE
			SYNTAX INTEGER
				{
				unblock(1),
				block(2)
				}
			MAX-ACCESS read-write
			STATUS current
			DESCRIPTION
				"LED level block."
			::= { sleAlarmLEDControl 8 }

		
--   1.3.6.1.4.1.6296.101.4.11.4
-- 1.3.6.1.4.1.6296.101.4.11.4
		-- 1.3.6.1.4.1.6296.101.4.11.4
		sleAlarmLEDNotification OBJECT IDENTIFIER ::= { sleAlarmLED 4 }

		
--   1.3.6.1.4.1.6296.101.4.11.4.1
-- 1.3.6.1.4.1.6296.101.4.11.4.1
		-- 1.3.6.1.4.1.6296.101.4.11.4.1
		sleAlarmLEDOffChanged NOTIFICATION-TYPE
			OBJECTS { sleAlarmLEDControlRequest, sleAlarmLEDControlTimeStamp, sleAlarmLEDControlReqResult, sleAlarmLEDControlLevel }
			STATUS current
			DESCRIPTION 
				"Description."
			::= { sleAlarmLEDNotification 1 }

		
--   1.3.6.1.4.1.6296.101.4.11.4.2
-- 1.3.6.1.4.1.6296.101.4.11.4.2
		-- 1.3.6.1.4.1.6296.101.4.11.4.2
		sleAlarmLEDLevelChanged NOTIFICATION-TYPE
			OBJECTS { sleAlarmLEDControlRequest, sleAlarmLEDControlTimeStamp, sleAlarmLEDControlReqResult, sleAlarmLEDControlType, sleAlarmLEDControlLevel
				 }
			STATUS current
			DESCRIPTION 
				"Description."
			::= { sleAlarmLEDNotification 2 }

		
--   1.3.6.1.4.1.6296.101.4.11.4.3
-- 1.3.6.1.4.1.6296.101.4.11.4.3
		-- 1.3.6.1.4.1.6296.101.4.11.4.3
		sleAlarmLEDCleared NOTIFICATION-TYPE
			OBJECTS { sleAlarmLEDControlRequest, sleAlarmLEDControlTimeStamp, sleAlarmLEDControlReqResult, sleAlarmLEDControlType }
			STATUS current
			DESCRIPTION 
				"Description."
			::= { sleAlarmLEDNotification 3 }

		
--   1.3.6.1.4.1.6296.101.4.11.4.4
-- 1.3.6.1.4.1.6296.101.4.11.4.4
		-- 1.3.6.1.4.1.6296.101.4.11.4.4
		sleAlarmLEDBlockChanged NOTIFICATION-TYPE
			OBJECTS { sleAlarmLEDControlRequest, sleAlarmLEDControlTimeStamp, sleAlarmLEDControlReqResult, sleAlarmLEDControlLevel, sleAlarmLEDControlBlock
				 }
			STATUS current
			DESCRIPTION 
				"Description."
			::= { sleAlarmLEDNotification 4 }

		
--   1.3.6.1.4.1.6296.101.4.12
-- 1.3.6.1.4.1.6296.101.4.12
		-- 1.3.6.1.4.1.6296.101.4.12
		sleY1731Oam OBJECT IDENTIFIER ::= { sleFaultMgmt 12 }

		
--   1.3.6.1.4.1.6296.101.4.12.1
-- 1.3.6.1.4.1.6296.101.4.12.1
		-- 1.3.6.1.4.1.6296.101.4.12.1
		sleY1731Base OBJECT IDENTIFIER ::= { sleY1731Oam 1 }

		
--   1.3.6.1.4.1.6296.101.4.12.1.1
-- 1.3.6.1.4.1.6296.101.4.12.1.1
		-- 1.3.6.1.4.1.6296.101.4.12.1.1
		sleY1731BaseGroup OBJECT IDENTIFIER ::= { sleY1731Base 1 }

		
--   1.3.6.1.4.1.6296.101.4.12.1.1.1
-- 1.3.6.1.4.1.6296.101.4.12.1.1.1
		-- 1.3.6.1.4.1.6296.101.4.12.1.1.1
		sleY1731Enable OBJECT-TYPE
			SYNTAX INTEGER
				{
				disable(0),
				enable(1)
				}
			MAX-ACCESS read-only
			STATUS current
			DESCRIPTION
				"Enables/Ddisables ITU-T Y.1731 OAM function"
			::= { sleY1731BaseGroup 1 }

		
--   1.3.6.1.4.1.6296.101.4.12.1.1.2
-- 1.3.6.1.4.1.6296.101.4.12.1.1.2
		-- 1.3.6.1.4.1.6296.101.4.12.1.1.2
		sleY1731TrunkEnable OBJECT-TYPE
			SYNTAX INTEGER
				{
				disable(0),
				enable(1)
				}
			MAX-ACCESS read-only
			STATUS current
			DESCRIPTION
				"Enables/Disables Y.1731 OAM on a trunk port"
			::= { sleY1731BaseGroup 2 }

		
--   1.3.6.1.4.1.6296.101.4.12.1.1.3
-- 1.3.6.1.4.1.6296.101.4.12.1.1.3
		-- 1.3.6.1.4.1.6296.101.4.12.1.1.3
		sleY1731LtrCacheHoldTime OBJECT-TYPE
			SYNTAX Integer32 (1..65535)
			MAX-ACCESS read-only
			STATUS current
			DESCRIPTION
				"Indicates the time that cache entries will be retained"
			::= { sleY1731BaseGroup 3 }

		
--   1.3.6.1.4.1.6296.101.4.12.1.1.4
-- 1.3.6.1.4.1.6296.101.4.12.1.1.4
		-- 1.3.6.1.4.1.6296.101.4.12.1.1.4
		sleY1731LtrCacheSize OBJECT-TYPE
			SYNTAX Integer32 (1..4095)
			MAX-ACCESS read-only
			STATUS current
			DESCRIPTION
				"Indicates the number of entries in the traceroute cache"
			::= { sleY1731BaseGroup 4 }

		
--   1.3.6.1.4.1.6296.101.4.12.1.1.5
-- 1.3.6.1.4.1.6296.101.4.12.1.1.5
		-- 1.3.6.1.4.1.6296.101.4.12.1.1.5
		sleY1731SnmpServerTraps OBJECT-TYPE
			SYNTAX BITS
				{
				rdi(0),
				loc(1),
				unp(2),
				unm(3),
				mmg(4),
				unl(5),
				ais(6),
				lck(7)
				}
			MAX-ACCESS read-only
			STATUS current
			DESCRIPTION
				"Indicates the SNMP traps"
			::= { sleY1731BaseGroup 5 }

		
--   1.3.6.1.4.1.6296.101.4.12.1.1.6
-- 1.3.6.1.4.1.6296.101.4.12.1.1.6
		-- 1.3.6.1.4.1.6296.101.4.12.1.1.6
		sleY1731XcheckStartDelay OBJECT-TYPE
			SYNTAX Integer32 (1..65535)
			MAX-ACCESS read-only
			STATUS current
			DESCRIPTION
				"Indicates the delay before the cross-check is started"
			::= { sleY1731BaseGroup 6 }

		
--   1.3.6.1.4.1.6296.101.4.12.1.1.7
-- 1.3.6.1.4.1.6296.101.4.12.1.1.7
		-- 1.3.6.1.4.1.6296.101.4.12.1.1.7
		sleY1731DefaultMegLevel OBJECT-TYPE
			SYNTAX Integer32 (0..7)
			MAX-ACCESS read-only
			STATUS current
			DESCRIPTION
				"Indicates the level to be created dynamic MHF"
			::= { sleY1731BaseGroup 7 }

		
--   1.3.6.1.4.1.6296.101.4.12.1.1.8
-- 1.3.6.1.4.1.6296.101.4.12.1.1.8
		-- 1.3.6.1.4.1.6296.101.4.12.1.1.8
		sleY1731DefaultMegMhfCreation OBJECT-TYPE
			SYNTAX INTEGER
				{
				none(0),
				default(1),
				explicit(2)
				}
			MAX-ACCESS read-only
			STATUS current
			DESCRIPTION
				"Indicates the mode of MHF creation"
			::= { sleY1731BaseGroup 8 }

		
--   1.3.6.1.4.1.6296.101.4.12.1.1.9
-- 1.3.6.1.4.1.6296.101.4.12.1.1.9
		-- 1.3.6.1.4.1.6296.101.4.12.1.1.9
		sleY1731PduToCfm OBJECT-TYPE
			SYNTAX INTEGER
				{
				disable(0),
				enable(1)
				}
			MAX-ACCESS read-only
			STATUS current
			DESCRIPTION
				"Enables/Disables changing from Y.1731 PDU format to CFM PDU format"
			::= { sleY1731BaseGroup 9 }

		
--   1.3.6.1.4.1.6296.101.4.12.1.1.10
-- 1.3.6.1.4.1.6296.101.4.12.1.1.10
		-- 1.3.6.1.4.1.6296.101.4.12.1.1.10
		sleY1731DedicatedVlan OBJECT-TYPE
			SYNTAX INTEGER
				{
				disable(0),
				enable(1)
				}
			MAX-ACCESS read-write
			STATUS current
			DESCRIPTION
				"Description."
			::= { sleY1731BaseGroup 10 }

		
--   1.3.6.1.4.1.6296.101.4.12.1.1.11
-- 1.3.6.1.4.1.6296.101.4.12.1.1.11
		-- 1.3.6.1.4.1.6296.101.4.12.1.1.11
		sleY1731RmepCreation OBJECT-TYPE
			SYNTAX INTEGER
				{
				dynamic(1),
				static(2)
				}
			MAX-ACCESS read-only
			STATUS current
			DESCRIPTION
				"RMEP creation mode"
			::= { sleY1731BaseGroup 11 }

		
--   1.3.6.1.4.1.6296.101.4.12.1.1.12
-- 1.3.6.1.4.1.6296.101.4.12.1.1.12
		-- 1.3.6.1.4.1.6296.101.4.12.1.1.12
		sleY1731CCIgnoreDefect OBJECT-TYPE
			SYNTAX INTEGER
				{
				disable(0),
				enable(1)
				}
			MAX-ACCESS read-only
			STATUS current
			DESCRIPTION
				"CC Ignore Defect Mode"
			::= { sleY1731BaseGroup 12 }

		
--   1.3.6.1.4.1.6296.101.4.12.1.1.13
-- 1.3.6.1.4.1.6296.101.4.12.1.1.13
		-- 1.3.6.1.4.1.6296.101.4.12.1.1.13
		sleY1731RapsFloodingBlock OBJECT-TYPE
			SYNTAX INTEGER
				{
				disable(0),
				enable(1)
				}
			MAX-ACCESS read-only
			STATUS current
			DESCRIPTION
				"R-APS Flooding Block Mode"
			::= { sleY1731BaseGroup 13 }

		
--   1.3.6.1.4.1.6296.101.4.12.1.1.14
-- 1.3.6.1.4.1.6296.101.4.12.1.1.14
		-- 1.3.6.1.4.1.6296.101.4.12.1.1.14
		sleY1731TlvPermission OBJECT-TYPE
			SYNTAX INTEGER
				{
				none(1),
				chassis(2)
				}
			MAX-ACCESS read-only
			STATUS current
			DESCRIPTION
				"Indicates TLV Permission"
			::= { sleY1731BaseGroup 14 }

		
--   1.3.6.1.4.1.6296.101.4.12.1.2
-- 1.3.6.1.4.1.6296.101.4.12.1.2
		-- 1.3.6.1.4.1.6296.101.4.12.1.2
		sleY1731BaseControl OBJECT IDENTIFIER ::= { sleY1731Base 2 }

		
--   1.3.6.1.4.1.6296.101.4.12.1.2.1
-- 1.3.6.1.4.1.6296.101.4.12.1.2.1
		-- 1.3.6.1.4.1.6296.101.4.12.1.2.1
		sleY1731BaseControlRequest OBJECT-TYPE
			SYNTAX INTEGER
				{
				setY1731Enable(1),
				setY1731TrunkEnable(2),
				setY1731LtrCacheProfile(3),
				setY1731SnmpProfile(4),
				setY1731XcheckProfile(5),
				setY1731DefaultMegProfile(6),
				setY1731PduToCfm(7),
				setY1731DedicatedVlan(8),
				destroyMipCcdb(9),
				destroyLtrCache(10),
				setRmepCreation(11),
				setTrunkOamstatus(12),
				setY1731CCIgnoreDefect(13),
				setY1731RapsFloodingBlock(14),
				setY1731TlvPermission(15)
				}
			MAX-ACCESS read-write
			STATUS current
			DESCRIPTION
				" This attribute identifies the control commands.
				updateAlarmList:
				   the NE updates entries of alarms in the sleAlarmListTable
				   after having changed alarm severities of alarms 
				   (due to change profile pointers in
				   managed entities or after modification of alarm severities 
				   in profiles). This command should be applied once after having 
				   finisled modifications of severties.
				modifyAlarmSeverity: 
				   modifies the severity of an alarm in specific profile.
				createAlarmSeverityProfile: 
				   creates a new profile with default severities.
				   The severities then have to be modified with command changeAlarmSeverity.
				deleteAlarmSeverityProfile: 
				   deletes a profile. Profile 1 is not allowed to be deleted.
				 
				Notifications : none "
			::= { sleY1731BaseControl 1 }

		
--   1.3.6.1.4.1.6296.101.4.12.1.2.2
-- 1.3.6.1.4.1.6296.101.4.12.1.2.2
		-- 1.3.6.1.4.1.6296.101.4.12.1.2.2
		sleY1731BaseControlStatus OBJECT-TYPE
			SYNTAX SleControlStatusType
			MAX-ACCESS read-only
			STATUS current
			DESCRIPTION
				" The status of a control request. "
			::= { sleY1731BaseControl 2 }

		
--   1.3.6.1.4.1.6296.101.4.12.1.2.3
-- 1.3.6.1.4.1.6296.101.4.12.1.2.3
		-- 1.3.6.1.4.1.6296.101.4.12.1.2.3
		sleY1731BaseControlTimer OBJECT-TYPE
			SYNTAX Gauge32
			MAX-ACCESS read-write
			STATUS current
			DESCRIPTION
				" The maximum wait time for the manager for command ending.
				For long running commands.
				The manager reads this value from the DSLAM. "
			::= { sleY1731BaseControl 3 }

		
--   1.3.6.1.4.1.6296.101.4.12.1.2.4
-- 1.3.6.1.4.1.6296.101.4.12.1.2.4
		-- 1.3.6.1.4.1.6296.101.4.12.1.2.4
		sleY1731BaseControlTimeStamp OBJECT-TYPE
			SYNTAX TimeTicks
			MAX-ACCESS read-only
			STATUS current
			DESCRIPTION
				" The time stamp of the last command (end of command). "
			::= { sleY1731BaseControl 4 }

		
--   1.3.6.1.4.1.6296.101.4.12.1.2.5
-- 1.3.6.1.4.1.6296.101.4.12.1.2.5
		-- 1.3.6.1.4.1.6296.101.4.12.1.2.5
		sleY1731BaseControlReqResult OBJECT-TYPE
			SYNTAX SleControlRequestResultType
			MAX-ACCESS read-only
			STATUS current
			DESCRIPTION
				" The result of the last user command. "
			::= { sleY1731BaseControl 5 }

		
--   1.3.6.1.4.1.6296.101.4.12.1.2.6
-- 1.3.6.1.4.1.6296.101.4.12.1.2.6
		-- 1.3.6.1.4.1.6296.101.4.12.1.2.6
		sleY1731BaseControlEnable OBJECT-TYPE
			SYNTAX INTEGER
				{
				disable(0),
				enable(1)
				}
			MAX-ACCESS read-write
			STATUS current
			DESCRIPTION
				"Enables/Ddisables ITU-T Y.1731 OAM function"
			::= { sleY1731BaseControl 6 }

		
--   1.3.6.1.4.1.6296.101.4.12.1.2.7
-- 1.3.6.1.4.1.6296.101.4.12.1.2.7
		-- 1.3.6.1.4.1.6296.101.4.12.1.2.7
		sleY1731BaseControlTrunkEnable OBJECT-TYPE
			SYNTAX INTEGER
				{
				disable(0),
				enable(1)
				}
			MAX-ACCESS read-write
			STATUS current
			DESCRIPTION
				"Enables/Disables Y.1731 OAM on a trunk port"
			::= { sleY1731BaseControl 7 }

		
--   1.3.6.1.4.1.6296.101.4.12.1.2.8
-- 1.3.6.1.4.1.6296.101.4.12.1.2.8
		-- 1.3.6.1.4.1.6296.101.4.12.1.2.8
		sleY1731BaseControlLtrCacheHoldTime OBJECT-TYPE
			SYNTAX Integer32 (1..65535)
			MAX-ACCESS read-write
			STATUS current
			DESCRIPTION
				"Indicates the time that cache entries will be retained"
			::= { sleY1731BaseControl 8 }

		
--   1.3.6.1.4.1.6296.101.4.12.1.2.9
-- 1.3.6.1.4.1.6296.101.4.12.1.2.9
		-- 1.3.6.1.4.1.6296.101.4.12.1.2.9
		sleY1731BaseControlLtrCacheSize OBJECT-TYPE
			SYNTAX Integer32 (1..4095)
			MAX-ACCESS read-write
			STATUS current
			DESCRIPTION
				"Indicates the number of entries in the traceroute cache"
			::= { sleY1731BaseControl 9 }

		
--   1.3.6.1.4.1.6296.101.4.12.1.2.10
-- 1.3.6.1.4.1.6296.101.4.12.1.2.10
		-- 1.3.6.1.4.1.6296.101.4.12.1.2.10
		sleY1731BaseControlSnmpServerTraps OBJECT-TYPE
			SYNTAX BITS
				{
				rdi(0),
				loc(1),
				unp(2),
				unm(3),
				mmg(4),
				unl(5),
				ais(6),
				lck(7)
				}
			MAX-ACCESS read-write
			STATUS current
			DESCRIPTION
				"Indicates the SNMP traps"
			::= { sleY1731BaseControl 10 }

		
--   1.3.6.1.4.1.6296.101.4.12.1.2.11
-- 1.3.6.1.4.1.6296.101.4.12.1.2.11
		-- 1.3.6.1.4.1.6296.101.4.12.1.2.11
		sleY1731BaseControlXcheckStartDelay OBJECT-TYPE
			SYNTAX Integer32 (1..65535)
			MAX-ACCESS read-write
			STATUS current
			DESCRIPTION
				"Indicates the delay before the cross-check is started"
			::= { sleY1731BaseControl 11 }

		
--   1.3.6.1.4.1.6296.101.4.12.1.2.12
-- 1.3.6.1.4.1.6296.101.4.12.1.2.12
		-- 1.3.6.1.4.1.6296.101.4.12.1.2.12
		sleY1731BaseControlDefaultMegLevel OBJECT-TYPE
			SYNTAX Integer32 (0..7)
			MAX-ACCESS read-write
			STATUS current
			DESCRIPTION
				"Indicates the level to be created dynamic MHF"
			::= { sleY1731BaseControl 12 }

		
--   1.3.6.1.4.1.6296.101.4.12.1.2.13
-- 1.3.6.1.4.1.6296.101.4.12.1.2.13
		-- 1.3.6.1.4.1.6296.101.4.12.1.2.13
		sleY1731BaseControlDefaultMegMhfCreation OBJECT-TYPE
			SYNTAX INTEGER
				{
				none(0),
				default(1),
				explicit(2)
				}
			MAX-ACCESS read-write
			STATUS current
			DESCRIPTION
				"Indicates the mode of MHF creation"
			::= { sleY1731BaseControl 13 }

		
--   1.3.6.1.4.1.6296.101.4.12.1.2.14
-- 1.3.6.1.4.1.6296.101.4.12.1.2.14
		-- 1.3.6.1.4.1.6296.101.4.12.1.2.14
		sleY1731BaseControlPduToCfm OBJECT-TYPE
			SYNTAX INTEGER
				{
				disable(0),
				enable(1)
				}
			MAX-ACCESS read-write
			STATUS current
			DESCRIPTION
				"Description."
			::= { sleY1731BaseControl 14 }

		
--   Enables/Disables changing from Y.1731 PDU format to CFM PDU format
-- 1.3.6.1.4.1.6296.101.4.12.1.2.15
-- 1.3.6.1.4.1.6296.101.4.12.1.2.15
		-- 1.3.6.1.4.1.6296.101.4.12.1.2.15
		sleY1731BaseControlDedicatedVlan OBJECT-TYPE
			SYNTAX INTEGER
				{
				disable(0),
				enable(1)
				}
			MAX-ACCESS read-write
			STATUS current
			DESCRIPTION
				"Description."
			::= { sleY1731BaseControl 15 }

		
--   1.3.6.1.4.1.6296.101.4.12.1.2.16
-- 1.3.6.1.4.1.6296.101.4.12.1.2.16
		-- 1.3.6.1.4.1.6296.101.4.12.1.2.16
		sleY1731BaseControlRmepCreation OBJECT-TYPE
			SYNTAX INTEGER
				{
				dynamic(1),
				static(2)
				}
			MAX-ACCESS read-write
			STATUS current
			DESCRIPTION
				"RMEP creation mode"
			::= { sleY1731BaseControl 16 }

		
--   1.3.6.1.4.1.6296.101.4.12.1.2.17
-- 1.3.6.1.4.1.6296.101.4.12.1.2.17
		-- 1.3.6.1.4.1.6296.101.4.12.1.2.17
		sleY1731BaseControlTrunkIndex OBJECT-TYPE
			SYNTAX INTEGER (1..65535)
			MAX-ACCESS read-write
			STATUS current
			DESCRIPTION
				"Trunk Index"
			::= { sleY1731BaseControl 17 }

		
--   1.3.6.1.4.1.6296.101.4.12.1.2.18
-- 1.3.6.1.4.1.6296.101.4.12.1.2.18
		-- 1.3.6.1.4.1.6296.101.4.12.1.2.18
		sleY1731BaseControlTrunkOamStatus OBJECT-TYPE
			SYNTAX INTEGER
				{
				disable(0),
				enable(1)
				}
			MAX-ACCESS read-write
			STATUS current
			DESCRIPTION
				"OAM status per each Trunk port."
			::= { sleY1731BaseControl 18 }

		
--   1.3.6.1.4.1.6296.101.4.12.1.2.19
-- 1.3.6.1.4.1.6296.101.4.12.1.2.19
		-- 1.3.6.1.4.1.6296.101.4.12.1.2.19
		sleY1731BaseControlTrunkMeg OBJECT-TYPE
			SYNTAX OCTET STRING
			MAX-ACCESS read-write
			STATUS current
			DESCRIPTION
				"trunk port meg name."
			::= { sleY1731BaseControl 19 }

		
--   1.3.6.1.4.1.6296.101.4.12.1.2.20
-- 1.3.6.1.4.1.6296.101.4.12.1.2.20
		-- 1.3.6.1.4.1.6296.101.4.12.1.2.20
		sleY1731BaseControlCCIgnoreDefect OBJECT-TYPE
			SYNTAX INTEGER
				{
				disable(0),
				enable(1)
				}
			MAX-ACCESS read-write
			STATUS current
			DESCRIPTION
				"CC Ignore Defect Mode"
			::= { sleY1731BaseControl 20 }

		
--   1.3.6.1.4.1.6296.101.4.12.1.2.21
-- 1.3.6.1.4.1.6296.101.4.12.1.2.21
		-- 1.3.6.1.4.1.6296.101.4.12.1.2.21
		sleY1731BaseControlRapsFloodingBlock OBJECT-TYPE
			SYNTAX INTEGER
				{
				disable(0),
				enable(1)
				}
			MAX-ACCESS read-write
			STATUS current
			DESCRIPTION
				"R-APS Flooding Block Mode"
			::= { sleY1731BaseControl 21 }

		
--   1.3.6.1.4.1.6296.101.4.12.1.2.22
-- 1.3.6.1.4.1.6296.101.4.12.1.2.22
		-- 1.3.6.1.4.1.6296.101.4.12.1.2.22
		sleY1731BaseControlTlvPermission OBJECT-TYPE
			SYNTAX INTEGER
				{
				none(1),
				chassis(2)
				}
			MAX-ACCESS read-write
			STATUS current
			DESCRIPTION
				"Indicates TLV Permission"
			::= { sleY1731BaseControl 22 }

		
--   1.3.6.1.4.1.6296.101.4.12.1.3
-- 1.3.6.1.4.1.6296.101.4.12.1.3
		-- 1.3.6.1.4.1.6296.101.4.12.1.3
		sleY1731BaseNotification OBJECT IDENTIFIER ::= { sleY1731Base 3 }

		
--   1.3.6.1.4.1.6296.101.4.12.1.3.1
-- 1.3.6.1.4.1.6296.101.4.12.1.3.1
		-- 1.3.6.1.4.1.6296.101.4.12.1.3.1
		sleY1731EnableChanged NOTIFICATION-TYPE
			OBJECTS { sleY1731BaseControlRequest, sleY1731BaseControlTimeStamp, sleY1731BaseControlReqResult, sleY1731BaseControlEnable }
			STATUS current
			DESCRIPTION 
				"setY1731Enable"
			::= { sleY1731BaseNotification 1 }

		
--   1.3.6.1.4.1.6296.101.4.12.1.3.2
-- 1.3.6.1.4.1.6296.101.4.12.1.3.2
		-- 1.3.6.1.4.1.6296.101.4.12.1.3.2
		sleY1731TrunkEnableChanged NOTIFICATION-TYPE
			OBJECTS { sleY1731BaseControlRequest, sleY1731BaseControlTimeStamp, sleY1731BaseControlReqResult, sleY1731BaseControlTrunkEnable }
			STATUS current
			DESCRIPTION 
				"setY1731TrunkEnable"
			::= { sleY1731BaseNotification 2 }

		
--   1.3.6.1.4.1.6296.101.4.12.1.3.3
-- 1.3.6.1.4.1.6296.101.4.12.1.3.3
		-- 1.3.6.1.4.1.6296.101.4.12.1.3.3
		sleY1731LtrCacheProfileChanged NOTIFICATION-TYPE
			OBJECTS { sleY1731BaseControlRequest, sleY1731BaseControlTimeStamp, sleY1731BaseControlReqResult, sleY1731BaseControlLtrCacheHoldTime, sleY1731BaseControlLtrCacheSize
				 }
			STATUS current
			DESCRIPTION 
				"setY1731LtrCacheProfile"
			::= { sleY1731BaseNotification 3 }

		
--   1.3.6.1.4.1.6296.101.4.12.1.3.4
-- 1.3.6.1.4.1.6296.101.4.12.1.3.4
		-- 1.3.6.1.4.1.6296.101.4.12.1.3.4
		sleY1731SnmpProfileChanged NOTIFICATION-TYPE
			OBJECTS { sleY1731BaseControlRequest, sleY1731BaseControlTimeStamp, sleY1731BaseControlReqResult, sleY1731BaseControlSnmpServerTraps }
			STATUS current
			DESCRIPTION 
				"setY1731SnmpProfile"
			::= { sleY1731BaseNotification 4 }

		
--   1.3.6.1.4.1.6296.101.4.12.1.3.5
-- 1.3.6.1.4.1.6296.101.4.12.1.3.5
		-- 1.3.6.1.4.1.6296.101.4.12.1.3.5
		sleY1731XcheckProfileChanged NOTIFICATION-TYPE
			OBJECTS { sleY1731BaseControlRequest, sleY1731BaseControlTimeStamp, sleY1731BaseControlReqResult, sleY1731BaseControlXcheckStartDelay }
			STATUS current
			DESCRIPTION 
				"setY1731XcheckProfile"
			::= { sleY1731BaseNotification 5 }

		
--   1.3.6.1.4.1.6296.101.4.12.1.3.6
-- 1.3.6.1.4.1.6296.101.4.12.1.3.6
		-- 1.3.6.1.4.1.6296.101.4.12.1.3.6
		sleY1731DefaultMegProfileChanged NOTIFICATION-TYPE
			OBJECTS { sleY1731BaseControlRequest, sleY1731BaseControlTimeStamp, sleY1731BaseControlReqResult, sleY1731BaseControlDefaultMegLevel, sleY1731BaseControlDefaultMegMhfCreation
				 }
			STATUS current
			DESCRIPTION 
				"setY1731DefaultMegProfile"
			::= { sleY1731BaseNotification 6 }

		
--   1.3.6.1.4.1.6296.101.4.12.1.3.7
-- 1.3.6.1.4.1.6296.101.4.12.1.3.7
		-- 1.3.6.1.4.1.6296.101.4.12.1.3.7
		sleY1731PduToCfmChanged NOTIFICATION-TYPE
			OBJECTS { sleY1731BaseControlRequest, sleY1731BaseControlTimeStamp, sleY1731BaseControlReqResult, sleY1731BaseControlPduToCfm }
			STATUS current
			DESCRIPTION 
				"Description."
			::= { sleY1731BaseNotification 7 }

		
--   1.3.6.1.4.1.6296.101.4.12.1.3.8
-- 1.3.6.1.4.1.6296.101.4.12.1.3.8
		-- 1.3.6.1.4.1.6296.101.4.12.1.3.8
		sleY1731DedicatedVlanChanged NOTIFICATION-TYPE
			OBJECTS { sleY1731BaseControlRequest, sleY1731BaseControlTimeStamp, sleY1731BaseControlReqResult, sleY1731BaseControlDedicatedVlan }
			STATUS current
			DESCRIPTION 
				"Description."
			::= { sleY1731BaseNotification 8 }

		
--   1.3.6.1.4.1.6296.101.4.12.1.3.9
-- 1.3.6.1.4.1.6296.101.4.12.1.3.9
		-- 1.3.6.1.4.1.6296.101.4.12.1.3.9
		sleY1731MipCcdbDestroyed NOTIFICATION-TYPE
			OBJECTS { sleY1731BaseControlRequest, sleY1731BaseControlTimeStamp, sleY1731BaseControlReqResult }
			STATUS current
			DESCRIPTION 
				"destroyMipCcdb"
			::= { sleY1731BaseNotification 9 }

		
--   1.3.6.1.4.1.6296.101.4.12.1.3.10
-- 1.3.6.1.4.1.6296.101.4.12.1.3.10
		-- 1.3.6.1.4.1.6296.101.4.12.1.3.10
		sleY1731LtrCacheDestroyed NOTIFICATION-TYPE
			OBJECTS { sleY1731BaseControlRequest, sleY1731BaseControlTimeStamp, sleY1731BaseControlReqResult }
			STATUS current
			DESCRIPTION 
				"destroyLtrCache"
			::= { sleY1731BaseNotification 10 }

		
--   1.3.6.1.4.1.6296.101.4.12.1.3.11
-- 1.3.6.1.4.1.6296.101.4.12.1.3.11
		-- 1.3.6.1.4.1.6296.101.4.12.1.3.11
		sleY1731RmepCreationChanged NOTIFICATION-TYPE
			OBJECTS { sleY1731BaseControlRequest, sleY1731BaseControlTimeStamp, sleY1731BaseControlReqResult, sleY1731BaseControlRmepCreation }
			STATUS current
			DESCRIPTION 
				"sleY1731BaseControlRmepCreation"
			::= { sleY1731BaseNotification 11 }

		
--   1.3.6.1.4.1.6296.101.4.12.1.3.12
-- 1.3.6.1.4.1.6296.101.4.12.1.3.12
		-- 1.3.6.1.4.1.6296.101.4.12.1.3.12
		sleY1731TrunkOamStatusChanged NOTIFICATION-TYPE
			OBJECTS { sleY1731BaseControlRequest, sleY1731BaseControlTimeStamp, sleY1731BaseControlReqResult, sleY1731BaseControlTrunkIndex, sleY1731BaseControlTrunkOamStatus, 
				sleY1731BaseControlTrunkMeg }
			STATUS current
			DESCRIPTION 
				"sleY1731BaseControlTrunkIndex
				sleY1731BaseControlTrunkOamStatus"
			::= { sleY1731BaseNotification 12 }

		
--   1.3.6.1.4.1.6296.101.4.12.1.3.13
-- 1.3.6.1.4.1.6296.101.4.12.1.3.13
		-- 1.3.6.1.4.1.6296.101.4.12.1.3.13
		sleY1731CCIgnoreDefectChanged NOTIFICATION-TYPE
			OBJECTS { sleY1731BaseControlRequest, sleY1731BaseControlTimeStamp, sleY1731BaseControlReqResult, sleY1731BaseControlCCIgnoreDefect }
			STATUS current
			DESCRIPTION 
				"sleY1731BaseControlCCIgnoreDefect"
			::= { sleY1731BaseNotification 13 }

		
--   1.3.6.1.4.1.6296.101.4.12.1.3.14
-- 1.3.6.1.4.1.6296.101.4.12.1.3.14
		-- 1.3.6.1.4.1.6296.101.4.12.1.3.14
		sleY1731RapsFloodinBlockChanged NOTIFICATION-TYPE
			OBJECTS { sleY1731BaseControlRequest, sleY1731BaseControlTimeStamp, sleY1731BaseControlReqResult, sleY1731BaseControlRapsFloodingBlock }
			STATUS current
			DESCRIPTION 
				"sleY1731BaseControlCCIgnoreDefect"
			::= { sleY1731BaseNotification 14 }

		
--   1.3.6.1.4.1.6296.101.4.12.1.3.15
-- 1.3.6.1.4.1.6296.101.4.12.1.3.15
		-- 1.3.6.1.4.1.6296.101.4.12.1.3.15
		sleY1731TlvPermissionChanged NOTIFICATION-TYPE
			OBJECTS { sleY1731BaseControlRequest, sleY1731BaseControlTimeStamp, sleY1731BaseControlReqResult, sleY1731BaseControlTlvPermission }
			STATUS current
			DESCRIPTION 
				"setY1731TlvPermission"
			::= { sleY1731BaseNotification 15 }

		
--   1.3.6.1.4.1.6296.101.4.12.1.4
-- 1.3.6.1.4.1.6296.101.4.12.1.4
		-- 1.3.6.1.4.1.6296.101.4.12.1.4
		sleY1731TrunkTable OBJECT-TYPE
			SYNTAX SEQUENCE OF SleY1731TrunkEntry
			MAX-ACCESS not-accessible
			STATUS current
			DESCRIPTION
				"Description."
			::= { sleY1731Base 4 }

		
--   1.3.6.1.4.1.6296.101.4.12.1.4.1
-- 1.3.6.1.4.1.6296.101.4.12.1.4.1
		-- 1.3.6.1.4.1.6296.101.4.12.1.4.1
		sleY1731TrunkEntry OBJECT-TYPE
			SYNTAX SleY1731TrunkEntry
			MAX-ACCESS not-accessible
			STATUS current
			DESCRIPTION
				"Description."
			INDEX { sleY1731TrunkIndex }
			::= { sleY1731TrunkTable 1 }

		
		SleY1731TrunkEntry ::=
			SEQUENCE { 
				sleY1731TrunkIndex
					INTEGER,
				sleY1731TrunkOamStatus
					INTEGER,
				sleY1731TrunkMeg
					OCTET STRING
			 }

--   1.3.6.1.4.1.6296.101.4.12.1.4.1.1
-- 1.3.6.1.4.1.6296.101.4.12.1.4.1.1
		-- 1.3.6.1.4.1.6296.101.4.12.1.4.1.1
		sleY1731TrunkIndex OBJECT-TYPE
			SYNTAX INTEGER (0..65535)
			MAX-ACCESS read-only
			STATUS current
			DESCRIPTION
				"trunk port index."
			::= { sleY1731TrunkEntry 1 }

		
--   1.3.6.1.4.1.6296.101.4.12.1.4.1.2
-- 1.3.6.1.4.1.6296.101.4.12.1.4.1.2
		-- 1.3.6.1.4.1.6296.101.4.12.1.4.1.2
		sleY1731TrunkOamStatus OBJECT-TYPE
			SYNTAX INTEGER
				{
				disable(0),
				enable(1)
				}
			MAX-ACCESS read-only
			STATUS current
			DESCRIPTION
				"OAM status per each Trunk port."
			::= { sleY1731TrunkEntry 2 }

		
--   1.3.6.1.4.1.6296.101.4.12.1.4.1.3
-- 1.3.6.1.4.1.6296.101.4.12.1.4.1.3
		-- 1.3.6.1.4.1.6296.101.4.12.1.4.1.3
		sleY1731TrunkMeg OBJECT-TYPE
			SYNTAX OCTET STRING
			MAX-ACCESS read-only
			STATUS current
			DESCRIPTION
				"trunk port meg name."
			::= { sleY1731TrunkEntry 3 }

		
--   1.3.6.1.4.1.6296.101.4.12.2
-- 1.3.6.1.4.1.6296.101.4.12.2
		-- 1.3.6.1.4.1.6296.101.4.12.2
		sleY1731Meg OBJECT IDENTIFIER ::= { sleY1731Oam 2 }

		
--   1.3.6.1.4.1.6296.101.4.12.2.1
-- 1.3.6.1.4.1.6296.101.4.12.2.1
		-- 1.3.6.1.4.1.6296.101.4.12.2.1
		sleY1731MegTable OBJECT-TYPE
			SYNTAX SEQUENCE OF SleY1731MegEntry
			MAX-ACCESS not-accessible
			STATUS current
			DESCRIPTION
				"Description."
			::= { sleY1731Meg 1 }

		
--   1.3.6.1.4.1.6296.101.4.12.2.1.1
-- 1.3.6.1.4.1.6296.101.4.12.2.1.1
		-- 1.3.6.1.4.1.6296.101.4.12.2.1.1
		sleY1731MegEntry OBJECT-TYPE
			SYNTAX SleY1731MegEntry
			MAX-ACCESS not-accessible
			STATUS current
			DESCRIPTION
				"Description."
			INDEX { sleY1731MegIndex }
			::= { sleY1731MegTable 1 }

		
		SleY1731MegEntry ::=
			SEQUENCE { 
				sleY1731MegIndex
					Integer32,
				sleY1731MegName
					OCTET STRING,
				sleY1731MegLevel
					Integer32,
				sleY1731MegVid
					Integer32,
				sleY1731MegMepEnable
					INTEGER,
				sleY1731MegCcEnable
					INTEGER,
				sleY1731MegCcInterval
					Integer32,
				sleY1731MegCcPriority
					Integer32,
				sleY1731MegCcLossThreshold
					Integer32,
				sleY1731MegCcHoldTime
					Integer32,
				sleY1731MegFaultPriority
					Integer32,
				sleY1731MegFaultKeepTime
					Integer32,
				sleY1731MegFaultClearTime
					Integer32,
				sleY1731MegXcheckEnable
					INTEGER,
				sleY1731MegAisEnable
					INTEGER,
				sleY1731MegAisTransmitEnable
					INTEGER,
				sleY1731MegAisInterval
					INTEGER,
				sleY1731MegAisLevel
					Integer32,
				sleY1731MegAisPriority
					Integer32,
				sleY1731MegLckEnable
					INTEGER,
				sleY1731MegLckTransmitEnable
					INTEGER,
				sleY1731MegLckInterval
					INTEGER,
				sleY1731MegLckLevel
					Integer32,
				sleY1731MegLckPriority
					Integer32,
				sleY1731MegOutOfService
					INTEGER,
				sleY1731MegRapsEnable
					INTEGER,
				sleY1731MegRapsRplOwner
					INTEGER,
				sleY1731MegRapsEastPort
					Integer32,
				sleY1731MegRapsWestPort
					Integer32,
				sleY1731MegRapsRplPort
					INTEGER,
				sleY1731MegRapsHoldOffTime
					Integer32,
				sleY1731MegRapsGuardTime
					Integer32,
				sleY1731MegRapsWaitToRestore
					Integer32,
				sleY1731MegRapsState
					INTEGER,
				sleY1731MegRapsEastPortStatus
					INTEGER,
				sleY1731MegRapsWestPortStatus
					INTEGER,
				sleY1731MegRapsNonRevertive
					INTEGER,
				sleY1731MegRapsForcedSwitchEast
					INTEGER,
				sleY1731MegRapsForcedSwitchWest
					INTEGER
			 }

--   1.3.6.1.4.1.6296.101.4.12.2.1.1.1
-- 1.3.6.1.4.1.6296.101.4.12.2.1.1.1
		-- 1.3.6.1.4.1.6296.101.4.12.2.1.1.1
		sleY1731MegIndex OBJECT-TYPE
			SYNTAX Integer32 (1..65535)
			MAX-ACCESS read-only
			STATUS current
			DESCRIPTION
				"Indicates the MEG's Index"
			::= { sleY1731MegEntry 1 }

		
--   1.3.6.1.4.1.6296.101.4.12.2.1.1.2
-- 1.3.6.1.4.1.6296.101.4.12.2.1.1.2
		-- 1.3.6.1.4.1.6296.101.4.12.2.1.1.2
		sleY1731MegName OBJECT-TYPE
			SYNTAX OCTET STRING (SIZE (1..12))
			MAX-ACCESS read-only
			STATUS current
			DESCRIPTION
				"The MEG's name: ICC (6 bytes) + UMC (6 bytes)"
			::= { sleY1731MegEntry 2 }

		
--   1.3.6.1.4.1.6296.101.4.12.2.1.1.3
-- 1.3.6.1.4.1.6296.101.4.12.2.1.1.3
		-- 1.3.6.1.4.1.6296.101.4.12.2.1.1.3
		sleY1731MegLevel OBJECT-TYPE
			SYNTAX Integer32 (0..7)
			MAX-ACCESS read-only
			STATUS current
			DESCRIPTION
				"Indicates the MEG's level"
			::= { sleY1731MegEntry 3 }

		
--   1.3.6.1.4.1.6296.101.4.12.2.1.1.4
-- 1.3.6.1.4.1.6296.101.4.12.2.1.1.4
		-- 1.3.6.1.4.1.6296.101.4.12.2.1.1.4
		sleY1731MegVid OBJECT-TYPE
			SYNTAX Integer32 (1..4094)
			MAX-ACCESS read-only
			STATUS current
			DESCRIPTION
				"Indicates the MEG's VID"
			::= { sleY1731MegEntry 4 }

		
--   1.3.6.1.4.1.6296.101.4.12.2.1.1.5
-- 1.3.6.1.4.1.6296.101.4.12.2.1.1.5
		-- 1.3.6.1.4.1.6296.101.4.12.2.1.1.5
		sleY1731MegMepEnable OBJECT-TYPE
			SYNTAX INTEGER
				{
				disable(0),
				enable(1)
				}
			MAX-ACCESS read-only
			STATUS current
			DESCRIPTION
				"Enables/Disables Y.1731 OAM for MEPs"
			::= { sleY1731MegEntry 5 }

		
--   1.3.6.1.4.1.6296.101.4.12.2.1.1.6
-- 1.3.6.1.4.1.6296.101.4.12.2.1.1.6
		-- 1.3.6.1.4.1.6296.101.4.12.2.1.1.6
		sleY1731MegCcEnable OBJECT-TYPE
			SYNTAX INTEGER
				{
				disable(0),
				enable(1)
				}
			MAX-ACCESS read-only
			STATUS current
			DESCRIPTION
				"Enables/Disables MEPs to send Continuity Check messages"
			::= { sleY1731MegEntry 6 }

		
--   1.3.6.1.4.1.6296.101.4.12.2.1.1.7
-- 1.3.6.1.4.1.6296.101.4.12.2.1.1.7
		-- 1.3.6.1.4.1.6296.101.4.12.2.1.1.7
		sleY1731MegCcInterval OBJECT-TYPE
			SYNTAX Integer32 (1 | 2..7)
			MAX-ACCESS read-only
			STATUS current
			DESCRIPTION
				"Indicates the interval between CCM transmissions"
			::= { sleY1731MegEntry 7 }

		
--   1.3.6.1.4.1.6296.101.4.12.2.1.1.8
-- 1.3.6.1.4.1.6296.101.4.12.2.1.1.8
		-- 1.3.6.1.4.1.6296.101.4.12.2.1.1.8
		sleY1731MegCcPriority OBJECT-TYPE
			SYNTAX Integer32 (0..7)
			MAX-ACCESS read-only
			STATUS current
			DESCRIPTION
				"Indicates the CCM or LTM Message Priority"
			::= { sleY1731MegEntry 8 }

		
--   1.3.6.1.4.1.6296.101.4.12.2.1.1.9
-- 1.3.6.1.4.1.6296.101.4.12.2.1.1.9
		-- 1.3.6.1.4.1.6296.101.4.12.2.1.1.9
		sleY1731MegCcLossThreshold OBJECT-TYPE
			SYNTAX Integer32 (2..255)
			MAX-ACCESS read-only
			STATUS current
			DESCRIPTION
				"Indicates the minimum number of CCMs that can be missed before declaring that a MEP is down"
			::= { sleY1731MegEntry 9 }

		
--   1.3.6.1.4.1.6296.101.4.12.2.1.1.10
-- 1.3.6.1.4.1.6296.101.4.12.2.1.1.10
		-- 1.3.6.1.4.1.6296.101.4.12.2.1.1.10
		sleY1731MegCcHoldTime OBJECT-TYPE
			SYNTAX Integer32 (1..65535)
			MAX-ACCESS read-only
			STATUS current
			DESCRIPTION
				"Indicates the time that data of a missing MEP is kept"
			::= { sleY1731MegEntry 10 }

		
--   1.3.6.1.4.1.6296.101.4.12.2.1.1.11
-- 1.3.6.1.4.1.6296.101.4.12.2.1.1.11
		-- 1.3.6.1.4.1.6296.101.4.12.2.1.1.11
		sleY1731MegFaultPriority OBJECT-TYPE
			SYNTAX Integer32 (1..8)
			MAX-ACCESS read-only
			STATUS current
			DESCRIPTION
				"Indicates the lowest priority for fault alarm"
			::= { sleY1731MegEntry 11 }

		
--   1.3.6.1.4.1.6296.101.4.12.2.1.1.12
-- 1.3.6.1.4.1.6296.101.4.12.2.1.1.12
		-- 1.3.6.1.4.1.6296.101.4.12.2.1.1.12
		sleY1731MegFaultKeepTime OBJECT-TYPE
			SYNTAX Integer32 (0..1023)
			MAX-ACCESS read-only
			STATUS current
			DESCRIPTION
				"Indicates the keep time for the fault alarm"
			::= { sleY1731MegEntry 12 }

		
--   1.3.6.1.4.1.6296.101.4.12.2.1.1.13
-- 1.3.6.1.4.1.6296.101.4.12.2.1.1.13
		-- 1.3.6.1.4.1.6296.101.4.12.2.1.1.13
		sleY1731MegFaultClearTime OBJECT-TYPE
			SYNTAX Integer32 (0..1023)
			MAX-ACCESS read-only
			STATUS current
			DESCRIPTION
				"Indicates the clear time for the fault alarm"
			::= { sleY1731MegEntry 13 }

		
--   1.3.6.1.4.1.6296.101.4.12.2.1.1.14
-- 1.3.6.1.4.1.6296.101.4.12.2.1.1.14
		-- 1.3.6.1.4.1.6296.101.4.12.2.1.1.14
		sleY1731MegXcheckEnable OBJECT-TYPE
			SYNTAX INTEGER
				{
				disable(0),
				enable(1)
				}
			MAX-ACCESS read-only
			STATUS current
			DESCRIPTION
				"Enables/Disables Y.1731 cross-check for a specific MEG"
			::= { sleY1731MegEntry 14 }

		
--   1.3.6.1.4.1.6296.101.4.12.2.1.1.15
-- 1.3.6.1.4.1.6296.101.4.12.2.1.1.15
		-- 1.3.6.1.4.1.6296.101.4.12.2.1.1.15
		sleY1731MegAisEnable OBJECT-TYPE
			SYNTAX INTEGER
				{
				disable(0),
				enable(1)
				}
			MAX-ACCESS read-only
			STATUS current
			DESCRIPTION
				"Enables/Disables ETH-AIS function"
			::= { sleY1731MegEntry 15 }

		
--   1.3.6.1.4.1.6296.101.4.12.2.1.1.16
-- 1.3.6.1.4.1.6296.101.4.12.2.1.1.16
		-- 1.3.6.1.4.1.6296.101.4.12.2.1.1.16
		sleY1731MegAisTransmitEnable OBJECT-TYPE
			SYNTAX INTEGER
				{
				disable(0),
				enable(1)
				}
			MAX-ACCESS read-only
			STATUS current
			DESCRIPTION
				"Enables/Disables ETH-AIS frame transmission on a MEP"
			::= { sleY1731MegEntry 16 }

		
--   1.3.6.1.4.1.6296.101.4.12.2.1.1.17
-- 1.3.6.1.4.1.6296.101.4.12.2.1.1.17
		-- 1.3.6.1.4.1.6296.101.4.12.2.1.1.17
		sleY1731MegAisInterval OBJECT-TYPE
			SYNTAX INTEGER
				{
				oneSecond(4),
				oneMinute(6)
				}
			MAX-ACCESS read-only
			STATUS current
			DESCRIPTION
				"Indicates the interval between AIS transmissions"
			::= { sleY1731MegEntry 17 }

		
--   1.3.6.1.4.1.6296.101.4.12.2.1.1.18
-- 1.3.6.1.4.1.6296.101.4.12.2.1.1.18
		-- 1.3.6.1.4.1.6296.101.4.12.2.1.1.18
		sleY1731MegAisLevel OBJECT-TYPE
			SYNTAX Integer32 (1..7)
			MAX-ACCESS read-only
			STATUS current
			DESCRIPTION
				"Indicates the client MEG's level"
			::= { sleY1731MegEntry 18 }

		
--   1.3.6.1.4.1.6296.101.4.12.2.1.1.19
-- 1.3.6.1.4.1.6296.101.4.12.2.1.1.19
		-- 1.3.6.1.4.1.6296.101.4.12.2.1.1.19
		sleY1731MegAisPriority OBJECT-TYPE
			SYNTAX Integer32 (0..7)
			MAX-ACCESS read-only
			STATUS current
			DESCRIPTION
				"Indicates the AIS Message Priority"
			::= { sleY1731MegEntry 19 }

		
--   1.3.6.1.4.1.6296.101.4.12.2.1.1.20
-- 1.3.6.1.4.1.6296.101.4.12.2.1.1.20
		-- 1.3.6.1.4.1.6296.101.4.12.2.1.1.20
		sleY1731MegLckEnable OBJECT-TYPE
			SYNTAX INTEGER
				{
				disable(0),
				enable(1)
				}
			MAX-ACCESS read-only
			STATUS current
			DESCRIPTION
				"Enables/Disables ETH-LCK function"
			::= { sleY1731MegEntry 20 }

		
--   1.3.6.1.4.1.6296.101.4.12.2.1.1.21
-- 1.3.6.1.4.1.6296.101.4.12.2.1.1.21
		-- 1.3.6.1.4.1.6296.101.4.12.2.1.1.21
		sleY1731MegLckTransmitEnable OBJECT-TYPE
			SYNTAX INTEGER
				{
				disable(0),
				enable(1)
				}
			MAX-ACCESS read-only
			STATUS current
			DESCRIPTION
				"Enables/Disables ETH-LCK frame transmission on a MEP"
			::= { sleY1731MegEntry 21 }

		
--   1.3.6.1.4.1.6296.101.4.12.2.1.1.22
-- 1.3.6.1.4.1.6296.101.4.12.2.1.1.22
		-- 1.3.6.1.4.1.6296.101.4.12.2.1.1.22
		sleY1731MegLckInterval OBJECT-TYPE
			SYNTAX INTEGER
				{
				oneSecond(4),
				oneMinute(6)
				}
			MAX-ACCESS read-only
			STATUS current
			DESCRIPTION
				"Indicates the interval between LCK transmissions"
			::= { sleY1731MegEntry 22 }

		
--   1.3.6.1.4.1.6296.101.4.12.2.1.1.23
-- 1.3.6.1.4.1.6296.101.4.12.2.1.1.23
		-- 1.3.6.1.4.1.6296.101.4.12.2.1.1.23
		sleY1731MegLckLevel OBJECT-TYPE
			SYNTAX Integer32 (1..7)
			MAX-ACCESS read-only
			STATUS current
			DESCRIPTION
				"Indicates the client MEG's level"
			::= { sleY1731MegEntry 23 }

		
--   1.3.6.1.4.1.6296.101.4.12.2.1.1.24
-- 1.3.6.1.4.1.6296.101.4.12.2.1.1.24
		-- 1.3.6.1.4.1.6296.101.4.12.2.1.1.24
		sleY1731MegLckPriority OBJECT-TYPE
			SYNTAX Integer32 (0..7)
			MAX-ACCESS read-only
			STATUS current
			DESCRIPTION
				"Indicates the LCK Message Priority"
			::= { sleY1731MegEntry 24 }

		
--   1.3.6.1.4.1.6296.101.4.12.2.1.1.25
-- 1.3.6.1.4.1.6296.101.4.12.2.1.1.25
		-- 1.3.6.1.4.1.6296.101.4.12.2.1.1.25
		sleY1731MegOutOfService OBJECT-TYPE
			SYNTAX INTEGER
				{
				disable(0),
				enable(1)
				}
			MAX-ACCESS read-only
			STATUS current
			DESCRIPTION
				"Indicates the out-of-service mode"
			::= { sleY1731MegEntry 25 }

		
--   1.3.6.1.4.1.6296.101.4.12.2.1.1.26
-- 1.3.6.1.4.1.6296.101.4.12.2.1.1.26
		-- 1.3.6.1.4.1.6296.101.4.12.2.1.1.26
		sleY1731MegRapsEnable OBJECT-TYPE
			SYNTAX INTEGER
				{
				disable(0),
				enable(1)
				}
			MAX-ACCESS read-only
			STATUS current
			DESCRIPTION
				"Enables/Disables R-APS node"
			::= { sleY1731MegEntry 26 }

		
--   1.3.6.1.4.1.6296.101.4.12.2.1.1.27
-- 1.3.6.1.4.1.6296.101.4.12.2.1.1.27
		-- 1.3.6.1.4.1.6296.101.4.12.2.1.1.27
		sleY1731MegRapsRplOwner OBJECT-TYPE
			SYNTAX INTEGER
				{
				false(0),
				true(1)
				}
			MAX-ACCESS read-only
			STATUS current
			DESCRIPTION
				"Indicates the owner of the ring protection link"
			::= { sleY1731MegEntry 27 }

		
--   1.3.6.1.4.1.6296.101.4.12.2.1.1.28
-- 1.3.6.1.4.1.6296.101.4.12.2.1.1.28
		-- 1.3.6.1.4.1.6296.101.4.12.2.1.1.28
		sleY1731MegRapsEastPort OBJECT-TYPE
			SYNTAX Integer32
			MAX-ACCESS read-only
			STATUS current
			DESCRIPTION
				"Indicates the east port of R-APS node"
			::= { sleY1731MegEntry 28 }

		
--   1.3.6.1.4.1.6296.101.4.12.2.1.1.29
-- 1.3.6.1.4.1.6296.101.4.12.2.1.1.29
		-- 1.3.6.1.4.1.6296.101.4.12.2.1.1.29
		sleY1731MegRapsWestPort OBJECT-TYPE
			SYNTAX Integer32
			MAX-ACCESS read-only
			STATUS current
			DESCRIPTION
				"Indicates the west port of R-APS node"
			::= { sleY1731MegEntry 29 }

		
--   1.3.6.1.4.1.6296.101.4.12.2.1.1.30
-- 1.3.6.1.4.1.6296.101.4.12.2.1.1.30
		-- 1.3.6.1.4.1.6296.101.4.12.2.1.1.30
		sleY1731MegRapsRplPort OBJECT-TYPE
			SYNTAX INTEGER
				{
				none(-1),
				east(0),
				west(1)
				}
			MAX-ACCESS read-only
			STATUS current
			DESCRIPTION
				"Indicates the RPL port of R-APS node"
			::= { sleY1731MegEntry 30 }

		
--   1.3.6.1.4.1.6296.101.4.12.2.1.1.31
-- 1.3.6.1.4.1.6296.101.4.12.2.1.1.31
		-- 1.3.6.1.4.1.6296.101.4.12.2.1.1.31
		sleY1731MegRapsHoldOffTime OBJECT-TYPE
			SYNTAX Integer32 (0..10000)
			MAX-ACCESS read-only
			STATUS current
			DESCRIPTION
				"Indicates the hold-off time for verifying local SF"
			::= { sleY1731MegEntry 31 }

		
--   1.3.6.1.4.1.6296.101.4.12.2.1.1.32
-- 1.3.6.1.4.1.6296.101.4.12.2.1.1.32
		-- 1.3.6.1.4.1.6296.101.4.12.2.1.1.32
		sleY1731MegRapsGuardTime OBJECT-TYPE
			SYNTAX Integer32 (10..2000)
			MAX-ACCESS read-only
			STATUS current
			DESCRIPTION
				"Indicates the guard time for verifying local clear SF"
			::= { sleY1731MegEntry 32 }

		
--   1.3.6.1.4.1.6296.101.4.12.2.1.1.33
-- 1.3.6.1.4.1.6296.101.4.12.2.1.1.33
		-- 1.3.6.1.4.1.6296.101.4.12.2.1.1.33
		sleY1731MegRapsWaitToRestore OBJECT-TYPE
			SYNTAX Integer32 (5..720)
			MAX-ACCESS read-only
			STATUS current
			DESCRIPTION
				"Indicates the wait-to-restore time for verifying remote SF"
			::= { sleY1731MegEntry 33 }

		
--   1.3.6.1.4.1.6296.101.4.12.2.1.1.34
-- 1.3.6.1.4.1.6296.101.4.12.2.1.1.34
		-- 1.3.6.1.4.1.6296.101.4.12.2.1.1.34
		sleY1731MegRapsState OBJECT-TYPE
			SYNTAX INTEGER
				{
				none(0),
				idle(1),
				protection(2)
				}
			MAX-ACCESS read-only
			STATUS current
			DESCRIPTION
				"Indicate the state of r-aps state machine"
			::= { sleY1731MegEntry 34 }

		
--   1.3.6.1.4.1.6296.101.4.12.2.1.1.35
-- 1.3.6.1.4.1.6296.101.4.12.2.1.1.35
		-- 1.3.6.1.4.1.6296.101.4.12.2.1.1.35
		sleY1731MegRapsEastPortStatus OBJECT-TYPE
			SYNTAX INTEGER
				{
				none(0),
				disabled(1),
				forwarding(2),
				blocking(3)
				}
			MAX-ACCESS read-only
			STATUS current
			DESCRIPTION
				"The port status of east port."
			::= { sleY1731MegEntry 35 }

		
--   1.3.6.1.4.1.6296.101.4.12.2.1.1.36
-- 1.3.6.1.4.1.6296.101.4.12.2.1.1.36
		-- 1.3.6.1.4.1.6296.101.4.12.2.1.1.36
		sleY1731MegRapsWestPortStatus OBJECT-TYPE
			SYNTAX INTEGER
				{
				none(0),
				disabled(1),
				forwarding(2),
				blocking(3)
				}
			MAX-ACCESS read-only
			STATUS current
			DESCRIPTION
				"The port status of west port."
			::= { sleY1731MegEntry 36 }

		
--   1.3.6.1.4.1.6296.101.4.12.2.1.1.37
-- 1.3.6.1.4.1.6296.101.4.12.2.1.1.37
		-- 1.3.6.1.4.1.6296.101.4.12.2.1.1.37
		sleY1731MegRapsNonRevertive OBJECT-TYPE
			SYNTAX INTEGER
				{
				false(0),
				true(1)
				}
			MAX-ACCESS read-only
			STATUS current
			DESCRIPTION
				"NonRevertive"
			::= { sleY1731MegEntry 37 }

		
--   1.3.6.1.4.1.6296.101.4.12.2.1.1.38
-- 1.3.6.1.4.1.6296.101.4.12.2.1.1.38
		-- 1.3.6.1.4.1.6296.101.4.12.2.1.1.38
		sleY1731MegRapsForcedSwitchEast OBJECT-TYPE
			SYNTAX INTEGER
				{
				false(0),
				true(1)
				}
			MAX-ACCESS read-only
			STATUS current
			DESCRIPTION
				"ForcedSwitchEast"
			::= { sleY1731MegEntry 38 }

		
--   1.3.6.1.4.1.6296.101.4.12.2.1.1.39
-- 1.3.6.1.4.1.6296.101.4.12.2.1.1.39
		-- 1.3.6.1.4.1.6296.101.4.12.2.1.1.39
		sleY1731MegRapsForcedSwitchWest OBJECT-TYPE
			SYNTAX INTEGER
				{
				false(0),
				true(1)
				}
			MAX-ACCESS read-only
			STATUS current
			DESCRIPTION
				"ForcedSwitchWest"
			::= { sleY1731MegEntry 39 }

		
--   1.3.6.1.4.1.6296.101.4.12.2.2
-- 1.3.6.1.4.1.6296.101.4.12.2.2
		-- 1.3.6.1.4.1.6296.101.4.12.2.2
		sleY1731MegControl OBJECT IDENTIFIER ::= { sleY1731Meg 2 }

		
--   1.3.6.1.4.1.6296.101.4.12.2.2.1
-- 1.3.6.1.4.1.6296.101.4.12.2.2.1
		-- 1.3.6.1.4.1.6296.101.4.12.2.2.1
		sleY1731MegControlRequest OBJECT-TYPE
			SYNTAX INTEGER
				{
				createY1731Meg(1),
				deleteY1731Meg(2),
				setY1731MegMepEnable(3),
				setY1731MegCcEnable(4),
				setY1731MegCcProfile(5),
				setY1731MegFaultProfile(6),
				setY1731MegXcheckEnable(7),
				setY1731MegAisEnable(8),
				setY1731MegAisTransmitEnable(9),
				setY1731MegAisProfile(10),
				setY1731MegLckEnable(11),
				setY1731MegLckTransmitEnable(12),
				setY1731MegLckProfile(13),
				setY1731MegOutOfService(14),
				setY1731MegRapsEnable(15),
				setY1731MegRapsRingports(16),
				setY1731MegRapsRplPort(17),
				setY1731MegRapsRplOwner(18),
				setY1731MegRapsRplTimer(19),
				destroyY1731MegRemoteMep(20),
				destroyY1731MegError(21),
				setY1731MegRapsNonRevertive(22),
				setY1731MegRapsForcedSwitchEast(23),
				setY1731MegRapsForcedSwitchWest(24)
				}
			MAX-ACCESS read-write
			STATUS current
			DESCRIPTION
				"Description."
			::= { sleY1731MegControl 1 }

		
--   1.3.6.1.4.1.6296.101.4.12.2.2.2
-- 1.3.6.1.4.1.6296.101.4.12.2.2.2
		-- 1.3.6.1.4.1.6296.101.4.12.2.2.2
		sleY1731MegControlStatus OBJECT-TYPE
			SYNTAX SleControlStatusType
			MAX-ACCESS read-only
			STATUS current
			DESCRIPTION
				"Description."
			::= { sleY1731MegControl 2 }

		
--   1.3.6.1.4.1.6296.101.4.12.2.2.3
-- 1.3.6.1.4.1.6296.101.4.12.2.2.3
		-- 1.3.6.1.4.1.6296.101.4.12.2.2.3
		sleY1731MegControlTimer OBJECT-TYPE
			SYNTAX Gauge32
			MAX-ACCESS read-write
			STATUS current
			DESCRIPTION
				"Description."
			::= { sleY1731MegControl 3 }

		
--   1.3.6.1.4.1.6296.101.4.12.2.2.4
-- 1.3.6.1.4.1.6296.101.4.12.2.2.4
		-- 1.3.6.1.4.1.6296.101.4.12.2.2.4
		sleY1731MegControlTimeStamp OBJECT-TYPE
			SYNTAX TimeTicks
			MAX-ACCESS read-only
			STATUS current
			DESCRIPTION
				"Description."
			::= { sleY1731MegControl 4 }

		
--   1.3.6.1.4.1.6296.101.4.12.2.2.5
-- 1.3.6.1.4.1.6296.101.4.12.2.2.5
		-- 1.3.6.1.4.1.6296.101.4.12.2.2.5
		sleY1731MegControlReqResult OBJECT-TYPE
			SYNTAX SleControlRequestResultType
			MAX-ACCESS read-only
			STATUS current
			DESCRIPTION
				"Description."
			::= { sleY1731MegControl 5 }

		
--   1.3.6.1.4.1.6296.101.4.12.2.2.6
-- 1.3.6.1.4.1.6296.101.4.12.2.2.6
		-- 1.3.6.1.4.1.6296.101.4.12.2.2.6
		sleY1731MegControlIndex OBJECT-TYPE
			SYNTAX Integer32 (1..65535)
			MAX-ACCESS read-write
			STATUS current
			DESCRIPTION
				"Indicates the MEG's Index"
			::= { sleY1731MegControl 6 }

		
--   1.3.6.1.4.1.6296.101.4.12.2.2.7
-- 1.3.6.1.4.1.6296.101.4.12.2.2.7
		-- 1.3.6.1.4.1.6296.101.4.12.2.2.7
		sleY1731MegControlName OBJECT-TYPE
			SYNTAX OCTET STRING (SIZE (1..12))
			MAX-ACCESS read-write
			STATUS current
			DESCRIPTION
				"The MEG's name: ICC (6 bytes) + UMC (6 bytes)"
			::= { sleY1731MegControl 7 }

		
--   1.3.6.1.4.1.6296.101.4.12.2.2.8
-- 1.3.6.1.4.1.6296.101.4.12.2.2.8
		-- 1.3.6.1.4.1.6296.101.4.12.2.2.8
		sleY1731MegControlLevel OBJECT-TYPE
			SYNTAX Integer32 (0..7)
			MAX-ACCESS read-write
			STATUS current
			DESCRIPTION
				"Indicates the MEG's level"
			::= { sleY1731MegControl 8 }

		
--   1.3.6.1.4.1.6296.101.4.12.2.2.9
-- 1.3.6.1.4.1.6296.101.4.12.2.2.9
		-- 1.3.6.1.4.1.6296.101.4.12.2.2.9
		sleY1731MegControlVid OBJECT-TYPE
			SYNTAX Integer32 (1..4094)
			MAX-ACCESS read-write
			STATUS current
			DESCRIPTION
				"Indicates the MEG's VID"
			::= { sleY1731MegControl 9 }

		
--   1.3.6.1.4.1.6296.101.4.12.2.2.10
-- 1.3.6.1.4.1.6296.101.4.12.2.2.10
		-- 1.3.6.1.4.1.6296.101.4.12.2.2.10
		sleY1731MegControlMepEnable OBJECT-TYPE
			SYNTAX INTEGER
				{
				disable(0),
				enable(1)
				}
			MAX-ACCESS read-write
			STATUS current
			DESCRIPTION
				"Enables/Disables Y.1731 OAM for MEPs"
			::= { sleY1731MegControl 10 }

		
--   1.3.6.1.4.1.6296.101.4.12.2.2.11
-- 1.3.6.1.4.1.6296.101.4.12.2.2.11
		-- 1.3.6.1.4.1.6296.101.4.12.2.2.11
		sleY1731MegControlCcEnable OBJECT-TYPE
			SYNTAX INTEGER
				{
				disable(0),
				enable(1)
				}
			MAX-ACCESS read-write
			STATUS current
			DESCRIPTION
				"Enables/Disables MEPs to send Continuity Check messages"
			::= { sleY1731MegControl 11 }

		
--   1.3.6.1.4.1.6296.101.4.12.2.2.12
-- 1.3.6.1.4.1.6296.101.4.12.2.2.12
		-- 1.3.6.1.4.1.6296.101.4.12.2.2.12
		sleY1731MegControlCcInterval OBJECT-TYPE
			SYNTAX Integer32 (1 | 2..7)
			MAX-ACCESS read-write
			STATUS current
			DESCRIPTION
				"Indicates the interval between CCM transmissions"
			::= { sleY1731MegControl 12 }

		
--   1.3.6.1.4.1.6296.101.4.12.2.2.13
-- 1.3.6.1.4.1.6296.101.4.12.2.2.13
		-- 1.3.6.1.4.1.6296.101.4.12.2.2.13
		sleY1731MegControlCcPriority OBJECT-TYPE
			SYNTAX Integer32 (0..7)
			MAX-ACCESS read-write
			STATUS current
			DESCRIPTION
				"Indicates the CCM or LTM Message Priority"
			::= { sleY1731MegControl 13 }

		
--   1.3.6.1.4.1.6296.101.4.12.2.2.14
-- 1.3.6.1.4.1.6296.101.4.12.2.2.14
		-- 1.3.6.1.4.1.6296.101.4.12.2.2.14
		sleY1731MegControlCcLossThreshold OBJECT-TYPE
			SYNTAX Integer32 (2..255)
			MAX-ACCESS read-write
			STATUS current
			DESCRIPTION
				"Indicates the minimum number of CCMs that can be missed before declaring that a MEP is down"
			::= { sleY1731MegControl 14 }

		
--   1.3.6.1.4.1.6296.101.4.12.2.2.15
-- 1.3.6.1.4.1.6296.101.4.12.2.2.15
		-- 1.3.6.1.4.1.6296.101.4.12.2.2.15
		sleY1731MegControlCcHoldTime OBJECT-TYPE
			SYNTAX Integer32 (1..65535)
			MAX-ACCESS read-write
			STATUS current
			DESCRIPTION
				"Indicates the time that data of a missing MEP is kept"
			::= { sleY1731MegControl 15 }

		
--   1.3.6.1.4.1.6296.101.4.12.2.2.16
-- 1.3.6.1.4.1.6296.101.4.12.2.2.16
		-- 1.3.6.1.4.1.6296.101.4.12.2.2.16
		sleY1731MegControlFaultPriority OBJECT-TYPE
			SYNTAX Integer32 (1..8)
			MAX-ACCESS read-write
			STATUS current
			DESCRIPTION
				"Indicates the lowest priority for fault alarm"
			::= { sleY1731MegControl 16 }

		
--   1.3.6.1.4.1.6296.101.4.12.2.2.17
-- 1.3.6.1.4.1.6296.101.4.12.2.2.17
		-- 1.3.6.1.4.1.6296.101.4.12.2.2.17
		sleY1731MegControlFaultKeepTime OBJECT-TYPE
			SYNTAX Integer32 (0..1023)
			MAX-ACCESS read-write
			STATUS current
			DESCRIPTION
				"Indicates the keep time for the fault alarm"
			::= { sleY1731MegControl 17 }

		
--   1.3.6.1.4.1.6296.101.4.12.2.2.18
-- 1.3.6.1.4.1.6296.101.4.12.2.2.18
		-- 1.3.6.1.4.1.6296.101.4.12.2.2.18
		sleY1731MegControlFaultClearTime OBJECT-TYPE
			SYNTAX Integer32 (0..1023)
			MAX-ACCESS read-write
			STATUS current
			DESCRIPTION
				"Indicates the clear time for the fault alarm"
			::= { sleY1731MegControl 18 }

		
--   1.3.6.1.4.1.6296.101.4.12.2.2.19
-- 1.3.6.1.4.1.6296.101.4.12.2.2.19
		-- 1.3.6.1.4.1.6296.101.4.12.2.2.19
		sleY1731MegControlXcheckEnable OBJECT-TYPE
			SYNTAX INTEGER
				{
				disable(0),
				enable(1)
				}
			MAX-ACCESS read-write
			STATUS current
			DESCRIPTION
				"Enables/Disables Y.1731 cross-check for a specific MEG"
			::= { sleY1731MegControl 19 }

		
--   1.3.6.1.4.1.6296.101.4.12.2.2.20
-- 1.3.6.1.4.1.6296.101.4.12.2.2.20
		-- 1.3.6.1.4.1.6296.101.4.12.2.2.20
		sleY1731MegControlAisEnable OBJECT-TYPE
			SYNTAX INTEGER
				{
				disable(0),
				enable(1)
				}
			MAX-ACCESS read-write
			STATUS current
			DESCRIPTION
				"Enables/Disables ETH-AIS function"
			::= { sleY1731MegControl 20 }

		
--   1.3.6.1.4.1.6296.101.4.12.2.2.21
-- 1.3.6.1.4.1.6296.101.4.12.2.2.21
		-- 1.3.6.1.4.1.6296.101.4.12.2.2.21
		sleY1731MegControlAisTransmitEnable OBJECT-TYPE
			SYNTAX INTEGER
				{
				disable(0),
				enable(1)
				}
			MAX-ACCESS read-write
			STATUS current
			DESCRIPTION
				"Enables/Disables ETH-AIS frame transmission on a MEP"
			::= { sleY1731MegControl 21 }

		
--   1.3.6.1.4.1.6296.101.4.12.2.2.22
-- 1.3.6.1.4.1.6296.101.4.12.2.2.22
		-- 1.3.6.1.4.1.6296.101.4.12.2.2.22
		sleY1731MegControlAisInterval OBJECT-TYPE
			SYNTAX INTEGER
				{
				oneSecond(4),
				oneMinute(6)
				}
			MAX-ACCESS read-write
			STATUS current
			DESCRIPTION
				"Indicates the interval between AIS transmissions"
			::= { sleY1731MegControl 22 }

		
--   1.3.6.1.4.1.6296.101.4.12.2.2.23
-- 1.3.6.1.4.1.6296.101.4.12.2.2.23
		-- 1.3.6.1.4.1.6296.101.4.12.2.2.23
		sleY1731MegControlAisLevel OBJECT-TYPE
			SYNTAX Integer32 (1..7)
			MAX-ACCESS read-write
			STATUS current
			DESCRIPTION
				"Indicates the client MEG's level"
			::= { sleY1731MegControl 23 }

		
--   1.3.6.1.4.1.6296.101.4.12.2.2.24
-- 1.3.6.1.4.1.6296.101.4.12.2.2.24
		-- 1.3.6.1.4.1.6296.101.4.12.2.2.24
		sleY1731MegControlAisPriority OBJECT-TYPE
			SYNTAX Integer32 (0..7)
			MAX-ACCESS read-write
			STATUS current
			DESCRIPTION
				"Indicates the AIS Message Priority"
			::= { sleY1731MegControl 24 }

		
--   1.3.6.1.4.1.6296.101.4.12.2.2.25
-- 1.3.6.1.4.1.6296.101.4.12.2.2.25
		-- 1.3.6.1.4.1.6296.101.4.12.2.2.25
		sleY1731MegControlLckEnable OBJECT-TYPE
			SYNTAX INTEGER
				{
				disable(0),
				enable(1)
				}
			MAX-ACCESS read-write
			STATUS current
			DESCRIPTION
				"Enables/Disables ETH-LCK function"
			::= { sleY1731MegControl 25 }

		
--   1.3.6.1.4.1.6296.101.4.12.2.2.26
-- 1.3.6.1.4.1.6296.101.4.12.2.2.26
		-- 1.3.6.1.4.1.6296.101.4.12.2.2.26
		sleY1731MegControlLckTransmitEnable OBJECT-TYPE
			SYNTAX INTEGER
				{
				disable(0),
				enable(1)
				}
			MAX-ACCESS read-write
			STATUS current
			DESCRIPTION
				"Enables/Disables ETH-LCK frame transmission on a MEP"
			::= { sleY1731MegControl 26 }

		
--   1.3.6.1.4.1.6296.101.4.12.2.2.27
-- 1.3.6.1.4.1.6296.101.4.12.2.2.27
		-- 1.3.6.1.4.1.6296.101.4.12.2.2.27
		sleY1731MegControlLckInterval OBJECT-TYPE
			SYNTAX INTEGER
				{
				oneSecond(4),
				oneMinute(6)
				}
			MAX-ACCESS read-write
			STATUS current
			DESCRIPTION
				"Indicates the interval between LCK transmissions"
			::= { sleY1731MegControl 27 }

		
--   1.3.6.1.4.1.6296.101.4.12.2.2.28
-- 1.3.6.1.4.1.6296.101.4.12.2.2.28
		-- 1.3.6.1.4.1.6296.101.4.12.2.2.28
		sleY1731MegControlLckLevel OBJECT-TYPE
			SYNTAX Integer32 (1..7)
			MAX-ACCESS read-write
			STATUS current
			DESCRIPTION
				"Indicates the client MEG's level"
			::= { sleY1731MegControl 28 }

		
--   1.3.6.1.4.1.6296.101.4.12.2.2.29
-- 1.3.6.1.4.1.6296.101.4.12.2.2.29
		-- 1.3.6.1.4.1.6296.101.4.12.2.2.29
		sleY1731MegControlLckPriority OBJECT-TYPE
			SYNTAX Integer32 (0..7)
			MAX-ACCESS read-write
			STATUS current
			DESCRIPTION
				"Indicates the LCK Message Priority"
			::= { sleY1731MegControl 29 }

		
--   1.3.6.1.4.1.6296.101.4.12.2.2.30
-- 1.3.6.1.4.1.6296.101.4.12.2.2.30
		-- 1.3.6.1.4.1.6296.101.4.12.2.2.30
		sleY1731MegControlOutOfService OBJECT-TYPE
			SYNTAX INTEGER
				{
				disable(0),
				enable(1)
				}
			MAX-ACCESS read-write
			STATUS current
			DESCRIPTION
				"Indicates the out-of-service mode"
			::= { sleY1731MegControl 30 }

		
--   1.3.6.1.4.1.6296.101.4.12.2.2.31
-- 1.3.6.1.4.1.6296.101.4.12.2.2.31
		-- 1.3.6.1.4.1.6296.101.4.12.2.2.31
		sleY1731MegControlRapsEnable OBJECT-TYPE
			SYNTAX INTEGER
				{
				disable(0),
				enable(1)
				}
			MAX-ACCESS read-write
			STATUS current
			DESCRIPTION
				"Enables/Disables R-APS node"
			::= { sleY1731MegControl 31 }

		
--   1.3.6.1.4.1.6296.101.4.12.2.2.32
-- 1.3.6.1.4.1.6296.101.4.12.2.2.32
		-- 1.3.6.1.4.1.6296.101.4.12.2.2.32
		sleY1731MegControlRapsRplOwner OBJECT-TYPE
			SYNTAX INTEGER
				{
				false(0),
				true(1)
				}
			MAX-ACCESS read-write
			STATUS current
			DESCRIPTION
				"Indicates the owner of the ring protection link"
			::= { sleY1731MegControl 32 }

		
--   1.3.6.1.4.1.6296.101.4.12.2.2.33
-- 1.3.6.1.4.1.6296.101.4.12.2.2.33
		-- 1.3.6.1.4.1.6296.101.4.12.2.2.33
		sleY1731MegControlRapsEastPort OBJECT-TYPE
			SYNTAX Integer32
			MAX-ACCESS read-write
			STATUS current
			DESCRIPTION
				"Indicates the east port of R-APS node
				Set zero to delete east port"
			::= { sleY1731MegControl 33 }

		
--   1.3.6.1.4.1.6296.101.4.12.2.2.34
-- 1.3.6.1.4.1.6296.101.4.12.2.2.34
		-- 1.3.6.1.4.1.6296.101.4.12.2.2.34
		sleY1731MegControlRapsWestPort OBJECT-TYPE
			SYNTAX Integer32
			MAX-ACCESS read-write
			STATUS current
			DESCRIPTION
				"Indicates the west port of R-APS node
				Set zero to delete west port"
			::= { sleY1731MegControl 34 }

		
--   1.3.6.1.4.1.6296.101.4.12.2.2.35
-- 1.3.6.1.4.1.6296.101.4.12.2.2.35
		-- 1.3.6.1.4.1.6296.101.4.12.2.2.35
		sleY1731MegControlRapsRplPort OBJECT-TYPE
			SYNTAX INTEGER
				{
				none(-1),
				east(0),
				west(1)
				}
			MAX-ACCESS read-write
			STATUS current
			DESCRIPTION
				"Indicates the RPL port of R-APS node"
			::= { sleY1731MegControl 35 }

		
--   1.3.6.1.4.1.6296.101.4.12.2.2.36
-- 1.3.6.1.4.1.6296.101.4.12.2.2.36
		-- 1.3.6.1.4.1.6296.101.4.12.2.2.36
		sleY1731MegControlRapsHoldOffTime OBJECT-TYPE
			SYNTAX Integer32 (0..10000)
			MAX-ACCESS read-write
			STATUS current
			DESCRIPTION
				"Indicates the hold-off time for verifying local SF
				The hold-off time's step must be 100
				"
			::= { sleY1731MegControl 36 }

		
--   1.3.6.1.4.1.6296.101.4.12.2.2.37
-- 1.3.6.1.4.1.6296.101.4.12.2.2.37
		-- 1.3.6.1.4.1.6296.101.4.12.2.2.37
		sleY1731MegControlRapsGuardTime OBJECT-TYPE
			SYNTAX Integer32 (10..2000)
			MAX-ACCESS read-write
			STATUS current
			DESCRIPTION
				"Indicates the guard time for verifying local clear SF
				The guard time's step must be 10
				"
			::= { sleY1731MegControl 37 }

		
--   1.3.6.1.4.1.6296.101.4.12.2.2.38
-- 1.3.6.1.4.1.6296.101.4.12.2.2.38
		-- 1.3.6.1.4.1.6296.101.4.12.2.2.38
		sleY1731MegControlRapsWaitToRestore OBJECT-TYPE
			SYNTAX Integer32 (5..720)
			MAX-ACCESS read-write
			STATUS current
			DESCRIPTION
				"Indicates the wait-to-restore time for verifying remote SF
				"
			::= { sleY1731MegControl 38 }

		
--   1.3.6.1.4.1.6296.101.4.12.2.2.39
-- 1.3.6.1.4.1.6296.101.4.12.2.2.39
		-- 1.3.6.1.4.1.6296.101.4.12.2.2.39
		sleY1731MegControlRapsNonRevertive OBJECT-TYPE
			SYNTAX INTEGER
				{
				false(0),
				true(1)
				}
			MAX-ACCESS read-write
			STATUS current
			DESCRIPTION
				"NonRevertive"
			::= { sleY1731MegControl 39 }

		
--   1.3.6.1.4.1.6296.101.4.12.2.2.40
-- 1.3.6.1.4.1.6296.101.4.12.2.2.40
		-- 1.3.6.1.4.1.6296.101.4.12.2.2.40
		sleY1731MegControlRapsForcedSwitchEast OBJECT-TYPE
			SYNTAX INTEGER
				{
				false(0),
				true(1)
				}
			MAX-ACCESS read-write
			STATUS current
			DESCRIPTION
				"ForcedSwitchEast"
			::= { sleY1731MegControl 40 }

		
--   1.3.6.1.4.1.6296.101.4.12.2.2.41
-- 1.3.6.1.4.1.6296.101.4.12.2.2.41
		-- 1.3.6.1.4.1.6296.101.4.12.2.2.41
		sleY1731MegControlRapsForcedSwitchWest OBJECT-TYPE
			SYNTAX INTEGER
				{
				false(0),
				true(1)
				}
			MAX-ACCESS read-write
			STATUS current
			DESCRIPTION
				"ForcedSwitchWest"
			::= { sleY1731MegControl 41 }

		
--   1.3.6.1.4.1.6296.101.4.12.2.3
-- 1.3.6.1.4.1.6296.101.4.12.2.3
		-- 1.3.6.1.4.1.6296.101.4.12.2.3
		sleY1731MegNotification OBJECT IDENTIFIER ::= { sleY1731Meg 3 }

		
--   1.3.6.1.4.1.6296.101.4.12.2.3.1
-- 1.3.6.1.4.1.6296.101.4.12.2.3.1
		-- 1.3.6.1.4.1.6296.101.4.12.2.3.1
		sleY1731MegCreated NOTIFICATION-TYPE
			OBJECTS { sleY1731MegControlRequest, sleY1731MegControlTimeStamp, sleY1731MegControlReqResult, sleY1731MegControlName, sleY1731MegControlLevel, 
				sleY1731MegControlVid }
			STATUS current
			DESCRIPTION 
				"createY1731Meg"
			::= { sleY1731MegNotification 1 }

		
--   1.3.6.1.4.1.6296.101.4.12.2.3.2
-- 1.3.6.1.4.1.6296.101.4.12.2.3.2
		-- 1.3.6.1.4.1.6296.101.4.12.2.3.2
		sleY1731MegDeleted NOTIFICATION-TYPE
			OBJECTS { sleY1731MegControlRequest, sleY1731MegControlTimeStamp, sleY1731MegControlReqResult, sleY1731MegControlName }
			STATUS current
			DESCRIPTION 
				"deleteY1731Meg"
			::= { sleY1731MegNotification 2 }

		
--   1.3.6.1.4.1.6296.101.4.12.2.3.3
-- 1.3.6.1.4.1.6296.101.4.12.2.3.3
		-- 1.3.6.1.4.1.6296.101.4.12.2.3.3
		sleY1731MegMepEnableChanged NOTIFICATION-TYPE
			OBJECTS { sleY1731MegControlRequest, sleY1731MegControlTimeStamp, sleY1731MegControlReqResult, sleY1731MegControlIndex, sleY1731MegControlName, 
				sleY1731MegControlMepEnable }
			STATUS current
			DESCRIPTION 
				"setY1731MepEnable"
			::= { sleY1731MegNotification 3 }

		
--   1.3.6.1.4.1.6296.101.4.12.2.3.4
-- 1.3.6.1.4.1.6296.101.4.12.2.3.4
		-- 1.3.6.1.4.1.6296.101.4.12.2.3.4
		sleY1731MegCcEnableChanged NOTIFICATION-TYPE
			OBJECTS { sleY1731MegControlRequest, sleY1731MegControlTimeStamp, sleY1731MegControlReqResult, sleY1731MegControlName, sleY1731MegControlCcEnable
				 }
			STATUS current
			DESCRIPTION 
				"setY1731CcEnable"
			::= { sleY1731MegNotification 4 }

		
--   1.3.6.1.4.1.6296.101.4.12.2.3.5
-- 1.3.6.1.4.1.6296.101.4.12.2.3.5
		-- 1.3.6.1.4.1.6296.101.4.12.2.3.5
		sleY1731MegCcProfileChanged NOTIFICATION-TYPE
			OBJECTS { sleY1731MegControlRequest, sleY1731MegControlTimeStamp, sleY1731MegControlReqResult, sleY1731MegControlIndex, sleY1731MegControlName, 
				sleY1731MegControlCcInterval, sleY1731MegControlCcPriority, sleY1731MegControlCcLossThreshold, sleY1731MegControlCcHoldTime }
			STATUS current
			DESCRIPTION 
				"setY1731CcProfile"
			::= { sleY1731MegNotification 5 }

		
--   1.3.6.1.4.1.6296.101.4.12.2.3.6
-- 1.3.6.1.4.1.6296.101.4.12.2.3.6
		-- 1.3.6.1.4.1.6296.101.4.12.2.3.6
		sleY1731MegFaultProfileChanged NOTIFICATION-TYPE
			OBJECTS { sleY1731MegControlRequest, sleY1731MegControlTimeStamp, sleY1731MegControlReqResult, sleY1731MegControlIndex, sleY1731MegControlName, 
				sleY1731MegControlFaultPriority, sleY1731MegControlFaultKeepTime, sleY1731MegControlFaultClearTime }
			STATUS current
			DESCRIPTION 
				"setY1731FaultProfile"
			::= { sleY1731MegNotification 6 }

		
--   1.3.6.1.4.1.6296.101.4.12.2.3.7
-- 1.3.6.1.4.1.6296.101.4.12.2.3.7
		-- 1.3.6.1.4.1.6296.101.4.12.2.3.7
		sleY1731MegXcheckEnableChanged NOTIFICATION-TYPE
			OBJECTS { sleY1731MegControlRequest, sleY1731MegControlTimeStamp, sleY1731MegControlReqResult, sleY1731MegControlIndex, sleY1731MegControlName, 
				sleY1731MegControlXcheckEnable }
			STATUS current
			DESCRIPTION 
				"setY1731XcheckEnable"
			::= { sleY1731MegNotification 7 }

		
--   1.3.6.1.4.1.6296.101.4.12.2.3.8
-- 1.3.6.1.4.1.6296.101.4.12.2.3.8
		-- 1.3.6.1.4.1.6296.101.4.12.2.3.8
		sleY1731MegAisEnableChanged NOTIFICATION-TYPE
			OBJECTS { sleY1731MegControlRequest, sleY1731MegControlTimeStamp, sleY1731MegControlReqResult, sleY1731MegControlIndex, sleY1731MegControlName, 
				sleY1731MegControlAisEnable }
			STATUS current
			DESCRIPTION 
				"setY1731AisEnable"
			::= { sleY1731MegNotification 8 }

		
--   1.3.6.1.4.1.6296.101.4.12.2.3.9
-- 1.3.6.1.4.1.6296.101.4.12.2.3.9
		-- 1.3.6.1.4.1.6296.101.4.12.2.3.9
		sleY1731MegAisTransmitEnableChanged NOTIFICATION-TYPE
			OBJECTS { sleY1731MegControlRequest, sleY1731MegControlTimeStamp, sleY1731MegControlReqResult, sleY1731MegControlIndex, sleY1731MegControlName, 
				sleY1731MegControlAisTransmitEnable }
			STATUS current
			DESCRIPTION 
				"setY1731AisTransmitEnable"
			::= { sleY1731MegNotification 9 }

		
--   1.3.6.1.4.1.6296.101.4.12.2.3.10
-- 1.3.6.1.4.1.6296.101.4.12.2.3.10
		-- 1.3.6.1.4.1.6296.101.4.12.2.3.10
		sleY1731MegAisProfileChanged NOTIFICATION-TYPE
			OBJECTS { sleY1731MegControlRequest, sleY1731MegControlTimeStamp, sleY1731MegControlReqResult, sleY1731MegControlIndex, sleY1731MegControlName, 
				sleY1731MegControlAisInterval, sleY1731MegControlAisLevel, sleY1731MegControlAisPriority }
			STATUS current
			DESCRIPTION 
				"setY1731AisProfile"
			::= { sleY1731MegNotification 10 }

		
--   1.3.6.1.4.1.6296.101.4.12.2.3.11
-- 1.3.6.1.4.1.6296.101.4.12.2.3.11
		-- 1.3.6.1.4.1.6296.101.4.12.2.3.11
		sleY1731MegLckEnableChanged NOTIFICATION-TYPE
			OBJECTS { sleY1731MegControlRequest, sleY1731MegControlTimeStamp, sleY1731MegControlReqResult, sleY1731MegControlIndex, sleY1731MegControlName, 
				sleY1731MegControlLckEnable }
			STATUS current
			DESCRIPTION 
				"setY1731LckEnable"
			::= { sleY1731MegNotification 11 }

		
--   1.3.6.1.4.1.6296.101.4.12.2.3.12
-- 1.3.6.1.4.1.6296.101.4.12.2.3.12
		-- 1.3.6.1.4.1.6296.101.4.12.2.3.12
		sleY1731MegLckTransmitEnableChanged NOTIFICATION-TYPE
			OBJECTS { sleY1731MegControlRequest, sleY1731MegControlTimeStamp, sleY1731MegControlReqResult, sleY1731MegControlIndex, sleY1731MegControlName, 
				sleY1731MegControlLckTransmitEnable }
			STATUS current
			DESCRIPTION 
				"setY1731LckTransmitEnable"
			::= { sleY1731MegNotification 12 }

		
--   1.3.6.1.4.1.6296.101.4.12.2.3.13
-- 1.3.6.1.4.1.6296.101.4.12.2.3.13
		-- 1.3.6.1.4.1.6296.101.4.12.2.3.13
		sleY1731MegLckProfileChanged NOTIFICATION-TYPE
			OBJECTS { sleY1731MegControlRequest, sleY1731MegControlTimeStamp, sleY1731MegControlReqResult, sleY1731MegControlIndex, sleY1731MegControlName, 
				sleY1731MegControlLckInterval, sleY1731MegControlLckLevel, sleY1731MegControlLckPriority }
			STATUS current
			DESCRIPTION 
				"setY1731LckProfile"
			::= { sleY1731MegNotification 13 }

		
--   1.3.6.1.4.1.6296.101.4.12.2.3.14
-- 1.3.6.1.4.1.6296.101.4.12.2.3.14
		-- 1.3.6.1.4.1.6296.101.4.12.2.3.14
		sleY1731MegOutOfServiceChanged NOTIFICATION-TYPE
			OBJECTS { sleY1731MegControlRequest, sleY1731MegControlTimeStamp, sleY1731MegControlReqResult, sleY1731MegControlIndex, sleY1731MegControlName, 
				sleY1731MegControlOutOfService }
			STATUS current
			DESCRIPTION 
				"setY1731OutOfService"
			::= { sleY1731MegNotification 14 }

		
--   1.3.6.1.4.1.6296.101.4.12.2.3.15
-- 1.3.6.1.4.1.6296.101.4.12.2.3.15
		-- 1.3.6.1.4.1.6296.101.4.12.2.3.15
		sleY1731MegRapsEnableChanged NOTIFICATION-TYPE
			OBJECTS { sleY1731MegControlRequest, sleY1731MegControlTimeStamp, sleY1731MegControlReqResult, sleY1731MegControlIndex, sleY1731MegControlName, 
				sleY1731MegControlRapsEnable }
			STATUS current
			DESCRIPTION 
				"setY1731RapsEnable"
			::= { sleY1731MegNotification 15 }

		
--   1.3.6.1.4.1.6296.101.4.12.2.3.16
-- 1.3.6.1.4.1.6296.101.4.12.2.3.16
		-- 1.3.6.1.4.1.6296.101.4.12.2.3.16
		sleY1731MegRapsRingportsChanged NOTIFICATION-TYPE
			OBJECTS { sleY1731MegControlRequest, sleY1731MegControlTimeStamp, sleY1731MegControlReqResult, sleY1731MegControlIndex, sleY1731MegControlName, 
				sleY1731MegControlRapsEastPort, sleY1731MegControlRapsWestPort }
			STATUS current
			DESCRIPTION 
				"setY1731RapsProfile"
			::= { sleY1731MegNotification 16 }

		
--   1.3.6.1.4.1.6296.101.4.12.2.3.17
-- 1.3.6.1.4.1.6296.101.4.12.2.3.17
		-- 1.3.6.1.4.1.6296.101.4.12.2.3.17
		sleY1731MegRapsRplPortChanged NOTIFICATION-TYPE
			OBJECTS { sleY1731MegControlRequest, sleY1731MegControlTimeStamp, sleY1731MegControlReqResult, sleY1731MegControlIndex, sleY1731MegControlName, 
				sleY1731MegControlRapsRplPort }
			STATUS current
			DESCRIPTION 
				"Description."
			::= { sleY1731MegNotification 17 }

		
--   1.3.6.1.4.1.6296.101.4.12.2.3.18
-- 1.3.6.1.4.1.6296.101.4.12.2.3.18
		-- 1.3.6.1.4.1.6296.101.4.12.2.3.18
		sleY1731MegRapsRplOwnerChanged NOTIFICATION-TYPE
			OBJECTS { sleY1731MegControlRequest, sleY1731MegControlTimeStamp, sleY1731MegControlReqResult, sleY1731MegControlIndex, sleY1731MegControlName, 
				sleY1731MegControlRapsRplOwner }
			STATUS current
			DESCRIPTION 
				"Description."
			::= { sleY1731MegNotification 18 }

		
--   1.3.6.1.4.1.6296.101.4.12.2.3.19
-- 1.3.6.1.4.1.6296.101.4.12.2.3.19
		-- 1.3.6.1.4.1.6296.101.4.12.2.3.19
		sleY1731MegRapsTimerChanged NOTIFICATION-TYPE
			OBJECTS { sleY1731MegControlRequest, sleY1731MegControlTimeStamp, sleY1731MegControlReqResult, sleY1731MegControlIndex, sleY1731MegControlName, 
				sleY1731MegControlRapsHoldOffTime, sleY1731MegControlRapsGuardTime, sleY1731MegControlRapsWaitToRestore }
			STATUS current
			DESCRIPTION 
				"Description."
			::= { sleY1731MegNotification 19 }

		
--   1.3.6.1.4.1.6296.101.4.12.2.3.20
-- 1.3.6.1.4.1.6296.101.4.12.2.3.20
		-- 1.3.6.1.4.1.6296.101.4.12.2.3.20
		sleY1731MegRemoteMepDestroyed NOTIFICATION-TYPE
			OBJECTS { sleY1731MegControlRequest, sleY1731MegControlTimeStamp, sleY1731MegControlReqResult, sleY1731MegControlIndex }
			STATUS current
			DESCRIPTION 
				"destroyRemoteMep"
			::= { sleY1731MegNotification 20 }

		
--   1.3.6.1.4.1.6296.101.4.12.2.3.21
-- 1.3.6.1.4.1.6296.101.4.12.2.3.21
		-- 1.3.6.1.4.1.6296.101.4.12.2.3.21
		sleY1731MegErrorDestroyed NOTIFICATION-TYPE
			OBJECTS { sleY1731MegControlRequest, sleY1731MegControlTimeStamp, sleY1731MegControlReqResult, sleY1731MegControlIndex }
			STATUS current
			DESCRIPTION 
				"destroyError"
			::= { sleY1731MegNotification 21 }

		
--   1.3.6.1.4.1.6296.101.4.12.2.3.22
-- 1.3.6.1.4.1.6296.101.4.12.2.3.22
		-- 1.3.6.1.4.1.6296.101.4.12.2.3.22
		sleY1731MegRapsNonRevertiveChanged NOTIFICATION-TYPE
			OBJECTS { sleY1731MegControlRequest, sleY1731MegControlTimeStamp, sleY1731MegControlReqResult, sleY1731MegControlName, sleY1731MegControlRapsNonRevertive
				 }
			STATUS current
			DESCRIPTION 
				"sleY1731MegRapsNonRevertiveChanged"
			::= { sleY1731MegNotification 22 }

		
--   1.3.6.1.4.1.6296.101.4.12.2.3.23
-- 1.3.6.1.4.1.6296.101.4.12.2.3.23
		-- 1.3.6.1.4.1.6296.101.4.12.2.3.23
		sleY1731MegRapsForcedSwitchEastChanged NOTIFICATION-TYPE
			OBJECTS { sleY1731MegControlRequest, sleY1731MegControlTimeStamp, sleY1731MegControlReqResult, sleY1731MegControlName, sleY1731MegControlRapsForcedSwitchEast
				 }
			STATUS current
			DESCRIPTION 
				"sleY1731MegRapsForcedSwitchEastChanged"
			::= { sleY1731MegNotification 23 }

		
--   1.3.6.1.4.1.6296.101.4.12.2.3.24
-- 1.3.6.1.4.1.6296.101.4.12.2.3.24
		-- 1.3.6.1.4.1.6296.101.4.12.2.3.24
		sleY1731MegRapsForcedSwitchWestChanged NOTIFICATION-TYPE
			OBJECTS { sleY1731MegControlRequest, sleY1731MegControlTimeStamp, sleY1731MegControlReqResult, sleY1731MegControlName, sleY1731MegControlRapsForcedSwitchWest
				 }
			STATUS current
			DESCRIPTION 
				"sleY1731MegRapsForcedSwitchWestChanged"
			::= { sleY1731MegNotification 24 }

		
--   1.3.6.1.4.1.6296.101.4.12.3
-- 1.3.6.1.4.1.6296.101.4.12.3
		-- 1.3.6.1.4.1.6296.101.4.12.3
		sleY1731Mep OBJECT IDENTIFIER ::= { sleY1731Oam 3 }

		
--   1.3.6.1.4.1.6296.101.4.12.3.1
-- 1.3.6.1.4.1.6296.101.4.12.3.1
		-- 1.3.6.1.4.1.6296.101.4.12.3.1
		sleY1731MepTable OBJECT-TYPE
			SYNTAX SEQUENCE OF SleY1731MepEntry
			MAX-ACCESS not-accessible
			STATUS current
			DESCRIPTION
				"Description."
			::= { sleY1731Mep 1 }

		
--   1.3.6.1.4.1.6296.101.4.12.3.1.1
-- 1.3.6.1.4.1.6296.101.4.12.3.1.1
		-- 1.3.6.1.4.1.6296.101.4.12.3.1.1
		sleY1731MepEntry OBJECT-TYPE
			SYNTAX SleY1731MepEntry
			MAX-ACCESS not-accessible
			STATUS current
			DESCRIPTION
				"Description."
			INDEX { sleY1731MegIndex, sleY1731MepIdentifier }
			::= { sleY1731MepTable 1 }

		
		SleY1731MepEntry ::=
			SEQUENCE { 
				sleY1731MepIdentifier
					Integer32,
				sleY1731MepIfIndex
					Integer32,
				sleY1731MepDirection
					INTEGER,
				sleY1731MepEnable
					INTEGER,
				sleY1731MepFngState
					INTEGER,
				sleY1731MepCcEnable
					INTEGER,
				sleY1731MepMacAddress
					OCTET STRING,
				sleY1731MepFaultPriority
					INTEGER,
				sleY1731MepFaultKeepTime
					Integer32,
				sleY1731MepFaultClearTime
					Integer32,
				sleY1731MepHighestPrDefect
					INTEGER,
				sleY1731MepAisEnable
					INTEGER,
				sleY1731MepAisTransmitEnable
					INTEGER,
				sleY1731MepLckEnable
					INTEGER,
				sleY1731MepLckTransmitEnable
					INTEGER,
				sleY1731MepOutOfService
					INTEGER,
				sleY1731MepDlmEnabledRmep
					Integer32,
				sleY1731MepDefects
					BITS,
				sleY1731MepCcmSequenceErrors
					Counter32,
				sleY1731MepCciSentCcms
					Counter32,
				sleY1731MepNextLbmTransId
					Integer32,
				sleY1731MepLbSuccessRate
					Integer32,
				sleY1731MepLbRoundtripMin
					Counter32,
				sleY1731MepLbRoundtripMax
					Counter32,
				sleY1731MepLbRoundtripAvg
					Counter32,
				sleY1731MepLbrIn
					Counter32,
				sleY1731MepLbrInOutOfOrder
					Counter32,
				sleY1731MepTstLbrInBitError
					Counter32,
				sleY1731MepTstLbrInCrcError
					Counter32,
				sleY1731MepLtmNextSeqNumber
					Integer32,
				sleY1731MepUnexpLtrIn
					Counter32,
				sleY1731MepLbrOut
					Counter32,
				sleY1731MepTmLbmCount
					Integer32,
				sleY1731MepTmLbrCount
					Integer32,
				sleY1731MepTmLbrFirstLostId
					Integer32,
				sleY1731MepTmLbrMaxRate
					Integer32,
				sleY1731MepTmTstCount
					Integer32,
				sleY1731MepCcmFrameLossNearMin
					Integer32,
				sleY1731MepCcmFrameLossNearMax
					Integer32,
				sleY1731MepCcmFrameLossNearSum
					Integer32,
				sleY1731MepCcmFrameLossFarMin
					Integer32,
				sleY1731MepCcmFrameLossFarMax
					Integer32,
				sleY1731MepCcmFrameLossFarSum
					Integer32,
				sleY1731MepPmEnable
					INTEGER,
				sleY1731MepCcmFrameLossNearRatio
					Integer32,
				sleY1731MepCcmFrameLossNearAvgRatio
					Integer32,
				sleY1731MepCcmFrameLossFarRatio
					Integer32,
				sleY1731MepCcmFrameLossFarAvgRatio
					Integer32,
				sleY1731MepRllcf
					INTEGER,
				sleY1731MepRllcfHoldOff
					Integer32,
				sleY1731MepRllcfGuardTime
					Integer32
			 }

--   1.3.6.1.4.1.6296.101.4.12.3.1.1.1
-- 1.3.6.1.4.1.6296.101.4.12.3.1.1.1
		-- 1.3.6.1.4.1.6296.101.4.12.3.1.1.1
		sleY1731MepIdentifier OBJECT-TYPE
			SYNTAX Integer32 (1..8191)
			MAX-ACCESS read-only
			STATUS current
			DESCRIPTION
				"MEP Id"
			::= { sleY1731MepEntry 1 }

		
--   1.3.6.1.4.1.6296.101.4.12.3.1.1.2
-- 1.3.6.1.4.1.6296.101.4.12.3.1.1.2
		-- 1.3.6.1.4.1.6296.101.4.12.3.1.1.2
		sleY1731MepIfIndex OBJECT-TYPE
			SYNTAX Integer32
			MAX-ACCESS read-only
			STATUS current
			DESCRIPTION
				"Brige Port Index whitch the MEP is attached"
			::= { sleY1731MepEntry 2 }

		
--   1.3.6.1.4.1.6296.101.4.12.3.1.1.3
-- 1.3.6.1.4.1.6296.101.4.12.3.1.1.3
		-- 1.3.6.1.4.1.6296.101.4.12.3.1.1.3
		sleY1731MepDirection OBJECT-TYPE
			SYNTAX INTEGER
				{
				down(0),
				up(1)
				}
			MAX-ACCESS read-only
			STATUS current
			DESCRIPTION
				"The direction in which the MEP faces on the Bridge port"
			::= { sleY1731MepEntry 3 }

		
--   1.3.6.1.4.1.6296.101.4.12.3.1.1.4
-- 1.3.6.1.4.1.6296.101.4.12.3.1.1.4
		-- 1.3.6.1.4.1.6296.101.4.12.3.1.1.4
		sleY1731MepEnable OBJECT-TYPE
			SYNTAX INTEGER
				{
				disable(0),
				enable(1)
				}
			MAX-ACCESS read-only
			STATUS current
			DESCRIPTION
				"Administrative state of the MEP"
			::= { sleY1731MepEntry 4 }

		
--   1.3.6.1.4.1.6296.101.4.12.3.1.1.5
-- 1.3.6.1.4.1.6296.101.4.12.3.1.1.5
		-- 1.3.6.1.4.1.6296.101.4.12.3.1.1.5
		sleY1731MepFngState OBJECT-TYPE
			SYNTAX INTEGER
				{
				reset(1),
				defect(2),
				reportDefect(3),
				defectReported(4),
				defectCearing(5),
				defectCleared(6)
				}
			MAX-ACCESS read-only
			STATUS current
			DESCRIPTION
				"Current state of the MEP Fault Notification Generator State Machine"
			::= { sleY1731MepEntry 5 }

		
--   1.3.6.1.4.1.6296.101.4.12.3.1.1.6
-- 1.3.6.1.4.1.6296.101.4.12.3.1.1.6
		-- 1.3.6.1.4.1.6296.101.4.12.3.1.1.6
		sleY1731MepCcEnable OBJECT-TYPE
			SYNTAX INTEGER
				{
				disable(0),
				enable(1)
				}
			MAX-ACCESS read-only
			STATUS current
			DESCRIPTION
				"If set to true, the MEP will generate CCM messages"
			::= { sleY1731MepEntry 6 }

		
--   1.3.6.1.4.1.6296.101.4.12.3.1.1.7
-- 1.3.6.1.4.1.6296.101.4.12.3.1.1.7
		-- 1.3.6.1.4.1.6296.101.4.12.3.1.1.7
		sleY1731MepMacAddress OBJECT-TYPE
			SYNTAX OCTET STRING (SIZE (6))
			MAX-ACCESS read-only
			STATUS current
			DESCRIPTION
				"MAC address of the MEP"
			::= { sleY1731MepEntry 7 }

		
--   1.3.6.1.4.1.6296.101.4.12.3.1.1.8
-- 1.3.6.1.4.1.6296.101.4.12.3.1.1.8
		-- 1.3.6.1.4.1.6296.101.4.12.3.1.1.8
		sleY1731MepFaultPriority OBJECT-TYPE
			SYNTAX INTEGER
				{
				rdi(1),
				loc(2),
				unp(3),
				unm(4),
				mmg(5),
				unl(6),
				ais(7),
				lck(8)
				}
			MAX-ACCESS read-only
			STATUS current
			DESCRIPTION
				"An integer value specifying the lowest priority defect that is allowed to generate fault alarm"
			::= { sleY1731MepEntry 8 }

		
--   1.3.6.1.4.1.6296.101.4.12.3.1.1.9
-- 1.3.6.1.4.1.6296.101.4.12.3.1.1.9
		-- 1.3.6.1.4.1.6296.101.4.12.3.1.1.9
		sleY1731MepFaultKeepTime OBJECT-TYPE
			SYNTAX Integer32 (0..1023)
			MAX-ACCESS read-only
			STATUS current
			DESCRIPTION
				"The time that defects must be present before a Fault Alarm is issued"
			::= { sleY1731MepEntry 9 }

		
--   1.3.6.1.4.1.6296.101.4.12.3.1.1.10
-- 1.3.6.1.4.1.6296.101.4.12.3.1.1.10
		-- 1.3.6.1.4.1.6296.101.4.12.3.1.1.10
		sleY1731MepFaultClearTime OBJECT-TYPE
			SYNTAX Integer32 (0..1023)
			MAX-ACCESS read-only
			STATUS current
			DESCRIPTION
				"The time that defects must be absent before resetting a Fault Alarm"
			::= { sleY1731MepEntry 10 }

		
--   1.3.6.1.4.1.6296.101.4.12.3.1.1.11
-- 1.3.6.1.4.1.6296.101.4.12.3.1.1.11
		-- 1.3.6.1.4.1.6296.101.4.12.3.1.1.11
		sleY1731MepHighestPrDefect OBJECT-TYPE
			SYNTAX INTEGER
				{
				rdi(1),
				loc(2),
				unp(3),
				unm(4),
				mmg(5),
				unl(6),
				ais(7),
				lck(8)
				}
			MAX-ACCESS read-only
			STATUS current
			DESCRIPTION
				"The highest priority defect that has been present since the MEPs Fault Notification Generator State Machine was last in the FNG_RESET state"
			::= { sleY1731MepEntry 11 }

		
--   1.3.6.1.4.1.6296.101.4.12.3.1.1.12
-- 1.3.6.1.4.1.6296.101.4.12.3.1.1.12
		-- 1.3.6.1.4.1.6296.101.4.12.3.1.1.12
		sleY1731MepAisEnable OBJECT-TYPE
			SYNTAX INTEGER
				{
				disable(0),
				enable(1)
				}
			MAX-ACCESS read-only
			STATUS current
			DESCRIPTION
				"If set to true, the AIS function for the MEP is enabled"
			::= { sleY1731MepEntry 12 }

		
--   1.3.6.1.4.1.6296.101.4.12.3.1.1.13
-- 1.3.6.1.4.1.6296.101.4.12.3.1.1.13
		-- 1.3.6.1.4.1.6296.101.4.12.3.1.1.13
		sleY1731MepAisTransmitEnable OBJECT-TYPE
			SYNTAX INTEGER
				{
				disable(0),
				enable(1)
				}
			MAX-ACCESS read-only
			STATUS current
			DESCRIPTION
				"If set to true, the MEP can generate AIS messages"
			::= { sleY1731MepEntry 13 }

		
--   1.3.6.1.4.1.6296.101.4.12.3.1.1.14
-- 1.3.6.1.4.1.6296.101.4.12.3.1.1.14
		-- 1.3.6.1.4.1.6296.101.4.12.3.1.1.14
		sleY1731MepLckEnable OBJECT-TYPE
			SYNTAX INTEGER
				{
				disable(0),
				enable(1)
				}
			MAX-ACCESS read-only
			STATUS current
			DESCRIPTION
				"If set to true, the LCK function for the MEP is enabled"
			::= { sleY1731MepEntry 14 }

		
--   1.3.6.1.4.1.6296.101.4.12.3.1.1.15
-- 1.3.6.1.4.1.6296.101.4.12.3.1.1.15
		-- 1.3.6.1.4.1.6296.101.4.12.3.1.1.15
		sleY1731MepLckTransmitEnable OBJECT-TYPE
			SYNTAX INTEGER
				{
				disable(0),
				enable(1)
				}
			MAX-ACCESS read-only
			STATUS current
			DESCRIPTION
				"If set to true, the MEP can generate LCK messages"
			::= { sleY1731MepEntry 15 }

		
--   1.3.6.1.4.1.6296.101.4.12.3.1.1.16
-- 1.3.6.1.4.1.6296.101.4.12.3.1.1.16
		-- 1.3.6.1.4.1.6296.101.4.12.3.1.1.16
		sleY1731MepOutOfService OBJECT-TYPE
			SYNTAX INTEGER
				{
				disable(0),
				enable(1)
				}
			MAX-ACCESS read-only
			STATUS current
			DESCRIPTION
				"If set to true, the MEP is in out-of-service."
			::= { sleY1731MepEntry 16 }

		
--   1.3.6.1.4.1.6296.101.4.12.3.1.1.17
-- 1.3.6.1.4.1.6296.101.4.12.3.1.1.17
		-- 1.3.6.1.4.1.6296.101.4.12.3.1.1.17
		sleY1731MepDlmEnabledRmep OBJECT-TYPE
			SYNTAX Integer32 (0..8191)
			MAX-ACCESS read-only
			STATUS current
			DESCRIPTION
				"The RMEP identifier enabled DLM functin
				If set to zero, disabled DLM function.
				"
			::= { sleY1731MepEntry 17 }

		
--   1.3.6.1.4.1.6296.101.4.12.3.1.1.18
-- 1.3.6.1.4.1.6296.101.4.12.3.1.1.18
		-- 1.3.6.1.4.1.6296.101.4.12.3.1.1.18
		sleY1731MepDefects OBJECT-TYPE
			SYNTAX BITS
				{
				rdi(0),
				loc(1),
				unp(2),
				unm(3),
				mmg(4),
				unl(5),
				ais(6),
				lck(7)
				}
			MAX-ACCESS read-only
			STATUS current
			DESCRIPTION
				"A vector of Boolean defect conditions"
			::= { sleY1731MepEntry 18 }

		
--   1.3.6.1.4.1.6296.101.4.12.3.1.1.19
-- 1.3.6.1.4.1.6296.101.4.12.3.1.1.19
		-- 1.3.6.1.4.1.6296.101.4.12.3.1.1.19
		sleY1731MepCcmSequenceErrors OBJECT-TYPE
			SYNTAX Counter32
			MAX-ACCESS read-only
			STATUS current
			DESCRIPTION
				"The total number of out-of-sequence CCMs received from all remote MEPs"
			::= { sleY1731MepEntry 19 }

		
--   1.3.6.1.4.1.6296.101.4.12.3.1.1.20
-- 1.3.6.1.4.1.6296.101.4.12.3.1.1.20
		-- 1.3.6.1.4.1.6296.101.4.12.3.1.1.20
		sleY1731MepCciSentCcms OBJECT-TYPE
			SYNTAX Counter32
			MAX-ACCESS read-only
			STATUS current
			DESCRIPTION
				"Total number of Continuity Check messages transmitted"
			::= { sleY1731MepEntry 20 }

		
--   1.3.6.1.4.1.6296.101.4.12.3.1.1.21
-- 1.3.6.1.4.1.6296.101.4.12.3.1.1.21
		-- 1.3.6.1.4.1.6296.101.4.12.3.1.1.21
		sleY1731MepNextLbmTransId OBJECT-TYPE
			SYNTAX Integer32
			MAX-ACCESS read-only
			STATUS current
			DESCRIPTION
				"Next sequence number/transaction identifier to be sent in a Loopback message"
			::= { sleY1731MepEntry 21 }

		
--   1.3.6.1.4.1.6296.101.4.12.3.1.1.22
-- 1.3.6.1.4.1.6296.101.4.12.3.1.1.22
		-- 1.3.6.1.4.1.6296.101.4.12.3.1.1.22
		sleY1731MepLbSuccessRate OBJECT-TYPE
			SYNTAX Integer32
			MAX-ACCESS read-only
			STATUS current
			DESCRIPTION
				"Loopback Success rate"
			::= { sleY1731MepEntry 22 }

		
--   1.3.6.1.4.1.6296.101.4.12.3.1.1.23
-- 1.3.6.1.4.1.6296.101.4.12.3.1.1.23
		-- 1.3.6.1.4.1.6296.101.4.12.3.1.1.23
		sleY1731MepLbRoundtripMin OBJECT-TYPE
			SYNTAX Counter32
			MAX-ACCESS read-only
			STATUS current
			DESCRIPTION
				"The minimum round trip time of Loopback message"
			::= { sleY1731MepEntry 23 }

		
--   1.3.6.1.4.1.6296.101.4.12.3.1.1.24
-- 1.3.6.1.4.1.6296.101.4.12.3.1.1.24
		-- 1.3.6.1.4.1.6296.101.4.12.3.1.1.24
		sleY1731MepLbRoundtripMax OBJECT-TYPE
			SYNTAX Counter32
			MAX-ACCESS read-only
			STATUS current
			DESCRIPTION
				"The maximum round trip time of Loopback message"
			::= { sleY1731MepEntry 24 }

		
--   1.3.6.1.4.1.6296.101.4.12.3.1.1.25
-- 1.3.6.1.4.1.6296.101.4.12.3.1.1.25
		-- 1.3.6.1.4.1.6296.101.4.12.3.1.1.25
		sleY1731MepLbRoundtripAvg OBJECT-TYPE
			SYNTAX Counter32
			MAX-ACCESS read-only
			STATUS current
			DESCRIPTION
				"The average round trip time of Loopback message"
			::= { sleY1731MepEntry 25 }

		
--   1.3.6.1.4.1.6296.101.4.12.3.1.1.26
-- 1.3.6.1.4.1.6296.101.4.12.3.1.1.26
		-- 1.3.6.1.4.1.6296.101.4.12.3.1.1.26
		sleY1731MepLbrIn OBJECT-TYPE
			SYNTAX Counter32
			MAX-ACCESS read-only
			STATUS current
			DESCRIPTION
				"Total number of valid, in-order Loopback Replies received"
			::= { sleY1731MepEntry 26 }

		
--   1.3.6.1.4.1.6296.101.4.12.3.1.1.27
-- 1.3.6.1.4.1.6296.101.4.12.3.1.1.27
		-- 1.3.6.1.4.1.6296.101.4.12.3.1.1.27
		sleY1731MepLbrInOutOfOrder OBJECT-TYPE
			SYNTAX Counter32
			MAX-ACCESS read-only
			STATUS current
			DESCRIPTION
				"The total number of valid, out-of-order Loopback Replies received"
			::= { sleY1731MepEntry 27 }

		
--   1.3.6.1.4.1.6296.101.4.12.3.1.1.28
-- 1.3.6.1.4.1.6296.101.4.12.3.1.1.28
		-- 1.3.6.1.4.1.6296.101.4.12.3.1.1.28
		sleY1731MepTstLbrInBitError OBJECT-TYPE
			SYNTAX Counter32
			MAX-ACCESS read-only
			STATUS current
			DESCRIPTION
				"The total number of invalid, bit-error Loopback Replies received for diagnostic test"
			::= { sleY1731MepEntry 28 }

		
--   1.3.6.1.4.1.6296.101.4.12.3.1.1.29
-- 1.3.6.1.4.1.6296.101.4.12.3.1.1.29
		-- 1.3.6.1.4.1.6296.101.4.12.3.1.1.29
		sleY1731MepTstLbrInCrcError OBJECT-TYPE
			SYNTAX Counter32
			MAX-ACCESS read-only
			STATUS current
			DESCRIPTION
				"The total number of invalid, crc-error Loopback Replies received for diagnostic test"
			::= { sleY1731MepEntry 29 }

		
--   1.3.6.1.4.1.6296.101.4.12.3.1.1.30
-- 1.3.6.1.4.1.6296.101.4.12.3.1.1.30
		-- 1.3.6.1.4.1.6296.101.4.12.3.1.1.30
		sleY1731MepLtmNextSeqNumber OBJECT-TYPE
			SYNTAX Integer32
			MAX-ACCESS read-only
			STATUS current
			DESCRIPTION
				"Next transaction identifier/sequence number to be sent in a Linktrace message."
			::= { sleY1731MepEntry 30 }

		
--   1.3.6.1.4.1.6296.101.4.12.3.1.1.31
-- 1.3.6.1.4.1.6296.101.4.12.3.1.1.31
		-- 1.3.6.1.4.1.6296.101.4.12.3.1.1.31
		sleY1731MepUnexpLtrIn OBJECT-TYPE
			SYNTAX Counter32
			MAX-ACCESS read-only
			STATUS current
			DESCRIPTION
				"The total number of unexpected LTRs received"
			::= { sleY1731MepEntry 31 }

		
--   1.3.6.1.4.1.6296.101.4.12.3.1.1.32
-- 1.3.6.1.4.1.6296.101.4.12.3.1.1.32
		-- 1.3.6.1.4.1.6296.101.4.12.3.1.1.32
		sleY1731MepLbrOut OBJECT-TYPE
			SYNTAX Counter32
			MAX-ACCESS read-only
			STATUS current
			DESCRIPTION
				"Total number of Loopback Replies transmitted"
			::= { sleY1731MepEntry 32 }

		
--   1.3.6.1.4.1.6296.101.4.12.3.1.1.33
-- 1.3.6.1.4.1.6296.101.4.12.3.1.1.33
		-- 1.3.6.1.4.1.6296.101.4.12.3.1.1.33
		sleY1731MepTmLbmCount OBJECT-TYPE
			SYNTAX Integer32
			MAX-ACCESS read-only
			STATUS current
			DESCRIPTION
				"Indicates the count of LBM frame for the throughput-measurement"
			::= { sleY1731MepEntry 33 }

		
--   1.3.6.1.4.1.6296.101.4.12.3.1.1.34
-- 1.3.6.1.4.1.6296.101.4.12.3.1.1.34
		-- 1.3.6.1.4.1.6296.101.4.12.3.1.1.34
		sleY1731MepTmLbrCount OBJECT-TYPE
			SYNTAX Integer32
			MAX-ACCESS read-only
			STATUS current
			DESCRIPTION
				"Indicates the count of LBM frame for the throughput-measurement"
			::= { sleY1731MepEntry 34 }

		
--   1.3.6.1.4.1.6296.101.4.12.3.1.1.35
-- 1.3.6.1.4.1.6296.101.4.12.3.1.1.35
		-- 1.3.6.1.4.1.6296.101.4.12.3.1.1.35
		sleY1731MepTmLbrFirstLostId OBJECT-TYPE
			SYNTAX Integer32
			MAX-ACCESS read-only
			STATUS current
			DESCRIPTION
				"Indicates the transaction identifier of first lost LBR frame for the throughput-measurement"
			::= { sleY1731MepEntry 35 }

		
--   1.3.6.1.4.1.6296.101.4.12.3.1.1.36
-- 1.3.6.1.4.1.6296.101.4.12.3.1.1.36
		-- 1.3.6.1.4.1.6296.101.4.12.3.1.1.36
		sleY1731MepTmLbrMaxRate OBJECT-TYPE
			SYNTAX Integer32
			MAX-ACCESS read-only
			STATUS current
			DESCRIPTION
				"Indicates the maximum transmission rate"
			::= { sleY1731MepEntry 36 }

		
--   1.3.6.1.4.1.6296.101.4.12.3.1.1.37
-- 1.3.6.1.4.1.6296.101.4.12.3.1.1.37
		-- 1.3.6.1.4.1.6296.101.4.12.3.1.1.37
		sleY1731MepTmTstCount OBJECT-TYPE
			SYNTAX Integer32
			MAX-ACCESS read-only
			STATUS current
			DESCRIPTION
				"Indicates the count of TST message for the throughput-measurement"
			::= { sleY1731MepEntry 37 }

		
--   1.3.6.1.4.1.6296.101.4.12.3.1.1.38
-- 1.3.6.1.4.1.6296.101.4.12.3.1.1.38
		-- 1.3.6.1.4.1.6296.101.4.12.3.1.1.38
		sleY1731MepCcmFrameLossNearMin OBJECT-TYPE
			SYNTAX Integer32
			MAX-ACCESS read-only
			STATUS current
			DESCRIPTION
				"Indicates the minimum of dual-ended near-end frame loss"
			::= { sleY1731MepEntry 38 }

		
--   1.3.6.1.4.1.6296.101.4.12.3.1.1.39
-- 1.3.6.1.4.1.6296.101.4.12.3.1.1.39
		-- 1.3.6.1.4.1.6296.101.4.12.3.1.1.39
		sleY1731MepCcmFrameLossNearMax OBJECT-TYPE
			SYNTAX Integer32
			MAX-ACCESS read-only
			STATUS current
			DESCRIPTION
				"Indicates the maximum of dual-ended near-end frame loss"
			::= { sleY1731MepEntry 39 }

		
--   1.3.6.1.4.1.6296.101.4.12.3.1.1.40
-- 1.3.6.1.4.1.6296.101.4.12.3.1.1.40
		-- 1.3.6.1.4.1.6296.101.4.12.3.1.1.40
		sleY1731MepCcmFrameLossNearSum OBJECT-TYPE
			SYNTAX Integer32
			MAX-ACCESS read-only
			STATUS current
			DESCRIPTION
				"Indicates the sum of dual-ended near-end frame loss"
			::= { sleY1731MepEntry 40 }

		
--   1.3.6.1.4.1.6296.101.4.12.3.1.1.41
-- 1.3.6.1.4.1.6296.101.4.12.3.1.1.41
		-- 1.3.6.1.4.1.6296.101.4.12.3.1.1.41
		sleY1731MepCcmFrameLossFarMin OBJECT-TYPE
			SYNTAX Integer32
			MAX-ACCESS read-only
			STATUS current
			DESCRIPTION
				"Indicates the minimum of dual-ended far-end frame loss"
			::= { sleY1731MepEntry 41 }

		
--   1.3.6.1.4.1.6296.101.4.12.3.1.1.42
-- 1.3.6.1.4.1.6296.101.4.12.3.1.1.42
		-- 1.3.6.1.4.1.6296.101.4.12.3.1.1.42
		sleY1731MepCcmFrameLossFarMax OBJECT-TYPE
			SYNTAX Integer32
			MAX-ACCESS read-only
			STATUS current
			DESCRIPTION
				"Indicates the maximum of dual-ended far-end frame loss"
			::= { sleY1731MepEntry 42 }

		
--   1.3.6.1.4.1.6296.101.4.12.3.1.1.43
-- 1.3.6.1.4.1.6296.101.4.12.3.1.1.43
		-- 1.3.6.1.4.1.6296.101.4.12.3.1.1.43
		sleY1731MepCcmFrameLossFarSum OBJECT-TYPE
			SYNTAX Integer32
			MAX-ACCESS read-only
			STATUS current
			DESCRIPTION
				"Indicates the sum of dual-ended far-end frame loss"
			::= { sleY1731MepEntry 43 }

		
--   1.3.6.1.4.1.6296.101.4.12.3.1.1.44
-- 1.3.6.1.4.1.6296.101.4.12.3.1.1.44
		-- 1.3.6.1.4.1.6296.101.4.12.3.1.1.44
		sleY1731MepPmEnable OBJECT-TYPE
			SYNTAX INTEGER
				{
				disable(0),
				enable(1)
				}
			MAX-ACCESS read-only
			STATUS current
			DESCRIPTION
				"If set to true, the PM(performance monitoring) of the MEP is enabled"
			::= { sleY1731MepEntry 44 }

		
--   1.3.6.1.4.1.6296.101.4.12.3.1.1.45
-- 1.3.6.1.4.1.6296.101.4.12.3.1.1.45
		-- 1.3.6.1.4.1.6296.101.4.12.3.1.1.45
		sleY1731MepCcmFrameLossNearRatio OBJECT-TYPE
			SYNTAX Integer32
			MAX-ACCESS read-only
			STATUS current
			DESCRIPTION
				"Indicates the ratio of dual-ended near-end frame loss"
			::= { sleY1731MepEntry 45 }

		
--   1.3.6.1.4.1.6296.101.4.12.3.1.1.46
-- 1.3.6.1.4.1.6296.101.4.12.3.1.1.46
		-- 1.3.6.1.4.1.6296.101.4.12.3.1.1.46
		sleY1731MepCcmFrameLossNearAvgRatio OBJECT-TYPE
			SYNTAX Integer32
			MAX-ACCESS read-only
			STATUS current
			DESCRIPTION
				"Indicates the average ratio of dual-ended near-end frame loss"
			::= { sleY1731MepEntry 46 }

		
--   1.3.6.1.4.1.6296.101.4.12.3.1.1.47
-- 1.3.6.1.4.1.6296.101.4.12.3.1.1.47
		-- 1.3.6.1.4.1.6296.101.4.12.3.1.1.47
		sleY1731MepCcmFrameLossFarRatio OBJECT-TYPE
			SYNTAX Integer32
			MAX-ACCESS read-only
			STATUS current
			DESCRIPTION
				"Indicates the ratio of dual-ended far-end frame loss"
			::= { sleY1731MepEntry 47 }

		
--   1.3.6.1.4.1.6296.101.4.12.3.1.1.48
-- 1.3.6.1.4.1.6296.101.4.12.3.1.1.48
		-- 1.3.6.1.4.1.6296.101.4.12.3.1.1.48
		sleY1731MepCcmFrameLossFarAvgRatio OBJECT-TYPE
			SYNTAX Integer32
			MAX-ACCESS read-only
			STATUS current
			DESCRIPTION
				"Indicates the average ratio of dual-ended far-end frame loss"
			::= { sleY1731MepEntry 48 }

		
--   1.3.6.1.4.1.6296.101.4.12.3.1.1.49
-- 1.3.6.1.4.1.6296.101.4.12.3.1.1.49
		-- 1.3.6.1.4.1.6296.101.4.12.3.1.1.49
		sleY1731MepRllcf OBJECT-TYPE
			SYNTAX INTEGER
				{
				disable(0),
				enable(1)
				}
			MAX-ACCESS read-only
			STATUS current
			DESCRIPTION
				"If set to true, the MEP is a MEP of client link for remote link loss carry forward."
			::= { sleY1731MepEntry 49 }

		
--   1.3.6.1.4.1.6296.101.4.12.3.1.1.50
-- 1.3.6.1.4.1.6296.101.4.12.3.1.1.50
		-- 1.3.6.1.4.1.6296.101.4.12.3.1.1.50
		sleY1731MepRllcfHoldOff OBJECT-TYPE
			SYNTAX Integer32 (10..3000)
			MAX-ACCESS read-only
			STATUS current
			DESCRIPTION
				"It is a Hold-off time of Remote LLCF and its unit is millisecond, interval is 10ms."
			::= { sleY1731MepEntry 50 }

		
--   1.3.6.1.4.1.6296.101.4.12.3.1.1.51
-- 1.3.6.1.4.1.6296.101.4.12.3.1.1.51
		-- 1.3.6.1.4.1.6296.101.4.12.3.1.1.51
		sleY1731MepRllcfGuardTime OBJECT-TYPE
			SYNTAX Integer32 (100..10000)
			MAX-ACCESS read-only
			STATUS current
			DESCRIPTION
				"It is a Guard time of Remote LLCF and its unit is millisecond, interval is 100ms.(default:500)"
			::= { sleY1731MepEntry 51 }

		
--   1.3.6.1.4.1.6296.101.4.12.3.2
-- 1.3.6.1.4.1.6296.101.4.12.3.2
		-- 1.3.6.1.4.1.6296.101.4.12.3.2
		sleY1731MepControl OBJECT IDENTIFIER ::= { sleY1731Mep 2 }

		
--   1.3.6.1.4.1.6296.101.4.12.3.2.1
-- 1.3.6.1.4.1.6296.101.4.12.3.2.1
		-- 1.3.6.1.4.1.6296.101.4.12.3.2.1
		sleY1731MepControlRequest OBJECT-TYPE
			SYNTAX INTEGER
				{
				createY1731Mep(1),
				deleteY1731Mep(2),
				setY1731MepEnable(3),
				setY1731MepCcEnable(4),
				setY1731MepFaultProfile(5),
				setY1731MepAisEnable(6),
				setY1731MepAisTransmitEnable(7),
				setY1731MepLckEnable(8),
				setY1731MepLckTransmitEnable(9),
				setY1731MepOutOfService(10),
				setY1731MepDlmEnable(11),
				transmitY1731Lbm(12),
				transmitY1731Ltm(13),
				transmitY1731TstLbm(14),
				transmitY1731TmLbm(15),
				transmitY1731Tst(16),
				receiveY1731Tst(17),
				transmitY1731TmTst(18),
				receiveY1731TmTst(19),
				transmitY1731Lmm(20),
				transmitY17311dm(21),
				receiveY17311dm(22),
				transmitY1731dmm(23),
				setY1731MepPmEnable(24),
				setY1731MepRllcf(25)
				}
			MAX-ACCESS read-write
			STATUS current
			DESCRIPTION
				"Description."
			::= { sleY1731MepControl 1 }

		
--   1.3.6.1.4.1.6296.101.4.12.3.2.2
-- 1.3.6.1.4.1.6296.101.4.12.3.2.2
		-- 1.3.6.1.4.1.6296.101.4.12.3.2.2
		sleY1731MepControlStatus OBJECT-TYPE
			SYNTAX SleControlStatusType
			MAX-ACCESS read-only
			STATUS current
			DESCRIPTION
				"Description."
			::= { sleY1731MepControl 2 }

		
--   1.3.6.1.4.1.6296.101.4.12.3.2.3
-- 1.3.6.1.4.1.6296.101.4.12.3.2.3
		-- 1.3.6.1.4.1.6296.101.4.12.3.2.3
		sleY1731MepControlTimer OBJECT-TYPE
			SYNTAX Gauge32
			MAX-ACCESS read-write
			STATUS current
			DESCRIPTION
				"Description."
			::= { sleY1731MepControl 3 }

		
--   1.3.6.1.4.1.6296.101.4.12.3.2.4
-- 1.3.6.1.4.1.6296.101.4.12.3.2.4
		-- 1.3.6.1.4.1.6296.101.4.12.3.2.4
		sleY1731MepControlTimeStamp OBJECT-TYPE
			SYNTAX TimeTicks
			MAX-ACCESS read-only
			STATUS current
			DESCRIPTION
				"Description."
			::= { sleY1731MepControl 4 }

		
--   1.3.6.1.4.1.6296.101.4.12.3.2.5
-- 1.3.6.1.4.1.6296.101.4.12.3.2.5
		-- 1.3.6.1.4.1.6296.101.4.12.3.2.5
		sleY1731MepControlReqResult OBJECT-TYPE
			SYNTAX SleControlRequestResultType
			MAX-ACCESS read-only
			STATUS current
			DESCRIPTION
				"Description."
			::= { sleY1731MepControl 5 }

		
--   1.3.6.1.4.1.6296.101.4.12.3.2.6
-- 1.3.6.1.4.1.6296.101.4.12.3.2.6
		-- 1.3.6.1.4.1.6296.101.4.12.3.2.6
		sleY1731MepControlIdentifier OBJECT-TYPE
			SYNTAX Integer32 (1..8191)
			MAX-ACCESS read-write
			STATUS current
			DESCRIPTION
				"MEP Id"
			::= { sleY1731MepControl 6 }

		
--   1.3.6.1.4.1.6296.101.4.12.3.2.7
-- 1.3.6.1.4.1.6296.101.4.12.3.2.7
		-- 1.3.6.1.4.1.6296.101.4.12.3.2.7
		sleY1731MepControlMegIndex OBJECT-TYPE
			SYNTAX Integer32 (1..65535)
			MAX-ACCESS read-write
			STATUS current
			DESCRIPTION
				"A index of MEG table"
			::= { sleY1731MepControl 7 }

		
--   1.3.6.1.4.1.6296.101.4.12.3.2.8
-- 1.3.6.1.4.1.6296.101.4.12.3.2.8
		-- 1.3.6.1.4.1.6296.101.4.12.3.2.8
		sleY1731MepControlIfIndex OBJECT-TYPE
			SYNTAX Integer32
			MAX-ACCESS read-write
			STATUS current
			DESCRIPTION
				"Bridge Port Index whitch the MEP is attached"
			::= { sleY1731MepControl 8 }

		
--   1.3.6.1.4.1.6296.101.4.12.3.2.9
-- 1.3.6.1.4.1.6296.101.4.12.3.2.9
		-- 1.3.6.1.4.1.6296.101.4.12.3.2.9
		sleY1731MepControlDirection OBJECT-TYPE
			SYNTAX INTEGER
				{
				down(0),
				up(1)
				}
			MAX-ACCESS read-write
			STATUS current
			DESCRIPTION
				"The direction in which the MEP faces on the Bridge port"
			::= { sleY1731MepControl 9 }

		
--   1.3.6.1.4.1.6296.101.4.12.3.2.10
-- 1.3.6.1.4.1.6296.101.4.12.3.2.10
		-- 1.3.6.1.4.1.6296.101.4.12.3.2.10
		sleY1731MepControlEnable OBJECT-TYPE
			SYNTAX INTEGER
				{
				disable(0),
				enable(1)
				}
			MAX-ACCESS read-write
			STATUS current
			DESCRIPTION
				"Administrative state of the MEP"
			::= { sleY1731MepControl 10 }

		
--   1.3.6.1.4.1.6296.101.4.12.3.2.11
-- 1.3.6.1.4.1.6296.101.4.12.3.2.11
		-- 1.3.6.1.4.1.6296.101.4.12.3.2.11
		sleY1731MepControlCcEnable OBJECT-TYPE
			SYNTAX INTEGER
				{
				disable(0),
				enable(1)
				}
			MAX-ACCESS read-write
			STATUS current
			DESCRIPTION
				"If set to true, the MEP will generate CCM messages"
			::= { sleY1731MepControl 11 }

		
--   1.3.6.1.4.1.6296.101.4.12.3.2.12
-- 1.3.6.1.4.1.6296.101.4.12.3.2.12
		-- 1.3.6.1.4.1.6296.101.4.12.3.2.12
		sleY1731MepControlFaultPriority OBJECT-TYPE
			SYNTAX INTEGER
				{
				rdi(1),
				loc(2),
				unp(3),
				unm(4),
				mmg(5),
				unl(6),
				ais(7),
				lck(8)
				}
			MAX-ACCESS read-write
			STATUS current
			DESCRIPTION
				"An integer value specifying the lowest priority defect that is allowed to generate fault alarm"
			::= { sleY1731MepControl 12 }

		
--   1.3.6.1.4.1.6296.101.4.12.3.2.13
-- 1.3.6.1.4.1.6296.101.4.12.3.2.13
		-- 1.3.6.1.4.1.6296.101.4.12.3.2.13
		sleY1731MepControlFaultKeepTime OBJECT-TYPE
			SYNTAX Integer32 (0..1023)
			MAX-ACCESS read-write
			STATUS current
			DESCRIPTION
				"The time that defects must be present before a Fault Alarm is issued"
			::= { sleY1731MepControl 13 }

		
--   1.3.6.1.4.1.6296.101.4.12.3.2.14
-- 1.3.6.1.4.1.6296.101.4.12.3.2.14
		-- 1.3.6.1.4.1.6296.101.4.12.3.2.14
		sleY1731MepControlFaultClearTime OBJECT-TYPE
			SYNTAX Integer32 (0..1023)
			MAX-ACCESS read-write
			STATUS current
			DESCRIPTION
				"The time that defects must be absent before resetting a Fault Alarm"
			::= { sleY1731MepControl 14 }

		
--   1.3.6.1.4.1.6296.101.4.12.3.2.15
-- 1.3.6.1.4.1.6296.101.4.12.3.2.15
		-- 1.3.6.1.4.1.6296.101.4.12.3.2.15
		sleY1731MepControlAisEnable OBJECT-TYPE
			SYNTAX INTEGER
				{
				disable(0),
				enable(1)
				}
			MAX-ACCESS read-write
			STATUS current
			DESCRIPTION
				"If set to true, the AIS function for the MEP is enabled"
			::= { sleY1731MepControl 15 }

		
--   1.3.6.1.4.1.6296.101.4.12.3.2.16
-- 1.3.6.1.4.1.6296.101.4.12.3.2.16
		-- 1.3.6.1.4.1.6296.101.4.12.3.2.16
		sleY1731MepControlAisTransmitEnable OBJECT-TYPE
			SYNTAX INTEGER
				{
				disable(0),
				enable(1)
				}
			MAX-ACCESS read-write
			STATUS current
			DESCRIPTION
				"If set to true, the MEP can generate AIS messages"
			::= { sleY1731MepControl 16 }

		
--   1.3.6.1.4.1.6296.101.4.12.3.2.17
-- 1.3.6.1.4.1.6296.101.4.12.3.2.17
		-- 1.3.6.1.4.1.6296.101.4.12.3.2.17
		sleY1731MepControlLckEnable OBJECT-TYPE
			SYNTAX INTEGER
				{
				disable(0),
				enable(1)
				}
			MAX-ACCESS read-write
			STATUS current
			DESCRIPTION
				"If set to true, the LCK function for the MEP is enabled"
			::= { sleY1731MepControl 17 }

		
--   1.3.6.1.4.1.6296.101.4.12.3.2.18
-- 1.3.6.1.4.1.6296.101.4.12.3.2.18
		-- 1.3.6.1.4.1.6296.101.4.12.3.2.18
		sleY1731MepControlLckTransmitEnable OBJECT-TYPE
			SYNTAX INTEGER
				{
				disable(0),
				enable(1)
				}
			MAX-ACCESS read-write
			STATUS current
			DESCRIPTION
				"If set to true, the MEP can generate LCK messages"
			::= { sleY1731MepControl 18 }

		
--   1.3.6.1.4.1.6296.101.4.12.3.2.19
-- 1.3.6.1.4.1.6296.101.4.12.3.2.19
		-- 1.3.6.1.4.1.6296.101.4.12.3.2.19
		sleY1731MepControlOutOfService OBJECT-TYPE
			SYNTAX INTEGER
				{
				disable(0),
				enable(1)
				}
			MAX-ACCESS read-write
			STATUS current
			DESCRIPTION
				"If set to true, the MEP is in out-of-service."
			::= { sleY1731MepControl 19 }

		
--   
-- 
-- 1.3.6.1.4.1.6296.101.4.12.3.2.20
-- 1.3.6.1.4.1.6296.101.4.12.3.2.20
		-- 1.3.6.1.4.1.6296.101.4.12.3.2.20
		sleY1731MepControlDlmEnabledRmep OBJECT-TYPE
			SYNTAX Integer32 (0..8191)
			MAX-ACCESS read-write
			STATUS current
			DESCRIPTION
				"The RMEP identifier enabled DLM functin
				If set to zero, disabled DLM function.
				"
			::= { sleY1731MepControl 20 }

		
--   1.3.6.1.4.1.6296.101.4.12.3.2.21
-- 1.3.6.1.4.1.6296.101.4.12.3.2.21
		-- 1.3.6.1.4.1.6296.101.4.12.3.2.21
		sleY1731MepControlTransmitLbmIsUnicast OBJECT-TYPE
			SYNTAX INTEGER
				{
				false(0),
				true(1)
				}
			MAX-ACCESS read-write
			STATUS current
			DESCRIPTION
				"Indicates transmitting unicast or multicast frame"
			::= { sleY1731MepControl 21 }

		
--   1.3.6.1.4.1.6296.101.4.12.3.2.22
-- 1.3.6.1.4.1.6296.101.4.12.3.2.22
		-- 1.3.6.1.4.1.6296.101.4.12.3.2.22
		sleY1731MepControlTransmitLbmDestMacAddress OBJECT-TYPE
			SYNTAX OCTET STRING (SIZE (6))
			MAX-ACCESS read-write
			STATUS current
			DESCRIPTION
				"The Target MAC Address Field to be transmitted"
			::= { sleY1731MepControl 22 }

		
--   1.3.6.1.4.1.6296.101.4.12.3.2.23
-- 1.3.6.1.4.1.6296.101.4.12.3.2.23
		-- 1.3.6.1.4.1.6296.101.4.12.3.2.23
		sleY1731MepControlTransmitLbmDestMepId OBJECT-TYPE
			SYNTAX Integer32 (1..8191)
			MAX-ACCESS read-write
			STATUS current
			DESCRIPTION
				"The Maintenance association End Point Identifier of another MEP in the same Maintenance Association to which the LBM is to be sent"
			::= { sleY1731MepControl 23 }

		
--   1.3.6.1.4.1.6296.101.4.12.3.2.24
-- 1.3.6.1.4.1.6296.101.4.12.3.2.24
		-- 1.3.6.1.4.1.6296.101.4.12.3.2.24
		sleY1731MepControlTransmitLbmDestIsMepId OBJECT-TYPE
			SYNTAX INTEGER
				{
				false(0),
				true(1)
				}
			MAX-ACCESS read-write
			STATUS current
			DESCRIPTION
				"True indicates that MEPID of the target MEP is used for  Loopback transmission"
			::= { sleY1731MepControl 24 }

		
--   1.3.6.1.4.1.6296.101.4.12.3.2.25
-- 1.3.6.1.4.1.6296.101.4.12.3.2.25
		-- 1.3.6.1.4.1.6296.101.4.12.3.2.25
		sleY1731MepControlTransmitLbmCount OBJECT-TYPE
			SYNTAX Integer32 (1..6000)
			MAX-ACCESS read-write
			STATUS current
			DESCRIPTION
				"The number of Loopback messages to be transmitted"
			::= { sleY1731MepControl 25 }

		
--   1.3.6.1.4.1.6296.101.4.12.3.2.26
-- 1.3.6.1.4.1.6296.101.4.12.3.2.26
		-- 1.3.6.1.4.1.6296.101.4.12.3.2.26
		sleY1731MepControlTransmitLbmInterval OBJECT-TYPE
			SYNTAX Integer32 (2..4)
			MAX-ACCESS read-write
			STATUS current
			DESCRIPTION
				"Indicates the interval for sending LBM"
			::= { sleY1731MepControl 26 }

		
--   1.3.6.1.4.1.6296.101.4.12.3.2.27
-- 1.3.6.1.4.1.6296.101.4.12.3.2.27
		-- 1.3.6.1.4.1.6296.101.4.12.3.2.27
		sleY1731MepControlTransmitLbmTimeout OBJECT-TYPE
			SYNTAX Integer32 (1..1000)
			MAX-ACCESS read-write
			STATUS current
			DESCRIPTION
				"Indicates the waiting time for receiving the expected LBR"
			::= { sleY1731MepControl 27 }

		
--   1.3.6.1.4.1.6296.101.4.12.3.2.28
-- 1.3.6.1.4.1.6296.101.4.12.3.2.28
		-- 1.3.6.1.4.1.6296.101.4.12.3.2.28
		sleY1731MepControlTransmitLbmPriority OBJECT-TYPE
			SYNTAX Integer32 (0..7)
			MAX-ACCESS read-write
			STATUS current
			DESCRIPTION
				"Priority. 3 bit value to be used in the VLAN tag"
			::= { sleY1731MepControl 28 }

		
--   1.3.6.1.4.1.6296.101.4.12.3.2.29
-- 1.3.6.1.4.1.6296.101.4.12.3.2.29
		-- 1.3.6.1.4.1.6296.101.4.12.3.2.29
		sleY1731MepControlTransmitLbmLength OBJECT-TYPE
			SYNTAX Integer32 (5..1400)
			MAX-ACCESS read-write
			STATUS current
			DESCRIPTION
				"Indicates the length of Data TLV"
			::= { sleY1731MepControl 29 }

		
--   1.3.6.1.4.1.6296.101.4.12.3.2.30
-- 1.3.6.1.4.1.6296.101.4.12.3.2.30
		-- 1.3.6.1.4.1.6296.101.4.12.3.2.30
		sleY1731MepControlTransmitLtmTargetMacAddress OBJECT-TYPE
			SYNTAX OCTET STRING (SIZE (6))
			MAX-ACCESS read-write
			STATUS current
			DESCRIPTION
				"The Target MAC Address Field to be transmitted: A unicast  destination MAC address."
			::= { sleY1731MepControl 30 }

		
--   1.3.6.1.4.1.6296.101.4.12.3.2.31
-- 1.3.6.1.4.1.6296.101.4.12.3.2.31
		-- 1.3.6.1.4.1.6296.101.4.12.3.2.31
		sleY1731MepControlTransmitLtmTargetMepId OBJECT-TYPE
			SYNTAX Integer32 (1..8191)
			MAX-ACCESS read-write
			STATUS current
			DESCRIPTION
				"An indication of the Target MAC Address Field to be  transmitted"
			::= { sleY1731MepControl 31 }

		
--   1.3.6.1.4.1.6296.101.4.12.3.2.32
-- 1.3.6.1.4.1.6296.101.4.12.3.2.32
		-- 1.3.6.1.4.1.6296.101.4.12.3.2.32
		sleY1731MepControlTransmitLtmTargetIsMepId OBJECT-TYPE
			SYNTAX INTEGER
				{
				false(0),
				true(1)
				}
			MAX-ACCESS read-write
			STATUS current
			DESCRIPTION
				"True indicates that MEPID of the target MEP is used for  Linktrace transmission."
			::= { sleY1731MepControl 32 }

		
--   1.3.6.1.4.1.6296.101.4.12.3.2.33
-- 1.3.6.1.4.1.6296.101.4.12.3.2.33
		-- 1.3.6.1.4.1.6296.101.4.12.3.2.33
		sleY1731MepControlTransmitLtmFlags OBJECT-TYPE
			SYNTAX BITS { useFDBonly(0) }
			MAX-ACCESS read-write
			STATUS current
			DESCRIPTION
				"The flags field for LTMs transmitted by the MEP"
			::= { sleY1731MepControl 33 }

		
--   1.3.6.1.4.1.6296.101.4.12.3.2.34
-- 1.3.6.1.4.1.6296.101.4.12.3.2.34
		-- 1.3.6.1.4.1.6296.101.4.12.3.2.34
		sleY1731MepControlTransmitLtmTtl OBJECT-TYPE
			SYNTAX Integer32 (1..64)
			MAX-ACCESS read-write
			STATUS current
			DESCRIPTION
				"The LTM TTL field"
			::= { sleY1731MepControl 34 }

		
--   1.3.6.1.4.1.6296.101.4.12.3.2.35
-- 1.3.6.1.4.1.6296.101.4.12.3.2.35
		-- 1.3.6.1.4.1.6296.101.4.12.3.2.35
		sleY1731MepControlTransmitLtmPriority OBJECT-TYPE
			SYNTAX Integer32 (0..7)
			MAX-ACCESS read-write
			STATUS current
			DESCRIPTION
				"Priority. 3 bit value to be used in the VLAN tag"
			::= { sleY1731MepControl 35 }

		
--   1.3.6.1.4.1.6296.101.4.12.3.2.36
-- 1.3.6.1.4.1.6296.101.4.12.3.2.36
		-- 1.3.6.1.4.1.6296.101.4.12.3.2.36
		sleY1731MepControlTransmitTstLbmDestMepId OBJECT-TYPE
			SYNTAX Integer32 (1..8191)
			MAX-ACCESS read-write
			STATUS current
			DESCRIPTION
				"The Maintenance association End Point Identifier of another MEP in the same Maintenance Association to which the LBM is to be sent"
			::= { sleY1731MepControl 36 }

		
--   1.3.6.1.4.1.6296.101.4.12.3.2.37
-- 1.3.6.1.4.1.6296.101.4.12.3.2.37
		-- 1.3.6.1.4.1.6296.101.4.12.3.2.37
		sleY1731MepControlTransmitTstLbmDuration OBJECT-TYPE
			SYNTAX Integer32 (5..6000)
			MAX-ACCESS read-write
			STATUS current
			DESCRIPTION
				"Indicates the duration to send LBM"
			::= { sleY1731MepControl 37 }

		
--   1.3.6.1.4.1.6296.101.4.12.3.2.38
-- 1.3.6.1.4.1.6296.101.4.12.3.2.38
		-- 1.3.6.1.4.1.6296.101.4.12.3.2.38
		sleY1731MepControlTransmitTstLbmInterval OBJECT-TYPE
			SYNTAX Integer32 (2..4)
			MAX-ACCESS read-write
			STATUS current
			DESCRIPTION
				"Indicates the interval for sending LBM"
			::= { sleY1731MepControl 38 }

		
--   1.3.6.1.4.1.6296.101.4.12.3.2.39
-- 1.3.6.1.4.1.6296.101.4.12.3.2.39
		-- 1.3.6.1.4.1.6296.101.4.12.3.2.39
		sleY1731MepControlTransmitTstLbmTimeout OBJECT-TYPE
			SYNTAX Integer32 (1..1000)
			MAX-ACCESS read-write
			STATUS current
			DESCRIPTION
				"Indicates the waiting time for receiving the expected LBR"
			::= { sleY1731MepControl 39 }

		
--   1.3.6.1.4.1.6296.101.4.12.3.2.40
-- 1.3.6.1.4.1.6296.101.4.12.3.2.40
		-- 1.3.6.1.4.1.6296.101.4.12.3.2.40
		sleY1731MepControlTransmitTstLbmPriority OBJECT-TYPE
			SYNTAX Integer32 (0..7)
			MAX-ACCESS read-write
			STATUS current
			DESCRIPTION
				"Priority. 3 bit value to be used in the VLAN tag"
			::= { sleY1731MepControl 40 }

		
--   1.3.6.1.4.1.6296.101.4.12.3.2.41
-- 1.3.6.1.4.1.6296.101.4.12.3.2.41
		-- 1.3.6.1.4.1.6296.101.4.12.3.2.41
		sleY1731MepControlTransmitTstLbmLength OBJECT-TYPE
			SYNTAX Integer32 (5..1400)
			MAX-ACCESS read-write
			STATUS current
			DESCRIPTION
				"Indicates the length of Test TLV"
			::= { sleY1731MepControl 41 }

		
--   1.3.6.1.4.1.6296.101.4.12.3.2.42
-- 1.3.6.1.4.1.6296.101.4.12.3.2.42
		-- 1.3.6.1.4.1.6296.101.4.12.3.2.42
		sleY1731MepControlTransmitTstLbmPattern OBJECT-TYPE
			SYNTAX Integer32 (0..3)
			MAX-ACCESS read-write
			STATUS current
			DESCRIPTION
				"Indicates the pattern of Test TLV used for diagnostic test"
			::= { sleY1731MepControl 42 }

		
--   1.3.6.1.4.1.6296.101.4.12.3.2.43
-- 1.3.6.1.4.1.6296.101.4.12.3.2.43
		-- 1.3.6.1.4.1.6296.101.4.12.3.2.43
		sleY1731MepControlTransmitTmLbmDestMepId OBJECT-TYPE
			SYNTAX Integer32 (1..8191)
			MAX-ACCESS read-write
			STATUS current
			DESCRIPTION
				"The Maintenance association End Point Identifier of another MEP in the same Maintenance Association to which the LBM is to be sent"
			::= { sleY1731MepControl 43 }

		
--   1.3.6.1.4.1.6296.101.4.12.3.2.44
-- 1.3.6.1.4.1.6296.101.4.12.3.2.44
		-- 1.3.6.1.4.1.6296.101.4.12.3.2.44
		sleY1731MepControlTransmitTmLbmDuration OBJECT-TYPE
			SYNTAX Integer32 (5..6000)
			MAX-ACCESS read-write
			STATUS current
			DESCRIPTION
				"Indicates the duration to send LBM"
			::= { sleY1731MepControl 44 }

		
--   1.3.6.1.4.1.6296.101.4.12.3.2.45
-- 1.3.6.1.4.1.6296.101.4.12.3.2.45
		-- 1.3.6.1.4.1.6296.101.4.12.3.2.45
		sleY1731MepControlTransmitTmLbmPartDuration OBJECT-TYPE
			SYNTAX Integer32 (1..5)
			MAX-ACCESS read-write
			STATUS current
			DESCRIPTION
				"Indicates the part duration of LBM to be transmitted at the same transmission rate"
			::= { sleY1731MepControl 45 }

		
--   1.3.6.1.4.1.6296.101.4.12.3.2.46
-- 1.3.6.1.4.1.6296.101.4.12.3.2.46
		-- 1.3.6.1.4.1.6296.101.4.12.3.2.46
		sleY1731MepControlTransmitTmLbmStartRate OBJECT-TYPE
			SYNTAX Integer32 (100..1000)
			MAX-ACCESS read-write
			STATUS current
			DESCRIPTION
				"Indicates the the number of LBMs to be transmitted per second at first time"
			::= { sleY1731MepControl 46 }

		
--   1.3.6.1.4.1.6296.101.4.12.3.2.47
-- 1.3.6.1.4.1.6296.101.4.12.3.2.47
		-- 1.3.6.1.4.1.6296.101.4.12.3.2.47
		sleY1731MepControlTransmitTmLbmIncRate OBJECT-TYPE
			SYNTAX Integer32 (100..1000)
			MAX-ACCESS read-write
			STATUS current
			DESCRIPTION
				"Indicates the increment of number of LBMs to be transmitted"
			::= { sleY1731MepControl 47 }

		
--   1.3.6.1.4.1.6296.101.4.12.3.2.48
-- 1.3.6.1.4.1.6296.101.4.12.3.2.48
		-- 1.3.6.1.4.1.6296.101.4.12.3.2.48
		sleY1731MepControlTransmitTmLbmTimeout OBJECT-TYPE
			SYNTAX Integer32 (1..1000)
			MAX-ACCESS read-write
			STATUS current
			DESCRIPTION
				"Indicates the waiting time for receiving the expected LBR"
			::= { sleY1731MepControl 48 }

		
--   1.3.6.1.4.1.6296.101.4.12.3.2.49
-- 1.3.6.1.4.1.6296.101.4.12.3.2.49
		-- 1.3.6.1.4.1.6296.101.4.12.3.2.49
		sleY1731MepControlTransmitTmLbmPriority OBJECT-TYPE
			SYNTAX Integer32 (0..7)
			MAX-ACCESS read-write
			STATUS current
			DESCRIPTION
				"Priority. 3 bit value to be used in the VLAN tag"
			::= { sleY1731MepControl 49 }

		
--   1.3.6.1.4.1.6296.101.4.12.3.2.50
-- 1.3.6.1.4.1.6296.101.4.12.3.2.50
		-- 1.3.6.1.4.1.6296.101.4.12.3.2.50
		sleY1731MepControlTransmitTmLbmLength OBJECT-TYPE
			SYNTAX Integer32 (5..1400)
			MAX-ACCESS read-write
			STATUS current
			DESCRIPTION
				"Indicates the length of Test TLV"
			::= { sleY1731MepControl 50 }

		
--   1.3.6.1.4.1.6296.101.4.12.3.2.51
-- 1.3.6.1.4.1.6296.101.4.12.3.2.51
		-- 1.3.6.1.4.1.6296.101.4.12.3.2.51
		sleY1731MepControlTransmitTmLbmPattern OBJECT-TYPE
			SYNTAX Integer32 (0..3)
			MAX-ACCESS read-write
			STATUS current
			DESCRIPTION
				"Indicates the pattern of Test TLV used for diagnostic test"
			::= { sleY1731MepControl 51 }

		
--   1.3.6.1.4.1.6296.101.4.12.3.2.52
-- 1.3.6.1.4.1.6296.101.4.12.3.2.52
		-- 1.3.6.1.4.1.6296.101.4.12.3.2.52
		sleY1731MepControlTransmitTstIsUnicast OBJECT-TYPE
			SYNTAX INTEGER
				{
				false(0),
				true(1)
				}
			MAX-ACCESS read-write
			STATUS current
			DESCRIPTION
				"Indicates transmitting unicast or multicast frame"
			::= { sleY1731MepControl 52 }

		
--   1.3.6.1.4.1.6296.101.4.12.3.2.53
-- 1.3.6.1.4.1.6296.101.4.12.3.2.53
		-- 1.3.6.1.4.1.6296.101.4.12.3.2.53
		sleY1731MepControlTransmitTstDestMepId OBJECT-TYPE
			SYNTAX Integer32 (1..8191)
			MAX-ACCESS read-write
			STATUS current
			DESCRIPTION
				"The Maintenance association End Point Identifier of another MEP in the same Maintenance Association to which the TST is to be sent"
			::= { sleY1731MepControl 53 }

		
--   1.3.6.1.4.1.6296.101.4.12.3.2.54
-- 1.3.6.1.4.1.6296.101.4.12.3.2.54
		-- 1.3.6.1.4.1.6296.101.4.12.3.2.54
		sleY1731MepControlTransmitTstDuration OBJECT-TYPE
			SYNTAX Integer32 (5..6000)
			MAX-ACCESS read-write
			STATUS current
			DESCRIPTION
				"Indicates the duration to send TST"
			::= { sleY1731MepControl 54 }

		
--   1.3.6.1.4.1.6296.101.4.12.3.2.55
-- 1.3.6.1.4.1.6296.101.4.12.3.2.55
		-- 1.3.6.1.4.1.6296.101.4.12.3.2.55
		sleY1731MepControlTransmitTstInterval OBJECT-TYPE
			SYNTAX Integer32 (2..4)
			MAX-ACCESS read-write
			STATUS current
			DESCRIPTION
				"Indicates the interval for sending TST"
			::= { sleY1731MepControl 55 }

		
--   1.3.6.1.4.1.6296.101.4.12.3.2.56
-- 1.3.6.1.4.1.6296.101.4.12.3.2.56
		-- 1.3.6.1.4.1.6296.101.4.12.3.2.56
		sleY1731MepControlTransmitTstPriority OBJECT-TYPE
			SYNTAX Integer32 (0..7)
			MAX-ACCESS read-write
			STATUS current
			DESCRIPTION
				"Priority. 3 bit value to be used in the VLAN tag"
			::= { sleY1731MepControl 56 }

		
--   1.3.6.1.4.1.6296.101.4.12.3.2.57
-- 1.3.6.1.4.1.6296.101.4.12.3.2.57
		-- 1.3.6.1.4.1.6296.101.4.12.3.2.57
		sleY1731MepControlTransmitTstLength OBJECT-TYPE
			SYNTAX Integer32 (5..1400)
			MAX-ACCESS read-write
			STATUS current
			DESCRIPTION
				"Indicates the length of Test TLV"
			::= { sleY1731MepControl 57 }

		
--   1.3.6.1.4.1.6296.101.4.12.3.2.58
-- 1.3.6.1.4.1.6296.101.4.12.3.2.58
		-- 1.3.6.1.4.1.6296.101.4.12.3.2.58
		sleY1731MepControlTransmitTstPattern OBJECT-TYPE
			SYNTAX Integer32 (0..3)
			MAX-ACCESS read-write
			STATUS current
			DESCRIPTION
				"Indicates the pattern of Test TLV used for diagnostic test"
			::= { sleY1731MepControl 58 }

		
--   1.3.6.1.4.1.6296.101.4.12.3.2.59
-- 1.3.6.1.4.1.6296.101.4.12.3.2.59
		-- 1.3.6.1.4.1.6296.101.4.12.3.2.59
		sleY1731MepControlReceiveTstDuration OBJECT-TYPE
			SYNTAX Integer32 (5..6000)
			MAX-ACCESS read-write
			STATUS current
			DESCRIPTION
				"Indicates the duration to receive TST"
			::= { sleY1731MepControl 59 }

		
--   1.3.6.1.4.1.6296.101.4.12.3.2.60
-- 1.3.6.1.4.1.6296.101.4.12.3.2.60
		-- 1.3.6.1.4.1.6296.101.4.12.3.2.60
		sleY1731MepControlTransmitTmTstIsUnicast OBJECT-TYPE
			SYNTAX INTEGER
				{
				false(0),
				true(1)
				}
			MAX-ACCESS read-write
			STATUS current
			DESCRIPTION
				"Indicates transmitting unicast or multicast frame"
			::= { sleY1731MepControl 60 }

		
--   1.3.6.1.4.1.6296.101.4.12.3.2.61
-- 1.3.6.1.4.1.6296.101.4.12.3.2.61
		-- 1.3.6.1.4.1.6296.101.4.12.3.2.61
		sleY1731MepControlTransmitTmTstDestMepId OBJECT-TYPE
			SYNTAX Integer32 (1..8191)
			MAX-ACCESS read-write
			STATUS current
			DESCRIPTION
				"The Maintenance association End Point Identifier of another MEP in the same Maintenance Association to which the TST is to be sent"
			::= { sleY1731MepControl 61 }

		
--   1.3.6.1.4.1.6296.101.4.12.3.2.62
-- 1.3.6.1.4.1.6296.101.4.12.3.2.62
		-- 1.3.6.1.4.1.6296.101.4.12.3.2.62
		sleY1731MepControlTransmitTmTstDuration OBJECT-TYPE
			SYNTAX Integer32 (5..6000)
			MAX-ACCESS read-write
			STATUS current
			DESCRIPTION
				"Indicates the duration to send TST"
			::= { sleY1731MepControl 62 }

		
--   1.3.6.1.4.1.6296.101.4.12.3.2.63
-- 1.3.6.1.4.1.6296.101.4.12.3.2.63
		-- 1.3.6.1.4.1.6296.101.4.12.3.2.63
		sleY1731MepControlTransmitTmTstPartDuration OBJECT-TYPE
			SYNTAX Integer32 (1..5)
			MAX-ACCESS read-write
			STATUS current
			DESCRIPTION
				"Indicates the part duration of TST to be transmitted at the same transmission rate"
			::= { sleY1731MepControl 63 }

		
--   1.3.6.1.4.1.6296.101.4.12.3.2.64
-- 1.3.6.1.4.1.6296.101.4.12.3.2.64
		-- 1.3.6.1.4.1.6296.101.4.12.3.2.64
		sleY1731MepControlTransmitTmTstStartRate OBJECT-TYPE
			SYNTAX Integer32 (100..1000)
			MAX-ACCESS read-write
			STATUS current
			DESCRIPTION
				"Indicates the the number of TSTs to be transmitted per second at first time"
			::= { sleY1731MepControl 64 }

		
--   1.3.6.1.4.1.6296.101.4.12.3.2.65
-- 1.3.6.1.4.1.6296.101.4.12.3.2.65
		-- 1.3.6.1.4.1.6296.101.4.12.3.2.65
		sleY1731MepControlTransmitTmTstIncRate OBJECT-TYPE
			SYNTAX Integer32 (100..1000)
			MAX-ACCESS read-write
			STATUS current
			DESCRIPTION
				"Indicates the increment of number of TSTs to be transmitted"
			::= { sleY1731MepControl 65 }

		
--   1.3.6.1.4.1.6296.101.4.12.3.2.66
-- 1.3.6.1.4.1.6296.101.4.12.3.2.66
		-- 1.3.6.1.4.1.6296.101.4.12.3.2.66
		sleY1731MepControlTransmitTmTstTimeout OBJECT-TYPE
			SYNTAX Integer32 (1..1000)
			MAX-ACCESS read-write
			STATUS current
			DESCRIPTION
				"Indicates the waiting time for receiving the expected LBR"
			::= { sleY1731MepControl 66 }

		
--   1.3.6.1.4.1.6296.101.4.12.3.2.67
-- 1.3.6.1.4.1.6296.101.4.12.3.2.67
		-- 1.3.6.1.4.1.6296.101.4.12.3.2.67
		sleY1731MepControlTransmitTmTstPriority OBJECT-TYPE
			SYNTAX Integer32 (0..7)
			MAX-ACCESS read-write
			STATUS current
			DESCRIPTION
				"Priority. 3 bit value to be used in the VLAN tag"
			::= { sleY1731MepControl 67 }

		
--   1.3.6.1.4.1.6296.101.4.12.3.2.68
-- 1.3.6.1.4.1.6296.101.4.12.3.2.68
		-- 1.3.6.1.4.1.6296.101.4.12.3.2.68
		sleY1731MepControlTransmitTmTstLength OBJECT-TYPE
			SYNTAX Integer32 (5..1400)
			MAX-ACCESS read-write
			STATUS current
			DESCRIPTION
				"Indicates the length of Test TLV"
			::= { sleY1731MepControl 68 }

		
--   1.3.6.1.4.1.6296.101.4.12.3.2.69
-- 1.3.6.1.4.1.6296.101.4.12.3.2.69
		-- 1.3.6.1.4.1.6296.101.4.12.3.2.69
		sleY1731MepControlTransmitTmTstPattern OBJECT-TYPE
			SYNTAX Integer32 (0..3)
			MAX-ACCESS read-write
			STATUS current
			DESCRIPTION
				"Indicates the pattern of Test TLV used for diagnostic test"
			::= { sleY1731MepControl 69 }

		
--   1.3.6.1.4.1.6296.101.4.12.3.2.70
-- 1.3.6.1.4.1.6296.101.4.12.3.2.70
		-- 1.3.6.1.4.1.6296.101.4.12.3.2.70
		sleY1731MepControlReceiveTmTstDuration OBJECT-TYPE
			SYNTAX Integer32 (5..6000)
			MAX-ACCESS read-write
			STATUS current
			DESCRIPTION
				"Indicates the duration to receive TST"
			::= { sleY1731MepControl 70 }

		
--   1.3.6.1.4.1.6296.101.4.12.3.2.71
-- 1.3.6.1.4.1.6296.101.4.12.3.2.71
		-- 1.3.6.1.4.1.6296.101.4.12.3.2.71
		sleY1731MepControlTransmitLmmIsUnicast OBJECT-TYPE
			SYNTAX INTEGER
				{
				false(0),
				true(1)
				}
			MAX-ACCESS read-write
			STATUS current
			DESCRIPTION
				"A flag to indicates transmitting unicast or multicast frame"
			::= { sleY1731MepControl 71 }

		
--   1.3.6.1.4.1.6296.101.4.12.3.2.72
-- 1.3.6.1.4.1.6296.101.4.12.3.2.72
		-- 1.3.6.1.4.1.6296.101.4.12.3.2.72
		sleY1731MepControlTransmitLmmDestMepId OBJECT-TYPE
			SYNTAX Integer32 (1..8191)
			MAX-ACCESS read-write
			STATUS current
			DESCRIPTION
				"The Maintenance association End Point Identifier of another MEP in the same Maintenance Association to which the LMM is to be sent"
			::= { sleY1731MepControl 72 }

		
--   1.3.6.1.4.1.6296.101.4.12.3.2.73
-- 1.3.6.1.4.1.6296.101.4.12.3.2.73
		-- 1.3.6.1.4.1.6296.101.4.12.3.2.73
		sleY1731MepControlTransmitLmmDuration OBJECT-TYPE
			SYNTAX Integer32 (5..6000)
			MAX-ACCESS read-write
			STATUS current
			DESCRIPTION
				"Indicates the duration to send LMM"
			::= { sleY1731MepControl 73 }

		
--   1.3.6.1.4.1.6296.101.4.12.3.2.74
-- 1.3.6.1.4.1.6296.101.4.12.3.2.74
		-- 1.3.6.1.4.1.6296.101.4.12.3.2.74
		sleY1731MepControlTransmitLmmInterval OBJECT-TYPE
			SYNTAX Integer32 (2..4)
			MAX-ACCESS read-write
			STATUS current
			DESCRIPTION
				"Indicates the interval for sending LMM"
			::= { sleY1731MepControl 74 }

		
--   1.3.6.1.4.1.6296.101.4.12.3.2.75
-- 1.3.6.1.4.1.6296.101.4.12.3.2.75
		-- 1.3.6.1.4.1.6296.101.4.12.3.2.75
		sleY1731MepControlTransmitLmmTimeout OBJECT-TYPE
			SYNTAX Integer32 (1..1000)
			MAX-ACCESS read-write
			STATUS current
			DESCRIPTION
				"Indicates the waiting time for receiving the expected LMM"
			::= { sleY1731MepControl 75 }

		
--   1.3.6.1.4.1.6296.101.4.12.3.2.76
-- 1.3.6.1.4.1.6296.101.4.12.3.2.76
		-- 1.3.6.1.4.1.6296.101.4.12.3.2.76
		sleY1731MepControlTransmitLmmPriority OBJECT-TYPE
			SYNTAX Integer32 (0..7)
			MAX-ACCESS read-write
			STATUS current
			DESCRIPTION
				"Priority. 3 bit value to be used in the VLAN tag"
			::= { sleY1731MepControl 76 }

		
--   1.3.6.1.4.1.6296.101.4.12.3.2.77
-- 1.3.6.1.4.1.6296.101.4.12.3.2.77
		-- 1.3.6.1.4.1.6296.101.4.12.3.2.77
		sleY1731MepControlTransmit1dmIsUnicast OBJECT-TYPE
			SYNTAX INTEGER
				{
				false(0),
				true(1)
				}
			MAX-ACCESS read-write
			STATUS current
			DESCRIPTION
				"A flag to indicates transmitting unicast or multicast frame"
			::= { sleY1731MepControl 77 }

		
--   1.3.6.1.4.1.6296.101.4.12.3.2.78
-- 1.3.6.1.4.1.6296.101.4.12.3.2.78
		-- 1.3.6.1.4.1.6296.101.4.12.3.2.78
		sleY1731MepControlTransmit1dmDestMepId OBJECT-TYPE
			SYNTAX Integer32 (1..8191)
			MAX-ACCESS read-write
			STATUS current
			DESCRIPTION
				"The Maintenance association End Point Identifier of another MEP in the same Maintenance Association to which the 1DM is to be sent"
			::= { sleY1731MepControl 78 }

		
--   1.3.6.1.4.1.6296.101.4.12.3.2.79
-- 1.3.6.1.4.1.6296.101.4.12.3.2.79
		-- 1.3.6.1.4.1.6296.101.4.12.3.2.79
		sleY1731MepControlTransmit1dmDuration OBJECT-TYPE
			SYNTAX Integer32 (5..6000)
			MAX-ACCESS read-write
			STATUS current
			DESCRIPTION
				"Indicates the duration to send 1DM"
			::= { sleY1731MepControl 79 }

		
--   1.3.6.1.4.1.6296.101.4.12.3.2.80
-- 1.3.6.1.4.1.6296.101.4.12.3.2.80
		-- 1.3.6.1.4.1.6296.101.4.12.3.2.80
		sleY1731MepControlTransmit1dmInterval OBJECT-TYPE
			SYNTAX Integer32 (2..4)
			MAX-ACCESS read-write
			STATUS current
			DESCRIPTION
				"Indicates the interval for sending 1DM"
			::= { sleY1731MepControl 80 }

		
--   1.3.6.1.4.1.6296.101.4.12.3.2.81
-- 1.3.6.1.4.1.6296.101.4.12.3.2.81
		-- 1.3.6.1.4.1.6296.101.4.12.3.2.81
		sleY1731MepControlTransmit1dmPriority OBJECT-TYPE
			SYNTAX Integer32 (0..7)
			MAX-ACCESS read-write
			STATUS current
			DESCRIPTION
				"Priority. 3 bit value to be used in the VLAN tag"
			::= { sleY1731MepControl 81 }

		
--   1.3.6.1.4.1.6296.101.4.12.3.2.82
-- 1.3.6.1.4.1.6296.101.4.12.3.2.82
		-- 1.3.6.1.4.1.6296.101.4.12.3.2.82
		sleY1731MepControlReceive1dmDuration OBJECT-TYPE
			SYNTAX Integer32 (5..6000)
			MAX-ACCESS read-write
			STATUS current
			DESCRIPTION
				"Indicates the duration to receive 1DM"
			::= { sleY1731MepControl 82 }

		
--   1.3.6.1.4.1.6296.101.4.12.3.2.83
-- 1.3.6.1.4.1.6296.101.4.12.3.2.83
		-- 1.3.6.1.4.1.6296.101.4.12.3.2.83
		sleY1731MepControlTransmitDmmIsUnicast OBJECT-TYPE
			SYNTAX INTEGER
				{
				false(0),
				true(1)
				}
			MAX-ACCESS read-write
			STATUS current
			DESCRIPTION
				"A flag to indicates transmitting unicast or multicast frame"
			::= { sleY1731MepControl 83 }

		
--   1.3.6.1.4.1.6296.101.4.12.3.2.84
-- 1.3.6.1.4.1.6296.101.4.12.3.2.84
		-- 1.3.6.1.4.1.6296.101.4.12.3.2.84
		sleY1731MepControlTransmitDmmDestMepId OBJECT-TYPE
			SYNTAX Integer32 (1..8191)
			MAX-ACCESS read-write
			STATUS current
			DESCRIPTION
				"The Maintenance association End Point Identifier of another MEP in the same Maintenance Association to which the DMM is to be sent"
			::= { sleY1731MepControl 84 }

		
--   1.3.6.1.4.1.6296.101.4.12.3.2.85
-- 1.3.6.1.4.1.6296.101.4.12.3.2.85
		-- 1.3.6.1.4.1.6296.101.4.12.3.2.85
		sleY1731MepControlTransmitDmmDuration OBJECT-TYPE
			SYNTAX Integer32 (5..6000)
			MAX-ACCESS read-write
			STATUS current
			DESCRIPTION
				"Indicates the duration to send DMM"
			::= { sleY1731MepControl 85 }

		
--   1.3.6.1.4.1.6296.101.4.12.3.2.86
-- 1.3.6.1.4.1.6296.101.4.12.3.2.86
		-- 1.3.6.1.4.1.6296.101.4.12.3.2.86
		sleY1731MepControlTransmitDmmInterval OBJECT-TYPE
			SYNTAX Integer32 (2..4)
			MAX-ACCESS read-write
			STATUS current
			DESCRIPTION
				"Indicates the interval for sending DMM"
			::= { sleY1731MepControl 86 }

		
--   1.3.6.1.4.1.6296.101.4.12.3.2.87
-- 1.3.6.1.4.1.6296.101.4.12.3.2.87
		-- 1.3.6.1.4.1.6296.101.4.12.3.2.87
		sleY1731MepControlTransmitDmmTimeout OBJECT-TYPE
			SYNTAX Integer32 (1..1000)
			MAX-ACCESS read-write
			STATUS current
			DESCRIPTION
				"Indicates the waiting time for receiving the expected DMM"
			::= { sleY1731MepControl 87 }

		
--   1.3.6.1.4.1.6296.101.4.12.3.2.88
-- 1.3.6.1.4.1.6296.101.4.12.3.2.88
		-- 1.3.6.1.4.1.6296.101.4.12.3.2.88
		sleY1731MepControlTransmitDmmPriority OBJECT-TYPE
			SYNTAX Integer32 (0..7)
			MAX-ACCESS read-write
			STATUS current
			DESCRIPTION
				"Priority. 3 bit value to be used in the VLAN tag"
			::= { sleY1731MepControl 88 }

		
--   1.3.6.1.4.1.6296.101.4.12.3.2.89
-- 1.3.6.1.4.1.6296.101.4.12.3.2.89
		-- 1.3.6.1.4.1.6296.101.4.12.3.2.89
		sleY1731MepControlPmEnable OBJECT-TYPE
			SYNTAX INTEGER
				{
				disable(0),
				enable(1)
				}
			MAX-ACCESS read-write
			STATUS current
			DESCRIPTION
				"If set to true, the PM(performance monitoring) of the MEP is enabled"
			::= { sleY1731MepControl 89 }

		
--   1.3.6.1.4.1.6296.101.4.12.3.2.90
-- 1.3.6.1.4.1.6296.101.4.12.3.2.90
		-- 1.3.6.1.4.1.6296.101.4.12.3.2.90
		sleY1731MepControlRllcf OBJECT-TYPE
			SYNTAX INTEGER
				{
				disable(0),
				enable(1)
				}
			MAX-ACCESS read-write
			STATUS current
			DESCRIPTION
				"If set to true, the MEP is a MEP of client link for remote link loss carry forward."
			::= { sleY1731MepControl 90 }

		
--   1.3.6.1.4.1.6296.101.4.12.3.2.91
-- 1.3.6.1.4.1.6296.101.4.12.3.2.91
		-- 1.3.6.1.4.1.6296.101.4.12.3.2.91
		sleY1731MepControlRllcfHoldOff OBJECT-TYPE
			SYNTAX Integer32 (10..3000)
			MAX-ACCESS read-write
			STATUS current
			DESCRIPTION
				"It is a Hold-off time of Remote LLCF and its unit is millisecond, interval is 10ms."
			::= { sleY1731MepControl 91 }

		
--   1.3.6.1.4.1.6296.101.4.12.3.2.92
-- 1.3.6.1.4.1.6296.101.4.12.3.2.92
		-- 1.3.6.1.4.1.6296.101.4.12.3.2.92
		sleY1731MepControlRllcfGuardTime OBJECT-TYPE
			SYNTAX Integer32 (100..10000)
			MAX-ACCESS read-write
			STATUS current
			DESCRIPTION
				"It is a Guard time of Remote LLCF and its unit is millisecond, interval is 100ms.(default:500)"
			::= { sleY1731MepControl 92 }

		
--   1.3.6.1.4.1.6296.101.4.12.3.3
-- 1.3.6.1.4.1.6296.101.4.12.3.3
		-- 1.3.6.1.4.1.6296.101.4.12.3.3
		sleY1731MepNotification OBJECT IDENTIFIER ::= { sleY1731Mep 3 }

		
--   1.3.6.1.4.1.6296.101.4.12.3.3.1
-- 1.3.6.1.4.1.6296.101.4.12.3.3.1
		-- 1.3.6.1.4.1.6296.101.4.12.3.3.1
		sleY1731MepCreated NOTIFICATION-TYPE
			OBJECTS { sleY1731MepControlRequest, sleY1731MepControlTimeStamp, sleY1731MepControlReqResult, sleY1731MepControlIdentifier, sleY1731MepControlMegIndex, 
				sleY1731MepControlIfIndex, sleY1731MepControlDirection }
			STATUS current
			DESCRIPTION 
				"createY1731Mep"
			::= { sleY1731MepNotification 1 }

		
--   1.3.6.1.4.1.6296.101.4.12.3.3.2
-- 1.3.6.1.4.1.6296.101.4.12.3.3.2
		-- 1.3.6.1.4.1.6296.101.4.12.3.3.2
		sleY1731MepDeleted NOTIFICATION-TYPE
			OBJECTS { sleY1731MepControlRequest, sleY1731MepControlTimeStamp, sleY1731MepControlReqResult, sleY1731MepControlIdentifier, sleY1731MepControlMegIndex
				 }
			STATUS current
			DESCRIPTION 
				"deleteY1731Mep"
			::= { sleY1731MepNotification 2 }

		
--   1.3.6.1.4.1.6296.101.4.12.3.3.3
-- 1.3.6.1.4.1.6296.101.4.12.3.3.3
		-- 1.3.6.1.4.1.6296.101.4.12.3.3.3
		sleY1731MepEnableChanged NOTIFICATION-TYPE
			OBJECTS { sleY1731MepControlRequest, sleY1731MepControlTimeStamp, sleY1731MepControlReqResult, sleY1731MepControlIdentifier, sleY1731MepControlMegIndex, 
				sleY1731MepControlEnable }
			STATUS current
			DESCRIPTION 
				"setY1731MepEnable"
			::= { sleY1731MepNotification 3 }

		
--   1.3.6.1.4.1.6296.101.4.12.3.3.4
-- 1.3.6.1.4.1.6296.101.4.12.3.3.4
		-- 1.3.6.1.4.1.6296.101.4.12.3.3.4
		sleY1731MepCcEnableChanged NOTIFICATION-TYPE
			OBJECTS { sleY1731MepControlRequest, sleY1731MepControlTimeStamp, sleY1731MepControlReqResult, sleY1731MepControlIdentifier, sleY1731MepControlMegIndex, 
				sleY1731MepControlCcEnable }
			STATUS current
			DESCRIPTION 
				"setY1731CcEnable"
			::= { sleY1731MepNotification 4 }

		
--   1.3.6.1.4.1.6296.101.4.12.3.3.5
-- 1.3.6.1.4.1.6296.101.4.12.3.3.5
		-- 1.3.6.1.4.1.6296.101.4.12.3.3.5
		sleY1731MepFaultProfileChanged NOTIFICATION-TYPE
			OBJECTS { sleY1731MepControlRequest, sleY1731MepControlTimeStamp, sleY1731MepControlReqResult, sleY1731MepControlIdentifier, sleY1731MepControlMegIndex, 
				sleY1731MepControlFaultPriority, sleY1731MepControlFaultKeepTime, sleY1731MepControlFaultClearTime }
			STATUS current
			DESCRIPTION 
				"setY1731FaultProfile"
			::= { sleY1731MepNotification 5 }

		
--   1.3.6.1.4.1.6296.101.4.12.3.3.6
-- 1.3.6.1.4.1.6296.101.4.12.3.3.6
		-- 1.3.6.1.4.1.6296.101.4.12.3.3.6
		sleY1731MepAisEnableChanged NOTIFICATION-TYPE
			OBJECTS { sleY1731MepControlRequest, sleY1731MepControlTimeStamp, sleY1731MepControlReqResult, sleY1731MepControlIdentifier, sleY1731MepControlMegIndex, 
				sleY1731MepControlAisEnable }
			STATUS current
			DESCRIPTION 
				"setY1731AisEnable"
			::= { sleY1731MepNotification 6 }

		
--   1.3.6.1.4.1.6296.101.4.12.3.3.7
-- 1.3.6.1.4.1.6296.101.4.12.3.3.7
		-- 1.3.6.1.4.1.6296.101.4.12.3.3.7
		sleY1731MepAisTransmitEnableChanged NOTIFICATION-TYPE
			OBJECTS { sleY1731MepControlRequest, sleY1731MepControlTimeStamp, sleY1731MepControlReqResult, sleY1731MepControlIdentifier, sleY1731MepControlMegIndex, 
				sleY1731MepControlAisTransmitEnable }
			STATUS current
			DESCRIPTION 
				"setY1731AisTransmitEnable"
			::= { sleY1731MepNotification 7 }

		
--   1.3.6.1.4.1.6296.101.4.12.3.3.8
-- 1.3.6.1.4.1.6296.101.4.12.3.3.8
		-- 1.3.6.1.4.1.6296.101.4.12.3.3.8
		sleY1731MepLckEnableChanged NOTIFICATION-TYPE
			OBJECTS { sleY1731MepControlRequest, sleY1731MepControlTimeStamp, sleY1731MepControlReqResult, sleY1731MepControlIdentifier, sleY1731MepControlMegIndex, 
				sleY1731MepControlLckEnable }
			STATUS current
			DESCRIPTION 
				"setY1731LckEnable"
			::= { sleY1731MepNotification 8 }

		
--   1.3.6.1.4.1.6296.101.4.12.3.3.9
-- 1.3.6.1.4.1.6296.101.4.12.3.3.9
		-- 1.3.6.1.4.1.6296.101.4.12.3.3.9
		sleY1731MepLckTransmitEnableChanged NOTIFICATION-TYPE
			OBJECTS { sleY1731MepControlRequest, sleY1731MepControlTimeStamp, sleY1731MepControlReqResult, sleY1731MepControlIdentifier, sleY1731MepControlMegIndex, 
				sleY1731MepControlLckTransmitEnable }
			STATUS current
			DESCRIPTION 
				"setY1731LckTransmitEnable"
			::= { sleY1731MepNotification 9 }

		
--   1.3.6.1.4.1.6296.101.4.12.3.3.10
-- 1.3.6.1.4.1.6296.101.4.12.3.3.10
		-- 1.3.6.1.4.1.6296.101.4.12.3.3.10
		sleY1731MepOutOfServiceChanged NOTIFICATION-TYPE
			OBJECTS { sleY1731MepControlRequest, sleY1731MepControlTimeStamp, sleY1731MepControlReqResult, sleY1731MepControlIdentifier, sleY1731MepControlMegIndex, 
				sleY1731MepControlOutOfService }
			STATUS current
			DESCRIPTION 
				"setY1731OutOfService"
			::= { sleY1731MepNotification 10 }

		
--   1.3.6.1.4.1.6296.101.4.12.3.3.11
-- 1.3.6.1.4.1.6296.101.4.12.3.3.11
		-- 1.3.6.1.4.1.6296.101.4.12.3.3.11
		sleY1731MepDlmEnableChanged NOTIFICATION-TYPE
			OBJECTS { sleY1731MepControlRequest, sleY1731MepControlTimeStamp, sleY1731MepControlReqResult, sleY1731MepControlIdentifier, sleY1731MepControlMegIndex, 
				sleY1731MepControlDlmEnabledRmep }
			STATUS current
			DESCRIPTION 
				"setY1731DlmEnable"
			::= { sleY1731MepNotification 11 }

		
--   1.3.6.1.4.1.6296.101.4.12.3.3.12
-- 1.3.6.1.4.1.6296.101.4.12.3.3.12
		-- 1.3.6.1.4.1.6296.101.4.12.3.3.12
		sleY1731MepTransmitLbmFinished NOTIFICATION-TYPE
			OBJECTS { sleY1731MepControlRequest, sleY1731MepControlTimeStamp, sleY1731MepControlReqResult, sleY1731MepControlIdentifier, sleY1731MepControlMegIndex
				 }
			STATUS current
			DESCRIPTION 
				"transmitY1731Lbm"
			::= { sleY1731MepNotification 12 }

		
--   1.3.6.1.4.1.6296.101.4.12.3.3.13
-- 1.3.6.1.4.1.6296.101.4.12.3.3.13
		-- 1.3.6.1.4.1.6296.101.4.12.3.3.13
		sleY1731MepTransmitLtmFinished NOTIFICATION-TYPE
			OBJECTS { sleY1731MepControlRequest, sleY1731MepControlTimeStamp, sleY1731MepControlReqResult, sleY1731MepControlIdentifier, sleY1731MepControlMegIndex
				 }
			STATUS current
			DESCRIPTION 
				"transmitY1731Ltm"
			::= { sleY1731MepNotification 13 }

		
--   1.3.6.1.4.1.6296.101.4.12.3.3.14
-- 1.3.6.1.4.1.6296.101.4.12.3.3.14
		-- 1.3.6.1.4.1.6296.101.4.12.3.3.14
		sleY1731MepTransmitTstLbmFinished NOTIFICATION-TYPE
			OBJECTS { sleY1731MepControlRequest, sleY1731MepControlTimeStamp, sleY1731MepControlReqResult, sleY1731MepControlIdentifier, sleY1731MepControlMegIndex
				 }
			STATUS current
			DESCRIPTION 
				"transmitY1731TstLbm"
			::= { sleY1731MepNotification 14 }

		
--   1.3.6.1.4.1.6296.101.4.12.3.3.15
-- 1.3.6.1.4.1.6296.101.4.12.3.3.15
		-- 1.3.6.1.4.1.6296.101.4.12.3.3.15
		sleY1731MepTransmitTmLbmFinished NOTIFICATION-TYPE
			OBJECTS { sleY1731MepControlRequest, sleY1731MepControlTimeStamp, sleY1731MepControlReqResult, sleY1731MepControlIdentifier, sleY1731MepControlMegIndex
				 }
			STATUS current
			DESCRIPTION 
				"transmitY1731TmLbm"
			::= { sleY1731MepNotification 15 }

		
--   1.3.6.1.4.1.6296.101.4.12.3.3.16
-- 1.3.6.1.4.1.6296.101.4.12.3.3.16
		-- 1.3.6.1.4.1.6296.101.4.12.3.3.16
		sleY1731MepTransmitTstFinished NOTIFICATION-TYPE
			OBJECTS { sleY1731MepControlRequest, sleY1731MepControlTimeStamp, sleY1731MepControlReqResult, sleY1731MepControlIdentifier, sleY1731MepControlMegIndex
				 }
			STATUS current
			DESCRIPTION 
				"transmitY1731Tst"
			::= { sleY1731MepNotification 16 }

		
--   1.3.6.1.4.1.6296.101.4.12.3.3.17
-- 1.3.6.1.4.1.6296.101.4.12.3.3.17
		-- 1.3.6.1.4.1.6296.101.4.12.3.3.17
		sleY1731MepReceiveTstFinished NOTIFICATION-TYPE
			OBJECTS { sleY1731MepControlRequest, sleY1731MepControlTimeStamp, sleY1731MepControlReqResult, sleY1731MepControlIdentifier, sleY1731MepControlMegIndex
				 }
			STATUS current
			DESCRIPTION 
				"receiveY1731Tst"
			::= { sleY1731MepNotification 17 }

		
--   1.3.6.1.4.1.6296.101.4.12.3.3.18
-- 1.3.6.1.4.1.6296.101.4.12.3.3.18
		-- 1.3.6.1.4.1.6296.101.4.12.3.3.18
		sleY1731MepTransmitTmTstFinished NOTIFICATION-TYPE
			OBJECTS { sleY1731MepControlRequest, sleY1731MepControlTimeStamp, sleY1731MepControlReqResult, sleY1731MepControlIdentifier, sleY1731MepControlMegIndex
				 }
			STATUS current
			DESCRIPTION 
				"transmitY1731TmTst"
			::= { sleY1731MepNotification 18 }

		
--   1.3.6.1.4.1.6296.101.4.12.3.3.19
-- 1.3.6.1.4.1.6296.101.4.12.3.3.19
		-- 1.3.6.1.4.1.6296.101.4.12.3.3.19
		sleY1731MepReceiveTmTstFinished NOTIFICATION-TYPE
			OBJECTS { sleY1731MepControlRequest, sleY1731MepControlTimeStamp, sleY1731MepControlReqResult, sleY1731MepControlIdentifier, sleY1731MepControlMegIndex
				 }
			STATUS current
			DESCRIPTION 
				"receiveY1731TmTst"
			::= { sleY1731MepNotification 19 }

		
--   1.3.6.1.4.1.6296.101.4.12.3.3.20
-- 1.3.6.1.4.1.6296.101.4.12.3.3.20
		-- 1.3.6.1.4.1.6296.101.4.12.3.3.20
		sleY1731MepTransmitLmmFinished NOTIFICATION-TYPE
			OBJECTS { sleY1731MepControlRequest, sleY1731MepControlTimeStamp, sleY1731MepControlReqResult, sleY1731MepControlIdentifier, sleY1731MepControlMegIndex
				 }
			STATUS current
			DESCRIPTION 
				"transmitY1731Lmm"
			::= { sleY1731MepNotification 20 }

		
--   1.3.6.1.4.1.6296.101.4.12.3.3.21
-- 1.3.6.1.4.1.6296.101.4.12.3.3.21
		-- 1.3.6.1.4.1.6296.101.4.12.3.3.21
		sleY1731MepTransmit1dmFinished NOTIFICATION-TYPE
			OBJECTS { sleY1731MepControlRequest, sleY1731MepControlTimeStamp, sleY1731MepControlReqResult, sleY1731MepControlIdentifier, sleY1731MepControlMegIndex
				 }
			STATUS current
			DESCRIPTION 
				"transmitY17311dm"
			::= { sleY1731MepNotification 21 }

		
--   1.3.6.1.4.1.6296.101.4.12.3.3.22
-- 1.3.6.1.4.1.6296.101.4.12.3.3.22
		-- 1.3.6.1.4.1.6296.101.4.12.3.3.22
		sleY1731MepReceive1dmFinished NOTIFICATION-TYPE
			OBJECTS { sleY1731MepControlRequest, sleY1731MepControlTimeStamp, sleY1731MepControlReqResult, sleY1731MepControlIdentifier, sleY1731MepControlMegIndex
				 }
			STATUS current
			DESCRIPTION 
				"receiveY17311dm"
			::= { sleY1731MepNotification 22 }

		
--   1.3.6.1.4.1.6296.101.4.12.3.3.23
-- 1.3.6.1.4.1.6296.101.4.12.3.3.23
		-- 1.3.6.1.4.1.6296.101.4.12.3.3.23
		sleY1731MepTransmitDmmFinished NOTIFICATION-TYPE
			OBJECTS { sleY1731MepControlRequest, sleY1731MepControlTimeStamp, sleY1731MepControlReqResult, sleY1731MepControlIdentifier, sleY1731MepControlMegIndex
				 }
			STATUS current
			DESCRIPTION 
				"transmitY1731Dmm"
			::= { sleY1731MepNotification 23 }

		
--   1.3.6.1.4.1.6296.101.4.12.3.3.24
-- 1.3.6.1.4.1.6296.101.4.12.3.3.24
		-- 1.3.6.1.4.1.6296.101.4.12.3.3.24
		sleY1731MepPmEnableChanged NOTIFICATION-TYPE
			OBJECTS { sleY1731MepControlRequest, sleY1731MepControlTimeStamp, sleY1731MepControlReqResult, sleY1731MepControlIdentifier, sleY1731MepControlMegIndex, 
				sleY1731MepControlPmEnable }
			STATUS current
			DESCRIPTION 
				"setY1731PmEnable"
			::= { sleY1731MepNotification 24 }

		
--   1.3.6.1.4.1.6296.101.4.12.3.3.25
-- 1.3.6.1.4.1.6296.101.4.12.3.3.25
		-- 1.3.6.1.4.1.6296.101.4.12.3.3.25
		sleY1731MepRllcfChanged NOTIFICATION-TYPE
			OBJECTS { sleY1731MepControlRequest, sleY1731MepControlTimeStamp, sleY1731MepControlReqResult, sleY1731MepControlIdentifier, sleY1731MepControlMegIndex, 
				sleY1731MepControlRllcf, sleY1731MepControlRllcfHoldOff, sleY1731MepControlRllcfGuardTime }
			STATUS current
			DESCRIPTION 
				"setY1731MepRllcf"
			::= { sleY1731MepNotification 25 }

		
--   1.3.6.1.4.1.6296.101.4.12.4
-- 1.3.6.1.4.1.6296.101.4.12.4
		-- 1.3.6.1.4.1.6296.101.4.12.4
		sleY1731Mip OBJECT IDENTIFIER ::= { sleY1731Oam 4 }

		
--   1.3.6.1.4.1.6296.101.4.12.4.1
-- 1.3.6.1.4.1.6296.101.4.12.4.1
		-- 1.3.6.1.4.1.6296.101.4.12.4.1
		sleY1731MipTable OBJECT-TYPE
			SYNTAX SEQUENCE OF SleY1731MipEntry
			MAX-ACCESS not-accessible
			STATUS current
			DESCRIPTION
				"Description."
			::= { sleY1731Mip 1 }

		
--   1.3.6.1.4.1.6296.101.4.12.4.1.1
-- 1.3.6.1.4.1.6296.101.4.12.4.1.1
		-- 1.3.6.1.4.1.6296.101.4.12.4.1.1
		sleY1731MipEntry OBJECT-TYPE
			SYNTAX SleY1731MipEntry
			MAX-ACCESS not-accessible
			STATUS current
			DESCRIPTION
				"Description."
			INDEX { sleY1731MipPort }
			::= { sleY1731MipTable 1 }

		
		SleY1731MipEntry ::=
			SEQUENCE { 
				sleY1731MipPort
					Integer32,
				sleY1731MipLevel
					Integer32,
				sleY1731MipType
					INTEGER
			 }

--   1.3.6.1.4.1.6296.101.4.12.4.1.1.1
-- 1.3.6.1.4.1.6296.101.4.12.4.1.1.1
		-- 1.3.6.1.4.1.6296.101.4.12.4.1.1.1
		sleY1731MipPort OBJECT-TYPE
			SYNTAX Integer32 (1..65535)
			MAX-ACCESS read-only
			STATUS current
			DESCRIPTION
				"Indicates the port number"
			::= { sleY1731MipEntry 1 }

		
--   1.3.6.1.4.1.6296.101.4.12.4.1.1.2
-- 1.3.6.1.4.1.6296.101.4.12.4.1.1.2
		-- 1.3.6.1.4.1.6296.101.4.12.4.1.1.2
		sleY1731MipLevel OBJECT-TYPE
			SYNTAX Integer32 (0..7)
			MAX-ACCESS read-only
			STATUS current
			DESCRIPTION
				"Indicates the MIP's level"
			::= { sleY1731MipEntry 2 }

		
--   1.3.6.1.4.1.6296.101.4.12.4.1.1.3
-- 1.3.6.1.4.1.6296.101.4.12.4.1.1.3
		-- 1.3.6.1.4.1.6296.101.4.12.4.1.1.3
		sleY1731MipType OBJECT-TYPE
			SYNTAX INTEGER
				{
				static(1),
				dynamic(2)
				}
			MAX-ACCESS read-only
			STATUS current
			DESCRIPTION
				"Indicate the MIP’s type"
			::= { sleY1731MipEntry 3 }

		
--   1.3.6.1.4.1.6296.101.4.12.4.2
-- 1.3.6.1.4.1.6296.101.4.12.4.2
		-- 1.3.6.1.4.1.6296.101.4.12.4.2
		sleY1731MipControl OBJECT IDENTIFIER ::= { sleY1731Mip 2 }

		
--   1.3.6.1.4.1.6296.101.4.12.4.2.1
-- 1.3.6.1.4.1.6296.101.4.12.4.2.1
		-- 1.3.6.1.4.1.6296.101.4.12.4.2.1
		sleY1731MipControlRequest OBJECT-TYPE
			SYNTAX INTEGER
				{
				createY1731Mip(1),
				deleteY1731Mip(2)
				}
			MAX-ACCESS read-write
			STATUS current
			DESCRIPTION
				"Description."
			::= { sleY1731MipControl 1 }

		
--   1.3.6.1.4.1.6296.101.4.12.4.2.2
-- 1.3.6.1.4.1.6296.101.4.12.4.2.2
		-- 1.3.6.1.4.1.6296.101.4.12.4.2.2
		sleY1731MipControlStatus OBJECT-TYPE
			SYNTAX SleControlStatusType
			MAX-ACCESS read-only
			STATUS current
			DESCRIPTION
				"Description."
			::= { sleY1731MipControl 2 }

		
--   1.3.6.1.4.1.6296.101.4.12.4.2.3
-- 1.3.6.1.4.1.6296.101.4.12.4.2.3
		-- 1.3.6.1.4.1.6296.101.4.12.4.2.3
		sleY1731MipControlTimer OBJECT-TYPE
			SYNTAX Gauge32
			MAX-ACCESS read-write
			STATUS current
			DESCRIPTION
				"Description."
			::= { sleY1731MipControl 3 }

		
--   1.3.6.1.4.1.6296.101.4.12.4.2.4
-- 1.3.6.1.4.1.6296.101.4.12.4.2.4
		-- 1.3.6.1.4.1.6296.101.4.12.4.2.4
		sleY1731MipControlTimeStamp OBJECT-TYPE
			SYNTAX TimeTicks
			MAX-ACCESS read-only
			STATUS current
			DESCRIPTION
				"Description."
			::= { sleY1731MipControl 4 }

		
--   1.3.6.1.4.1.6296.101.4.12.4.2.5
-- 1.3.6.1.4.1.6296.101.4.12.4.2.5
		-- 1.3.6.1.4.1.6296.101.4.12.4.2.5
		sleY1731MipControlReqResult OBJECT-TYPE
			SYNTAX SleControlRequestResultType
			MAX-ACCESS read-only
			STATUS current
			DESCRIPTION
				"Description."
			::= { sleY1731MipControl 5 }

		
--   1.3.6.1.4.1.6296.101.4.12.4.2.6
-- 1.3.6.1.4.1.6296.101.4.12.4.2.6
		-- 1.3.6.1.4.1.6296.101.4.12.4.2.6
		sleY1731MipControlPort OBJECT-TYPE
			SYNTAX Integer32 (1..65535)
			MAX-ACCESS read-write
			STATUS current
			DESCRIPTION
				"Indicates the port number"
			::= { sleY1731MipControl 6 }

		
--   1.3.6.1.4.1.6296.101.4.12.4.2.7
-- 1.3.6.1.4.1.6296.101.4.12.4.2.7
		-- 1.3.6.1.4.1.6296.101.4.12.4.2.7
		sleY1731MipControlLevel OBJECT-TYPE
			SYNTAX Integer32 (0..7)
			MAX-ACCESS read-write
			STATUS current
			DESCRIPTION
				"Indicates the MIP's level"
			::= { sleY1731MipControl 7 }

		
--   1.3.6.1.4.1.6296.101.4.12.4.3
-- 1.3.6.1.4.1.6296.101.4.12.4.3
		-- 1.3.6.1.4.1.6296.101.4.12.4.3
		sleY1731MipNotification OBJECT IDENTIFIER ::= { sleY1731Mip 3 }

		
--   1.3.6.1.4.1.6296.101.4.12.4.3.1
-- 1.3.6.1.4.1.6296.101.4.12.4.3.1
		-- 1.3.6.1.4.1.6296.101.4.12.4.3.1
		sleY1731MipCreated NOTIFICATION-TYPE
			OBJECTS { sleY1731MipControlRequest, sleY1731MipControlTimeStamp, sleY1731MipControlReqResult, sleY1731MipControlPort, sleY1731MipControlLevel
				 }
			STATUS current
			DESCRIPTION 
				"createY1731Mip"
			::= { sleY1731MipNotification 1 }

		
--   1.3.6.1.4.1.6296.101.4.12.4.3.2
-- 1.3.6.1.4.1.6296.101.4.12.4.3.2
		-- 1.3.6.1.4.1.6296.101.4.12.4.3.2
		sleY1731MipDeleted NOTIFICATION-TYPE
			OBJECTS { sleY1731MipControlRequest, sleY1731MipControlTimeStamp, sleY1731MipControlReqResult, sleY1731MipControlPort }
			STATUS current
			DESCRIPTION 
				"deleteY1731Mip"
			::= { sleY1731MipNotification 2 }

		
--   1.3.6.1.4.1.6296.101.4.12.5
-- 1.3.6.1.4.1.6296.101.4.12.5
		-- 1.3.6.1.4.1.6296.101.4.12.5
		sleY1731Xcheck OBJECT IDENTIFIER ::= { sleY1731Oam 5 }

		
--   1.3.6.1.4.1.6296.101.4.12.5.1
-- 1.3.6.1.4.1.6296.101.4.12.5.1
		-- 1.3.6.1.4.1.6296.101.4.12.5.1
		sleY1731XcheckTable OBJECT-TYPE
			SYNTAX SEQUENCE OF SleY1731XcheckEntry
			MAX-ACCESS not-accessible
			STATUS current
			DESCRIPTION
				"Description."
			::= { sleY1731Xcheck 1 }

		
--   1.3.6.1.4.1.6296.101.4.12.5.1.1
-- 1.3.6.1.4.1.6296.101.4.12.5.1.1
		-- 1.3.6.1.4.1.6296.101.4.12.5.1.1
		sleY1731XcheckEntry OBJECT-TYPE
			SYNTAX SleY1731XcheckEntry
			MAX-ACCESS not-accessible
			STATUS current
			DESCRIPTION
				"Description."
			INDEX { sleY1731MegIndex, sleY1731XcheckMepIdentifier }
			::= { sleY1731XcheckTable 1 }

		
		SleY1731XcheckEntry ::=
			SEQUENCE { 
				sleY1731XcheckMepIdentifier
					Integer32,
				sleY1731XcheckMepState
					INTEGER
			 }

--   1.3.6.1.4.1.6296.101.4.12.5.1.1.1
-- 1.3.6.1.4.1.6296.101.4.12.5.1.1.1
		-- 1.3.6.1.4.1.6296.101.4.12.5.1.1.1
		sleY1731XcheckMepIdentifier OBJECT-TYPE
			SYNTAX Integer32 (1..8191)
			MAX-ACCESS read-only
			STATUS current
			DESCRIPTION
				"Indicates the remote MEP's Id"
			::= { sleY1731XcheckEntry 1 }

		
--   1.3.6.1.4.1.6296.101.4.12.5.1.1.2
-- 1.3.6.1.4.1.6296.101.4.12.5.1.1.2
		-- 1.3.6.1.4.1.6296.101.4.12.5.1.1.2
		sleY1731XcheckMepState OBJECT-TYPE
			SYNTAX INTEGER
				{
				unknown(0),
				missing(1),
				up(2)
				}
			MAX-ACCESS read-only
			STATUS current
			DESCRIPTION
				"Indicates the cross-check MEP’s state"
			::= { sleY1731XcheckEntry 2 }

		
--   1.3.6.1.4.1.6296.101.4.12.5.2
-- 1.3.6.1.4.1.6296.101.4.12.5.2
		-- 1.3.6.1.4.1.6296.101.4.12.5.2
		sleY1731XcheckControl OBJECT IDENTIFIER ::= { sleY1731Xcheck 2 }

		
--   1.3.6.1.4.1.6296.101.4.12.5.2.1
-- 1.3.6.1.4.1.6296.101.4.12.5.2.1
		-- 1.3.6.1.4.1.6296.101.4.12.5.2.1
		sleY1731XcheckControlRequest OBJECT-TYPE
			SYNTAX INTEGER
				{
				createY1731XcheckMep(1),
				deleteY1731XcheckMep(2)
				}
			MAX-ACCESS read-write
			STATUS current
			DESCRIPTION
				"Description."
			::= { sleY1731XcheckControl 1 }

		
--   1.3.6.1.4.1.6296.101.4.12.5.2.2
-- 1.3.6.1.4.1.6296.101.4.12.5.2.2
		-- 1.3.6.1.4.1.6296.101.4.12.5.2.2
		sleY1731XcheckControlStatus OBJECT-TYPE
			SYNTAX SleControlStatusType
			MAX-ACCESS read-only
			STATUS current
			DESCRIPTION
				"Description."
			::= { sleY1731XcheckControl 2 }

		
--   1.3.6.1.4.1.6296.101.4.12.5.2.3
-- 1.3.6.1.4.1.6296.101.4.12.5.2.3
		-- 1.3.6.1.4.1.6296.101.4.12.5.2.3
		sleY1731XcheckControlTimer OBJECT-TYPE
			SYNTAX Gauge32
			MAX-ACCESS read-write
			STATUS current
			DESCRIPTION
				"Description."
			::= { sleY1731XcheckControl 3 }

		
--   1.3.6.1.4.1.6296.101.4.12.5.2.4
-- 1.3.6.1.4.1.6296.101.4.12.5.2.4
		-- 1.3.6.1.4.1.6296.101.4.12.5.2.4
		sleY1731XcheckControlTimeStamp OBJECT-TYPE
			SYNTAX TimeTicks
			MAX-ACCESS read-only
			STATUS current
			DESCRIPTION
				"Description."
			::= { sleY1731XcheckControl 4 }

		
--   1.3.6.1.4.1.6296.101.4.12.5.2.5
-- 1.3.6.1.4.1.6296.101.4.12.5.2.5
		-- 1.3.6.1.4.1.6296.101.4.12.5.2.5
		sleY1731XcheckControlReqResult OBJECT-TYPE
			SYNTAX SleControlRequestResultType
			MAX-ACCESS read-only
			STATUS current
			DESCRIPTION
				"Description."
			::= { sleY1731XcheckControl 5 }

		
--   1.3.6.1.4.1.6296.101.4.12.5.2.6
-- 1.3.6.1.4.1.6296.101.4.12.5.2.6
		-- 1.3.6.1.4.1.6296.101.4.12.5.2.6
		sleY1731XcheckControlMepIdentifier OBJECT-TYPE
			SYNTAX Integer32 (1..8191)
			MAX-ACCESS read-write
			STATUS current
			DESCRIPTION
				"Indicates the remote MEP's Id"
			::= { sleY1731XcheckControl 6 }

		
--   1.3.6.1.4.1.6296.101.4.12.5.2.7
-- 1.3.6.1.4.1.6296.101.4.12.5.2.7
		-- 1.3.6.1.4.1.6296.101.4.12.5.2.7
		sleY1731XcheckControlMegIndex OBJECT-TYPE
			SYNTAX Integer32 (1..65535)
			MAX-ACCESS read-write
			STATUS current
			DESCRIPTION
				"Indicates the MEG’s Index"
			::= { sleY1731XcheckControl 7 }

		
--   1.3.6.1.4.1.6296.101.4.12.5.3
-- 1.3.6.1.4.1.6296.101.4.12.5.3
		-- 1.3.6.1.4.1.6296.101.4.12.5.3
		sleY1731XcheckNotification OBJECT IDENTIFIER ::= { sleY1731Xcheck 3 }

		
--   1.3.6.1.4.1.6296.101.4.12.5.3.1
-- 1.3.6.1.4.1.6296.101.4.12.5.3.1
		-- 1.3.6.1.4.1.6296.101.4.12.5.3.1
		sleY1731XcheckMepCreated NOTIFICATION-TYPE
			OBJECTS { sleY1731XcheckControlRequest, sleY1731XcheckControlTimeStamp, sleY1731XcheckControlReqResult, sleY1731XcheckControlMepIdentifier, sleY1731XcheckControlMegIndex
				 }
			STATUS current
			DESCRIPTION 
				"createY1731XcheckMep"
			::= { sleY1731XcheckNotification 1 }

		
--   1.3.6.1.4.1.6296.101.4.12.5.3.2
-- 1.3.6.1.4.1.6296.101.4.12.5.3.2
		-- 1.3.6.1.4.1.6296.101.4.12.5.3.2
		sleY1731XcheckMepDeleted NOTIFICATION-TYPE
			OBJECTS { sleY1731XcheckControlRequest, sleY1731XcheckControlTimeStamp, sleY1731XcheckControlReqResult, sleY1731XcheckControlMepIdentifier, sleY1731XcheckControlMegIndex
				 }
			STATUS current
			DESCRIPTION 
				"deleteY1731XcheckMep"
			::= { sleY1731XcheckNotification 2 }

		
--   1.3.6.1.4.1.6296.101.4.12.6
-- 1.3.6.1.4.1.6296.101.4.12.6
		-- 1.3.6.1.4.1.6296.101.4.12.6
		sleY1731CcMac OBJECT IDENTIFIER ::= { sleY1731Oam 6 }

		
--   1.3.6.1.4.1.6296.101.4.12.6.1
-- 1.3.6.1.4.1.6296.101.4.12.6.1
		-- 1.3.6.1.4.1.6296.101.4.12.6.1
		sleY1731CcMacTable OBJECT-TYPE
			SYNTAX SEQUENCE OF SleY1731CcMacEntry
			MAX-ACCESS not-accessible
			STATUS current
			DESCRIPTION
				"Description."
			::= { sleY1731CcMac 1 }

		
--   1.3.6.1.4.1.6296.101.4.12.6.1.1
-- 1.3.6.1.4.1.6296.101.4.12.6.1.1
		-- 1.3.6.1.4.1.6296.101.4.12.6.1.1
		sleY1731CcMacEntry OBJECT-TYPE
			SYNTAX SleY1731CcMacEntry
			MAX-ACCESS not-accessible
			STATUS current
			DESCRIPTION
				"Description."
			INDEX { sleY1731MegIndex, sleY1731MepIdentifier, sleY1731CcMacAddress }
			::= { sleY1731CcMacTable 1 }

		
		SleY1731CcMacEntry ::=
			SEQUENCE { 
				sleY1731CcMacAddress
					OCTET STRING
			 }

--   1.3.6.1.4.1.6296.101.4.12.6.1.1.1
-- 1.3.6.1.4.1.6296.101.4.12.6.1.1.1
		-- 1.3.6.1.4.1.6296.101.4.12.6.1.1.1
		sleY1731CcMacAddress OBJECT-TYPE
			SYNTAX OCTET STRING (SIZE (6))
			MAX-ACCESS read-only
			STATUS current
			DESCRIPTION
				"Indicates the unicast MAC address to send CCM"
			::= { sleY1731CcMacEntry 1 }

		
--   1.3.6.1.4.1.6296.101.4.12.6.2
-- 1.3.6.1.4.1.6296.101.4.12.6.2
		-- 1.3.6.1.4.1.6296.101.4.12.6.2
		sleY1731CcMacControl OBJECT IDENTIFIER ::= { sleY1731CcMac 2 }

		
--   1.3.6.1.4.1.6296.101.4.12.6.2.1
-- 1.3.6.1.4.1.6296.101.4.12.6.2.1
		-- 1.3.6.1.4.1.6296.101.4.12.6.2.1
		sleY1731CcMacControlRequest OBJECT-TYPE
			SYNTAX INTEGER
				{
				createY1731CcMac(1),
				deleteY1731CcMac(2)
				}
			MAX-ACCESS read-write
			STATUS current
			DESCRIPTION
				"Description."
			::= { sleY1731CcMacControl 1 }

		
--   1.3.6.1.4.1.6296.101.4.12.6.2.2
-- 1.3.6.1.4.1.6296.101.4.12.6.2.2
		-- 1.3.6.1.4.1.6296.101.4.12.6.2.2
		sleY1731CcMacControlStatus OBJECT-TYPE
			SYNTAX SleControlStatusType
			MAX-ACCESS read-only
			STATUS current
			DESCRIPTION
				"Description."
			::= { sleY1731CcMacControl 2 }

		
--   1.3.6.1.4.1.6296.101.4.12.6.2.3
-- 1.3.6.1.4.1.6296.101.4.12.6.2.3
		-- 1.3.6.1.4.1.6296.101.4.12.6.2.3
		sleY1731CcMacControlTimer OBJECT-TYPE
			SYNTAX Gauge32
			MAX-ACCESS read-write
			STATUS current
			DESCRIPTION
				"Description."
			::= { sleY1731CcMacControl 3 }

		
--   1.3.6.1.4.1.6296.101.4.12.6.2.4
-- 1.3.6.1.4.1.6296.101.4.12.6.2.4
		-- 1.3.6.1.4.1.6296.101.4.12.6.2.4
		sleY1731CcMacControlTimeStamp OBJECT-TYPE
			SYNTAX TimeTicks
			MAX-ACCESS read-only
			STATUS current
			DESCRIPTION
				"Description."
			::= { sleY1731CcMacControl 4 }

		
--   1.3.6.1.4.1.6296.101.4.12.6.2.5
-- 1.3.6.1.4.1.6296.101.4.12.6.2.5
		-- 1.3.6.1.4.1.6296.101.4.12.6.2.5
		sleY1731CcMacControlReqResult OBJECT-TYPE
			SYNTAX SleControlRequestResultType
			MAX-ACCESS read-only
			STATUS current
			DESCRIPTION
				"Result of the last command."
			::= { sleY1731CcMacControl 5 }

		
--   1.3.6.1.4.1.6296.101.4.12.6.2.6
-- 1.3.6.1.4.1.6296.101.4.12.6.2.6
		-- 1.3.6.1.4.1.6296.101.4.12.6.2.6
		sleY1731CcMacControlMegIndex OBJECT-TYPE
			SYNTAX Integer32 (1..65535)
			MAX-ACCESS read-write
			STATUS current
			DESCRIPTION
				"Indicates the MEG's Index"
			::= { sleY1731CcMacControl 6 }

		
--   1.3.6.1.4.1.6296.101.4.12.6.2.7
-- 1.3.6.1.4.1.6296.101.4.12.6.2.7
		-- 1.3.6.1.4.1.6296.101.4.12.6.2.7
		sleY1731CcMacControlMepIdentifier OBJECT-TYPE
			SYNTAX Integer32 (1..8191)
			MAX-ACCESS read-write
			STATUS current
			DESCRIPTION
				"MEP Id"
			::= { sleY1731CcMacControl 7 }

		
--   1.3.6.1.4.1.6296.101.4.12.6.2.8
-- 1.3.6.1.4.1.6296.101.4.12.6.2.8
		-- 1.3.6.1.4.1.6296.101.4.12.6.2.8
		sleY1731CcMacControlAddress OBJECT-TYPE
			SYNTAX OCTET STRING (SIZE (6))
			MAX-ACCESS read-write
			STATUS current
			DESCRIPTION
				"Indicates the unicast MAC address to send CCM
				When running deleteY1731CcMac, if this is zero-length, delete all unicast mac."
			::= { sleY1731CcMacControl 8 }

		
--   1.3.6.1.4.1.6296.101.4.12.6.3
-- 1.3.6.1.4.1.6296.101.4.12.6.3
		-- 1.3.6.1.4.1.6296.101.4.12.6.3
		sleY1731CcMacNotification OBJECT IDENTIFIER ::= { sleY1731CcMac 3 }

		
--   1.3.6.1.4.1.6296.101.4.12.6.3.1
-- 1.3.6.1.4.1.6296.101.4.12.6.3.1
		-- 1.3.6.1.4.1.6296.101.4.12.6.3.1
		sleY1731CcMacCreated NOTIFICATION-TYPE
			OBJECTS { sleY1731CcMacControlRequest, sleY1731CcMacControlTimeStamp, sleY1731CcMacControlReqResult, sleY1731CcMacControlMegIndex, sleY1731CcMacControlMepIdentifier, 
				sleY1731CcMacControlAddress }
			STATUS current
			DESCRIPTION 
				"createY1731CcMac"
			::= { sleY1731CcMacNotification 1 }

		
--   1.3.6.1.4.1.6296.101.4.12.6.3.2
-- 1.3.6.1.4.1.6296.101.4.12.6.3.2
		-- 1.3.6.1.4.1.6296.101.4.12.6.3.2
		sleY1731CcMacDeleted NOTIFICATION-TYPE
			OBJECTS { sleY1731CcMacControlRequest, sleY1731CcMacControlTimeStamp, sleY1731CcMacControlReqResult, sleY1731CcMacControlMegIndex, sleY1731CcMacControlMepIdentifier, 
				sleY1731CcMacControlAddress }
			STATUS current
			DESCRIPTION 
				"deleteY1731CcMac"
			::= { sleY1731CcMacNotification 2 }

		
--   1.3.6.1.4.1.6296.101.4.12.7
-- 1.3.6.1.4.1.6296.101.4.12.7
		-- 1.3.6.1.4.1.6296.101.4.12.7
		sleY1731AisMac OBJECT IDENTIFIER ::= { sleY1731Oam 7 }

		
--   1.3.6.1.4.1.6296.101.4.12.7.1
-- 1.3.6.1.4.1.6296.101.4.12.7.1
		-- 1.3.6.1.4.1.6296.101.4.12.7.1
		sleY1731AisMacTable OBJECT-TYPE
			SYNTAX SEQUENCE OF SleY1731AisMacEntry
			MAX-ACCESS not-accessible
			STATUS current
			DESCRIPTION
				"Description."
			::= { sleY1731AisMac 1 }

		
--   1.3.6.1.4.1.6296.101.4.12.7.1.1
-- 1.3.6.1.4.1.6296.101.4.12.7.1.1
		-- 1.3.6.1.4.1.6296.101.4.12.7.1.1
		sleY1731AisMacEntry OBJECT-TYPE
			SYNTAX SleY1731AisMacEntry
			MAX-ACCESS not-accessible
			STATUS current
			DESCRIPTION
				"Description."
			INDEX { sleY1731MegIndex, sleY1731MepIdentifier, sleY1731AisMacAddress }
			::= { sleY1731AisMacTable 1 }

		
		SleY1731AisMacEntry ::=
			SEQUENCE { 
				sleY1731AisMacAddress
					OCTET STRING
			 }

--   1.3.6.1.4.1.6296.101.4.12.7.1.1.1
-- 1.3.6.1.4.1.6296.101.4.12.7.1.1.1
		-- 1.3.6.1.4.1.6296.101.4.12.7.1.1.1
		sleY1731AisMacAddress OBJECT-TYPE
			SYNTAX OCTET STRING (SIZE (6))
			MAX-ACCESS read-only
			STATUS current
			DESCRIPTION
				"Indicates the unicast MAC address to send AIS"
			::= { sleY1731AisMacEntry 1 }

		
--   1.3.6.1.4.1.6296.101.4.12.7.2
-- 1.3.6.1.4.1.6296.101.4.12.7.2
		-- 1.3.6.1.4.1.6296.101.4.12.7.2
		sleY1731AisMacControl OBJECT IDENTIFIER ::= { sleY1731AisMac 2 }

		
--   1.3.6.1.4.1.6296.101.4.12.7.2.1
-- 1.3.6.1.4.1.6296.101.4.12.7.2.1
		-- 1.3.6.1.4.1.6296.101.4.12.7.2.1
		sleY1731AisMacControlRequest OBJECT-TYPE
			SYNTAX INTEGER
				{
				createY1731AisMac(1),
				deleteY1731AisMac(2)
				}
			MAX-ACCESS read-write
			STATUS current
			DESCRIPTION
				"Description."
			::= { sleY1731AisMacControl 1 }

		
--   1.3.6.1.4.1.6296.101.4.12.7.2.2
-- 1.3.6.1.4.1.6296.101.4.12.7.2.2
		-- 1.3.6.1.4.1.6296.101.4.12.7.2.2
		sleY1731AisMacControlStatus OBJECT-TYPE
			SYNTAX SleControlStatusType
			MAX-ACCESS read-only
			STATUS current
			DESCRIPTION
				"Description."
			::= { sleY1731AisMacControl 2 }

		
--   1.3.6.1.4.1.6296.101.4.12.7.2.3
-- 1.3.6.1.4.1.6296.101.4.12.7.2.3
		-- 1.3.6.1.4.1.6296.101.4.12.7.2.3
		sleY1731AisMacControlTimer OBJECT-TYPE
			SYNTAX Gauge32
			MAX-ACCESS read-write
			STATUS current
			DESCRIPTION
				"Description."
			::= { sleY1731AisMacControl 3 }

		
--   1.3.6.1.4.1.6296.101.4.12.7.2.4
-- 1.3.6.1.4.1.6296.101.4.12.7.2.4
		-- 1.3.6.1.4.1.6296.101.4.12.7.2.4
		sleY1731AisMacControlTimeStamp OBJECT-TYPE
			SYNTAX TimeTicks
			MAX-ACCESS read-only
			STATUS current
			DESCRIPTION
				"Description."
			::= { sleY1731AisMacControl 4 }

		
--   1.3.6.1.4.1.6296.101.4.12.7.2.5
-- 1.3.6.1.4.1.6296.101.4.12.7.2.5
		-- 1.3.6.1.4.1.6296.101.4.12.7.2.5
		sleY1731AisMacControlReqResult OBJECT-TYPE
			SYNTAX SleControlRequestResultType
			MAX-ACCESS read-only
			STATUS current
			DESCRIPTION
				"Description."
			::= { sleY1731AisMacControl 5 }

		
--   1.3.6.1.4.1.6296.101.4.12.7.2.6
-- 1.3.6.1.4.1.6296.101.4.12.7.2.6
		-- 1.3.6.1.4.1.6296.101.4.12.7.2.6
		sleY1731AisMacControlMegIndex OBJECT-TYPE
			SYNTAX Integer32 (1..65535)
			MAX-ACCESS read-write
			STATUS current
			DESCRIPTION
				"Indicates the MEG's Index"
			::= { sleY1731AisMacControl 6 }

		
--   1.3.6.1.4.1.6296.101.4.12.7.2.7
-- 1.3.6.1.4.1.6296.101.4.12.7.2.7
		-- 1.3.6.1.4.1.6296.101.4.12.7.2.7
		sleY1731AisMacControlMepIdentifier OBJECT-TYPE
			SYNTAX Integer32 (1..8191)
			MAX-ACCESS read-write
			STATUS current
			DESCRIPTION
				"MEP Id"
			::= { sleY1731AisMacControl 7 }

		
--   1.3.6.1.4.1.6296.101.4.12.7.2.8
-- 1.3.6.1.4.1.6296.101.4.12.7.2.8
		-- 1.3.6.1.4.1.6296.101.4.12.7.2.8
		sleY1731AisMacControlAddress OBJECT-TYPE
			SYNTAX OCTET STRING (SIZE (6))
			MAX-ACCESS read-write
			STATUS current
			DESCRIPTION
				"Indicates the unicast MAC address to send AIS
				When running deleteY1731AisMac, if this is zero-length, delete all unicast mac."
			::= { sleY1731AisMacControl 8 }

		
--   1.3.6.1.4.1.6296.101.4.12.7.3
-- 1.3.6.1.4.1.6296.101.4.12.7.3
		-- 1.3.6.1.4.1.6296.101.4.12.7.3
		sleY1731AisMacNotification OBJECT IDENTIFIER ::= { sleY1731AisMac 3 }

		
--   1.3.6.1.4.1.6296.101.4.12.7.3.1
-- 1.3.6.1.4.1.6296.101.4.12.7.3.1
		-- 1.3.6.1.4.1.6296.101.4.12.7.3.1
		sleY1731AisMacCreated NOTIFICATION-TYPE
			OBJECTS { sleY1731AisMacControlRequest, sleY1731AisMacControlTimeStamp, sleY1731AisMacControlReqResult, sleY1731AisMacControlMegIndex, sleY1731AisMacControlMepIdentifier, 
				sleY1731AisMacControlAddress }
			STATUS current
			DESCRIPTION 
				"createY1731AisMac"
			::= { sleY1731AisMacNotification 1 }

		
--   1.3.6.1.4.1.6296.101.4.12.7.3.2
-- 1.3.6.1.4.1.6296.101.4.12.7.3.2
		-- 1.3.6.1.4.1.6296.101.4.12.7.3.2
		sleY1731AisMacDeleted NOTIFICATION-TYPE
			OBJECTS { sleY1731AisMacControlRequest, sleY1731AisMacControlTimeStamp, sleY1731AisMacControlReqResult, sleY1731AisMacControlMegIndex, sleY1731AisMacControlMepIdentifier, 
				sleY1731AisMacControlAddress }
			STATUS current
			DESCRIPTION 
				"deleteY1731AisMac"
			::= { sleY1731AisMacNotification 2 }

		
--   1.3.6.1.4.1.6296.101.4.12.8
-- 1.3.6.1.4.1.6296.101.4.12.8
		-- 1.3.6.1.4.1.6296.101.4.12.8
		sleY1731LckMac OBJECT IDENTIFIER ::= { sleY1731Oam 8 }

		
--   1.3.6.1.4.1.6296.101.4.12.8.1
-- 1.3.6.1.4.1.6296.101.4.12.8.1
		-- 1.3.6.1.4.1.6296.101.4.12.8.1
		sleY1731LckMacTable OBJECT-TYPE
			SYNTAX SEQUENCE OF SleY1731LckMacEntry
			MAX-ACCESS not-accessible
			STATUS current
			DESCRIPTION
				"Description."
			::= { sleY1731LckMac 1 }

		
--   1.3.6.1.4.1.6296.101.4.12.8.1.1
-- 1.3.6.1.4.1.6296.101.4.12.8.1.1
		-- 1.3.6.1.4.1.6296.101.4.12.8.1.1
		sleY1731LckMacEntry OBJECT-TYPE
			SYNTAX SleY1731LckMacEntry
			MAX-ACCESS not-accessible
			STATUS current
			DESCRIPTION
				"Description."
			INDEX { sleY1731MegIndex, sleY1731MepIdentifier, sleY1731LckMacAddress }
			::= { sleY1731LckMacTable 1 }

		
		SleY1731LckMacEntry ::=
			SEQUENCE { 
				sleY1731LckMacAddress
					OCTET STRING
			 }

--   1.3.6.1.4.1.6296.101.4.12.8.1.1.1
-- 1.3.6.1.4.1.6296.101.4.12.8.1.1.1
		-- 1.3.6.1.4.1.6296.101.4.12.8.1.1.1
		sleY1731LckMacAddress OBJECT-TYPE
			SYNTAX OCTET STRING (SIZE (6))
			MAX-ACCESS read-write
			STATUS current
			DESCRIPTION
				"Indicates the unicast MAC address to send LCK"
			::= { sleY1731LckMacEntry 1 }

		
--   1.3.6.1.4.1.6296.101.4.12.8.2
-- 1.3.6.1.4.1.6296.101.4.12.8.2
		-- 1.3.6.1.4.1.6296.101.4.12.8.2
		sleY1731LckMacControl OBJECT IDENTIFIER ::= { sleY1731LckMac 2 }

		
--   1.3.6.1.4.1.6296.101.4.12.8.2.1
-- 1.3.6.1.4.1.6296.101.4.12.8.2.1
		-- 1.3.6.1.4.1.6296.101.4.12.8.2.1
		sleY1731LckMacControlRequest OBJECT-TYPE
			SYNTAX INTEGER
				{
				createY1731LckMac(1),
				deleteY1731LckMac(2)
				}
			MAX-ACCESS read-write
			STATUS current
			DESCRIPTION
				"Description."
			::= { sleY1731LckMacControl 1 }

		
--   1.3.6.1.4.1.6296.101.4.12.8.2.2
-- 1.3.6.1.4.1.6296.101.4.12.8.2.2
		-- 1.3.6.1.4.1.6296.101.4.12.8.2.2
		sleY1731LckMacControlStatus OBJECT-TYPE
			SYNTAX SleControlStatusType
			MAX-ACCESS read-only
			STATUS current
			DESCRIPTION
				"Description."
			::= { sleY1731LckMacControl 2 }

		
--   1.3.6.1.4.1.6296.101.4.12.8.2.3
-- 1.3.6.1.4.1.6296.101.4.12.8.2.3
		-- 1.3.6.1.4.1.6296.101.4.12.8.2.3
		sleY1731LckMacControlTimer OBJECT-TYPE
			SYNTAX Gauge32
			MAX-ACCESS read-write
			STATUS current
			DESCRIPTION
				"Description."
			::= { sleY1731LckMacControl 3 }

		
--   1.3.6.1.4.1.6296.101.4.12.8.2.4
-- 1.3.6.1.4.1.6296.101.4.12.8.2.4
		-- 1.3.6.1.4.1.6296.101.4.12.8.2.4
		sleY1731LckMacControlTimeStamp OBJECT-TYPE
			SYNTAX TimeTicks
			MAX-ACCESS read-only
			STATUS current
			DESCRIPTION
				"Description."
			::= { sleY1731LckMacControl 4 }

		
--   1.3.6.1.4.1.6296.101.4.12.8.2.5
-- 1.3.6.1.4.1.6296.101.4.12.8.2.5
		-- 1.3.6.1.4.1.6296.101.4.12.8.2.5
		sleY1731LckMacControlReqResult OBJECT-TYPE
			SYNTAX SleControlRequestResultType
			MAX-ACCESS read-only
			STATUS current
			DESCRIPTION
				"Description."
			::= { sleY1731LckMacControl 5 }

		
--   1.3.6.1.4.1.6296.101.4.12.8.2.6
-- 1.3.6.1.4.1.6296.101.4.12.8.2.6
		-- 1.3.6.1.4.1.6296.101.4.12.8.2.6
		sleY1731LckMacControlMegIndex OBJECT-TYPE
			SYNTAX Integer32 (1..65535)
			MAX-ACCESS read-write
			STATUS current
			DESCRIPTION
				"Indicates the MEG's Index"
			::= { sleY1731LckMacControl 6 }

		
--   1.3.6.1.4.1.6296.101.4.12.8.2.7
-- 1.3.6.1.4.1.6296.101.4.12.8.2.7
		-- 1.3.6.1.4.1.6296.101.4.12.8.2.7
		sleY1731LckMacControlMepIdentifier OBJECT-TYPE
			SYNTAX Integer32 (1..8191)
			MAX-ACCESS read-write
			STATUS current
			DESCRIPTION
				"MEP Id"
			::= { sleY1731LckMacControl 7 }

		
--   1.3.6.1.4.1.6296.101.4.12.8.2.8
-- 1.3.6.1.4.1.6296.101.4.12.8.2.8
		-- 1.3.6.1.4.1.6296.101.4.12.8.2.8
		sleY1731LckMacControlAddress OBJECT-TYPE
			SYNTAX OCTET STRING (SIZE (6))
			MAX-ACCESS read-write
			STATUS current
			DESCRIPTION
				"Indicates the unicast MAC address to send LCK
				When running deleteY1731LckMac, if this is zero-length, delete all unicast mac."
			::= { sleY1731LckMacControl 8 }

		
--   1.3.6.1.4.1.6296.101.4.12.8.3
-- 1.3.6.1.4.1.6296.101.4.12.8.3
		-- 1.3.6.1.4.1.6296.101.4.12.8.3
		sleY1731LckMacNotification OBJECT IDENTIFIER ::= { sleY1731LckMac 3 }

		
--   1.3.6.1.4.1.6296.101.4.12.8.3.1
-- 1.3.6.1.4.1.6296.101.4.12.8.3.1
		-- 1.3.6.1.4.1.6296.101.4.12.8.3.1
		sleY1731LckMacCreated NOTIFICATION-TYPE
			OBJECTS { sleY1731LckMacControlRequest, sleY1731LckMacControlTimeStamp, sleY1731LckMacControlReqResult, sleY1731LckMacControlMegIndex, sleY1731LckMacControlMepIdentifier, 
				sleY1731LckMacControlAddress }
			STATUS current
			DESCRIPTION 
				"createY1731LckMac"
			::= { sleY1731LckMacNotification 1 }

		
--   1.3.6.1.4.1.6296.101.4.12.8.3.2
-- 1.3.6.1.4.1.6296.101.4.12.8.3.2
		-- 1.3.6.1.4.1.6296.101.4.12.8.3.2
		sleY1731LckMacDeleted NOTIFICATION-TYPE
			OBJECTS { sleY1731LckMacControlRequest, sleY1731LckMacControlTimeStamp, sleY1731LckMacControlReqResult, sleY1731LckMacControlMegIndex, sleY1731LckMacControlMepIdentifier, 
				sleY1731LckMacControlAddress }
			STATUS current
			DESCRIPTION 
				"deleteY1731LckMac"
			::= { sleY1731LckMacNotification 2 }

		
--   1.3.6.1.4.1.6296.101.4.12.9
-- 1.3.6.1.4.1.6296.101.4.12.9
		-- 1.3.6.1.4.1.6296.101.4.12.9
		sleY1731Rmep OBJECT IDENTIFIER ::= { sleY1731Oam 9 }

		
--   1.3.6.1.4.1.6296.101.4.12.9.1
-- 1.3.6.1.4.1.6296.101.4.12.9.1
		-- 1.3.6.1.4.1.6296.101.4.12.9.1
		sleY1731RmepTable OBJECT-TYPE
			SYNTAX SEQUENCE OF SleY1731RmepEntry
			MAX-ACCESS not-accessible
			STATUS current
			DESCRIPTION
				"Description."
			::= { sleY1731Rmep 1 }

		
--   1.3.6.1.4.1.6296.101.4.12.9.1.1
-- 1.3.6.1.4.1.6296.101.4.12.9.1.1
		-- 1.3.6.1.4.1.6296.101.4.12.9.1.1
		sleY1731RmepEntry OBJECT-TYPE
			SYNTAX SleY1731RmepEntry
			MAX-ACCESS not-accessible
			STATUS current
			DESCRIPTION
				"Description."
			INDEX { sleY1731MegIndex, sleY1731MepIdentifier, sleY1731RmepIdentifier }
			::= { sleY1731RmepTable 1 }

		
		SleY1731RmepEntry ::=
			SEQUENCE { 
				sleY1731RmepIdentifier
					Integer32,
				sleY1731RmepState
					INTEGER,
				sleY1731RmepFailedOkTime
					TimeTicks,
				sleY1731RmepMacAddress
					OCTET STRING,
				sleY1731RmepIfIndex
					Integer32,
				sleY1731RmepRdi
					INTEGER,
				sleY1731RmepLoc
					INTEGER,
				sleY1731RmepReceiveTstCount
					Counter32,
				sleY1731RmepReceiveTstOutOfOrder
					Counter32,
				sleY1731RmepReceiveTstBitError
					Counter32,
				sleY1731RmepReceiveTstCrcError
					Counter32,
				sleY1731RmepReceiveTmTstCount
					Counter32,
				sleY1731RmepReceiveTmTstLostId
					Integer32,
				sleY1731RmepLmrFrameLossNearMin
					Integer32,
				sleY1731RmepLmrFrameLossNearMax
					Integer32,
				sleY1731RmepLmrFrameLossNearSum
					Integer32,
				sleY1731RmepLmrFrameLossFarMin
					Integer32,
				sleY1731RmepLmrFrameLossFarMax
					Integer32,
				sleY1731RmepLmrFrameLossFarSum
					Integer32,
				sleY1731RmepReceive1dmCount
					Counter32,
				sleY1731Rmep1dmFrameDelayMin
					Integer32,
				sleY1731Rmep1dmFrameDelayMax
					Integer32,
				sleY1731Rmep1dmFrameDelayAvg
					Integer32,
				sleY1731Rmep1dmFrameDelayVar
					Integer32,
				sleY1731RmepReceiveDmrCount
					Counter32,
				sleY1731RmepDmrFrameDelayMin
					Integer32,
				sleY1731RmepDmrFrameDelayMax
					Integer32,
				sleY1731RmepDmrFrameDelayAvg
					Integer32,
				sleY1731RmepDmrFrameDelayVar
					Integer32,
				sleY1731RmepLmrFrameLossNearRatio
					Integer32,
				sleY1731RmepLmrFrameLossNearAvgRatio
					Integer32,
				sleY1731RmepLmrFrameLossFarRatio
					Integer32,
				sleY1731RmepLmrFrameLossFarAvgRatio
					Integer32
			 }

--   1.3.6.1.4.1.6296.101.4.12.9.1.1.1
-- 1.3.6.1.4.1.6296.101.4.12.9.1.1.1
		-- 1.3.6.1.4.1.6296.101.4.12.9.1.1.1
		sleY1731RmepIdentifier OBJECT-TYPE
			SYNTAX Integer32 (1..8191)
			MAX-ACCESS read-only
			STATUS current
			DESCRIPTION
				"Indicates the remote MEP's Id"
			::= { sleY1731RmepEntry 1 }

		
--   1.3.6.1.4.1.6296.101.4.12.9.1.1.2
-- 1.3.6.1.4.1.6296.101.4.12.9.1.1.2
		-- 1.3.6.1.4.1.6296.101.4.12.9.1.1.2
		sleY1731RmepState OBJECT-TYPE
			SYNTAX INTEGER
				{
				start(1),
				failed(2),
				ok(3)
				}
			MAX-ACCESS read-only
			STATUS current
			DESCRIPTION
				"Indicates the operational state of the remote MEP State machines"
			::= { sleY1731RmepEntry 2 }

		
--   1.3.6.1.4.1.6296.101.4.12.9.1.1.3
-- 1.3.6.1.4.1.6296.101.4.12.9.1.1.3
		-- 1.3.6.1.4.1.6296.101.4.12.9.1.1.3
		sleY1731RmepFailedOkTime OBJECT-TYPE
			SYNTAX TimeTicks
			MAX-ACCESS read-only
			STATUS current
			DESCRIPTION
				"Indicates the time (SysUpTime) at which the Remote MEP state machine last entered either the RMEP_FAILED or RMEP_OK state."
			::= { sleY1731RmepEntry 3 }

		
--   1.3.6.1.4.1.6296.101.4.12.9.1.1.4
-- 1.3.6.1.4.1.6296.101.4.12.9.1.1.4
		-- 1.3.6.1.4.1.6296.101.4.12.9.1.1.4
		sleY1731RmepMacAddress OBJECT-TYPE
			SYNTAX OCTET STRING (SIZE (6))
			MAX-ACCESS read-only
			STATUS current
			DESCRIPTION
				"Indicates the MAC address of the remote MEP"
			::= { sleY1731RmepEntry 4 }

		
--   1.3.6.1.4.1.6296.101.4.12.9.1.1.5
-- 1.3.6.1.4.1.6296.101.4.12.9.1.1.5
		-- 1.3.6.1.4.1.6296.101.4.12.9.1.1.5
		sleY1731RmepIfIndex OBJECT-TYPE
			SYNTAX Integer32
			MAX-ACCESS read-only
			STATUS current
			DESCRIPTION
				"Indicates the port number of the remote MEP"
			::= { sleY1731RmepEntry 5 }

		
--   
-- 
-- 1.3.6.1.4.1.6296.101.4.12.9.1.1.6
-- 1.3.6.1.4.1.6296.101.4.12.9.1.1.6
		-- 1.3.6.1.4.1.6296.101.4.12.9.1.1.6
		sleY1731RmepRdi OBJECT-TYPE
			SYNTAX INTEGER
				{
				false(0),
				true(1)
				}
			MAX-ACCESS read-only
			STATUS current
			DESCRIPTION
				"Indicates State of the RDI bit in the last received CCM (true for RDI=1), or false if none has been received"
			::= { sleY1731RmepEntry 6 }

		
--   1.3.6.1.4.1.6296.101.4.12.9.1.1.7
-- 1.3.6.1.4.1.6296.101.4.12.9.1.1.7
		-- 1.3.6.1.4.1.6296.101.4.12.9.1.1.7
		sleY1731RmepLoc OBJECT-TYPE
			SYNTAX INTEGER
				{
				false(0),
				true(1)
				}
			MAX-ACCESS read-only
			STATUS current
			DESCRIPTION
				"Indicates Loss-of-continuity"
			::= { sleY1731RmepEntry 7 }

		
--   1.3.6.1.4.1.6296.101.4.12.9.1.1.8
-- 1.3.6.1.4.1.6296.101.4.12.9.1.1.8
		-- 1.3.6.1.4.1.6296.101.4.12.9.1.1.8
		sleY1731RmepReceiveTstCount OBJECT-TYPE
			SYNTAX Counter32
			MAX-ACCESS read-only
			STATUS current
			DESCRIPTION
				"Indicates the number of received TST frame"
			::= { sleY1731RmepEntry 8 }

		
--   1.3.6.1.4.1.6296.101.4.12.9.1.1.9
-- 1.3.6.1.4.1.6296.101.4.12.9.1.1.9
		-- 1.3.6.1.4.1.6296.101.4.12.9.1.1.9
		sleY1731RmepReceiveTstOutOfOrder OBJECT-TYPE
			SYNTAX Counter32
			MAX-ACCESS read-only
			STATUS current
			DESCRIPTION
				"Indicates the number of received out-of-order TST frame"
			::= { sleY1731RmepEntry 9 }

		
--   1.3.6.1.4.1.6296.101.4.12.9.1.1.10
-- 1.3.6.1.4.1.6296.101.4.12.9.1.1.10
		-- 1.3.6.1.4.1.6296.101.4.12.9.1.1.10
		sleY1731RmepReceiveTstBitError OBJECT-TYPE
			SYNTAX Counter32
			MAX-ACCESS read-only
			STATUS current
			DESCRIPTION
				"Indicates the number of received bit-error TST frame"
			::= { sleY1731RmepEntry 10 }

		
--   1.3.6.1.4.1.6296.101.4.12.9.1.1.11
-- 1.3.6.1.4.1.6296.101.4.12.9.1.1.11
		-- 1.3.6.1.4.1.6296.101.4.12.9.1.1.11
		sleY1731RmepReceiveTstCrcError OBJECT-TYPE
			SYNTAX Counter32
			MAX-ACCESS read-only
			STATUS current
			DESCRIPTION
				"Indicates the number of received crc-error TST frame"
			::= { sleY1731RmepEntry 11 }

		
--   1.3.6.1.4.1.6296.101.4.12.9.1.1.12
-- 1.3.6.1.4.1.6296.101.4.12.9.1.1.12
		-- 1.3.6.1.4.1.6296.101.4.12.9.1.1.12
		sleY1731RmepReceiveTmTstCount OBJECT-TYPE
			SYNTAX Counter32
			MAX-ACCESS read-only
			STATUS current
			DESCRIPTION
				"Indicates the number of received TST frame for the throughput-measurement"
			::= { sleY1731RmepEntry 12 }

		
--   1.3.6.1.4.1.6296.101.4.12.9.1.1.13
-- 1.3.6.1.4.1.6296.101.4.12.9.1.1.13
		-- 1.3.6.1.4.1.6296.101.4.12.9.1.1.13
		sleY1731RmepReceiveTmTstLostId OBJECT-TYPE
			SYNTAX Integer32
			MAX-ACCESS read-only
			STATUS current
			DESCRIPTION
				"Indicates the transaction identifier of first lost TST frame for the throughput-measurement"
			::= { sleY1731RmepEntry 13 }

		
--   1.3.6.1.4.1.6296.101.4.12.9.1.1.14
-- 1.3.6.1.4.1.6296.101.4.12.9.1.1.14
		-- 1.3.6.1.4.1.6296.101.4.12.9.1.1.14
		sleY1731RmepLmrFrameLossNearMin OBJECT-TYPE
			SYNTAX Integer32
			MAX-ACCESS read-only
			STATUS current
			DESCRIPTION
				"Indicates the minimum of single-ended near-end frame loss"
			::= { sleY1731RmepEntry 14 }

		
--   1.3.6.1.4.1.6296.101.4.12.9.1.1.15
-- 1.3.6.1.4.1.6296.101.4.12.9.1.1.15
		-- 1.3.6.1.4.1.6296.101.4.12.9.1.1.15
		sleY1731RmepLmrFrameLossNearMax OBJECT-TYPE
			SYNTAX Integer32
			MAX-ACCESS read-only
			STATUS current
			DESCRIPTION
				"Indicates the maximum of single-ended near-end frame loss"
			::= { sleY1731RmepEntry 15 }

		
--   1.3.6.1.4.1.6296.101.4.12.9.1.1.16
-- 1.3.6.1.4.1.6296.101.4.12.9.1.1.16
		-- 1.3.6.1.4.1.6296.101.4.12.9.1.1.16
		sleY1731RmepLmrFrameLossNearSum OBJECT-TYPE
			SYNTAX Integer32
			MAX-ACCESS read-only
			STATUS current
			DESCRIPTION
				"Indicates the sum of single-ended near-end frame loss"
			::= { sleY1731RmepEntry 16 }

		
--   1.3.6.1.4.1.6296.101.4.12.9.1.1.17
-- 1.3.6.1.4.1.6296.101.4.12.9.1.1.17
		-- 1.3.6.1.4.1.6296.101.4.12.9.1.1.17
		sleY1731RmepLmrFrameLossFarMin OBJECT-TYPE
			SYNTAX Integer32
			MAX-ACCESS read-only
			STATUS current
			DESCRIPTION
				"Indicates the minimum of single-ended far-end frame loss"
			::= { sleY1731RmepEntry 17 }

		
--   1.3.6.1.4.1.6296.101.4.12.9.1.1.18
-- 1.3.6.1.4.1.6296.101.4.12.9.1.1.18
		-- 1.3.6.1.4.1.6296.101.4.12.9.1.1.18
		sleY1731RmepLmrFrameLossFarMax OBJECT-TYPE
			SYNTAX Integer32
			MAX-ACCESS read-only
			STATUS current
			DESCRIPTION
				"Indicates the maximum of single-ended far-end frame loss"
			::= { sleY1731RmepEntry 18 }

		
--   1.3.6.1.4.1.6296.101.4.12.9.1.1.19
-- 1.3.6.1.4.1.6296.101.4.12.9.1.1.19
		-- 1.3.6.1.4.1.6296.101.4.12.9.1.1.19
		sleY1731RmepLmrFrameLossFarSum OBJECT-TYPE
			SYNTAX Integer32
			MAX-ACCESS read-only
			STATUS current
			DESCRIPTION
				"Indicates the sum of single-ended far-end frame loss"
			::= { sleY1731RmepEntry 19 }

		
--   1.3.6.1.4.1.6296.101.4.12.9.1.1.20
-- 1.3.6.1.4.1.6296.101.4.12.9.1.1.20
		-- 1.3.6.1.4.1.6296.101.4.12.9.1.1.20
		sleY1731RmepReceive1dmCount OBJECT-TYPE
			SYNTAX Counter32
			MAX-ACCESS read-only
			STATUS current
			DESCRIPTION
				"Indicates the number of received 1DM frames for the frame delay measurement"
			::= { sleY1731RmepEntry 20 }

		
--   1.3.6.1.4.1.6296.101.4.12.9.1.1.21
-- 1.3.6.1.4.1.6296.101.4.12.9.1.1.21
		-- 1.3.6.1.4.1.6296.101.4.12.9.1.1.21
		sleY1731Rmep1dmFrameDelayMin OBJECT-TYPE
			SYNTAX Integer32
			MAX-ACCESS read-only
			STATUS current
			DESCRIPTION
				"Indicates the minimum of one-way frame delay"
			::= { sleY1731RmepEntry 21 }

		
--   1.3.6.1.4.1.6296.101.4.12.9.1.1.22
-- 1.3.6.1.4.1.6296.101.4.12.9.1.1.22
		-- 1.3.6.1.4.1.6296.101.4.12.9.1.1.22
		sleY1731Rmep1dmFrameDelayMax OBJECT-TYPE
			SYNTAX Integer32
			MAX-ACCESS read-only
			STATUS current
			DESCRIPTION
				"Indicates the maximum of one-way frame delay"
			::= { sleY1731RmepEntry 22 }

		
--   1.3.6.1.4.1.6296.101.4.12.9.1.1.23
-- 1.3.6.1.4.1.6296.101.4.12.9.1.1.23
		-- 1.3.6.1.4.1.6296.101.4.12.9.1.1.23
		sleY1731Rmep1dmFrameDelayAvg OBJECT-TYPE
			SYNTAX Integer32
			MAX-ACCESS read-only
			STATUS current
			DESCRIPTION
				"Indicates the average of one-way frame delay"
			::= { sleY1731RmepEntry 23 }

		
--   1.3.6.1.4.1.6296.101.4.12.9.1.1.24
-- 1.3.6.1.4.1.6296.101.4.12.9.1.1.24
		-- 1.3.6.1.4.1.6296.101.4.12.9.1.1.24
		sleY1731Rmep1dmFrameDelayVar OBJECT-TYPE
			SYNTAX Integer32
			MAX-ACCESS read-only
			STATUS current
			DESCRIPTION
				"Indicates the variation of one-way frame delay"
			::= { sleY1731RmepEntry 24 }

		
--   1.3.6.1.4.1.6296.101.4.12.9.1.1.25
-- 1.3.6.1.4.1.6296.101.4.12.9.1.1.25
		-- 1.3.6.1.4.1.6296.101.4.12.9.1.1.25
		sleY1731RmepReceiveDmrCount OBJECT-TYPE
			SYNTAX Counter32
			MAX-ACCESS read-only
			STATUS current
			DESCRIPTION
				"Indicates the number of received DMR frames for the frame delay measurement"
			::= { sleY1731RmepEntry 25 }

		
--   1.3.6.1.4.1.6296.101.4.12.9.1.1.26
-- 1.3.6.1.4.1.6296.101.4.12.9.1.1.26
		-- 1.3.6.1.4.1.6296.101.4.12.9.1.1.26
		sleY1731RmepDmrFrameDelayMin OBJECT-TYPE
			SYNTAX Integer32
			MAX-ACCESS read-only
			STATUS current
			DESCRIPTION
				"Indicates the minimum of two-way frame delay"
			::= { sleY1731RmepEntry 26 }

		
--   1.3.6.1.4.1.6296.101.4.12.9.1.1.27
-- 1.3.6.1.4.1.6296.101.4.12.9.1.1.27
		-- 1.3.6.1.4.1.6296.101.4.12.9.1.1.27
		sleY1731RmepDmrFrameDelayMax OBJECT-TYPE
			SYNTAX Integer32
			MAX-ACCESS read-only
			STATUS current
			DESCRIPTION
				"Indicates the maximum of two-way frame delay"
			::= { sleY1731RmepEntry 27 }

		
--   1.3.6.1.4.1.6296.101.4.12.9.1.1.28
-- 1.3.6.1.4.1.6296.101.4.12.9.1.1.28
		-- 1.3.6.1.4.1.6296.101.4.12.9.1.1.28
		sleY1731RmepDmrFrameDelayAvg OBJECT-TYPE
			SYNTAX Integer32
			MAX-ACCESS read-only
			STATUS current
			DESCRIPTION
				"Indicates the average of two-way frame delay"
			::= { sleY1731RmepEntry 28 }

		
--   1.3.6.1.4.1.6296.101.4.12.9.1.1.29
-- 1.3.6.1.4.1.6296.101.4.12.9.1.1.29
		-- 1.3.6.1.4.1.6296.101.4.12.9.1.1.29
		sleY1731RmepDmrFrameDelayVar OBJECT-TYPE
			SYNTAX Integer32
			MAX-ACCESS read-only
			STATUS current
			DESCRIPTION
				"Indicates the variation of two-way frame delay"
			::= { sleY1731RmepEntry 29 }

		
--   1.3.6.1.4.1.6296.101.4.12.9.1.1.30
-- 1.3.6.1.4.1.6296.101.4.12.9.1.1.30
		-- 1.3.6.1.4.1.6296.101.4.12.9.1.1.30
		sleY1731RmepLmrFrameLossNearRatio OBJECT-TYPE
			SYNTAX Integer32
			MAX-ACCESS read-only
			STATUS current
			DESCRIPTION
				"Indicates the ratio of single-ended near-end frame loss"
			::= { sleY1731RmepEntry 30 }

		
--   1.3.6.1.4.1.6296.101.4.12.9.1.1.31
-- 1.3.6.1.4.1.6296.101.4.12.9.1.1.31
		-- 1.3.6.1.4.1.6296.101.4.12.9.1.1.31
		sleY1731RmepLmrFrameLossNearAvgRatio OBJECT-TYPE
			SYNTAX Integer32
			MAX-ACCESS read-only
			STATUS current
			DESCRIPTION
				"Indicates the average ratio of single-ended near-end frame loss"
			::= { sleY1731RmepEntry 31 }

		
--   1.3.6.1.4.1.6296.101.4.12.9.1.1.32
-- 1.3.6.1.4.1.6296.101.4.12.9.1.1.32
		-- 1.3.6.1.4.1.6296.101.4.12.9.1.1.32
		sleY1731RmepLmrFrameLossFarRatio OBJECT-TYPE
			SYNTAX Integer32
			MAX-ACCESS read-only
			STATUS current
			DESCRIPTION
				"Indicates the ratio of single-ended far-end frame loss"
			::= { sleY1731RmepEntry 32 }

		
--   1.3.6.1.4.1.6296.101.4.12.9.1.1.33
-- 1.3.6.1.4.1.6296.101.4.12.9.1.1.33
		-- 1.3.6.1.4.1.6296.101.4.12.9.1.1.33
		sleY1731RmepLmrFrameLossFarAvgRatio OBJECT-TYPE
			SYNTAX Integer32
			MAX-ACCESS read-only
			STATUS current
			DESCRIPTION
				"Indicates the average ratio of single-ended far-end frame loss"
			::= { sleY1731RmepEntry 33 }

		
--   1.3.6.1.4.1.6296.101.4.12.9.2
-- 1.3.6.1.4.1.6296.101.4.12.9.2
		-- 1.3.6.1.4.1.6296.101.4.12.9.2
		sleY1731RmepControl OBJECT IDENTIFIER ::= { sleY1731Rmep 2 }

		
--   1.3.6.1.4.1.6296.101.4.12.9.2.1
-- 1.3.6.1.4.1.6296.101.4.12.9.2.1
		-- 1.3.6.1.4.1.6296.101.4.12.9.2.1
		sleY1731RmepControlRequest OBJECT-TYPE
			SYNTAX INTEGER
				{
				createY1731Rmep(1),
				deleteY1731Rmep(2)
				}
			MAX-ACCESS read-write
			STATUS current
			DESCRIPTION
				"Description."
			::= { sleY1731RmepControl 1 }

		
--   1.3.6.1.4.1.6296.101.4.12.9.2.2
-- 1.3.6.1.4.1.6296.101.4.12.9.2.2
		-- 1.3.6.1.4.1.6296.101.4.12.9.2.2
		sleY1731RMepControlStatus OBJECT-TYPE
			SYNTAX SleControlStatusType
			MAX-ACCESS read-only
			STATUS current
			DESCRIPTION
				"Description."
			::= { sleY1731RmepControl 2 }

		
--   1.3.6.1.4.1.6296.101.4.12.9.2.3
-- 1.3.6.1.4.1.6296.101.4.12.9.2.3
		-- 1.3.6.1.4.1.6296.101.4.12.9.2.3
		sleY1731RmepControlTimer OBJECT-TYPE
			SYNTAX Gauge32
			MAX-ACCESS read-write
			STATUS current
			DESCRIPTION
				"Description."
			::= { sleY1731RmepControl 3 }

		
--   1.3.6.1.4.1.6296.101.4.12.9.2.4
-- 1.3.6.1.4.1.6296.101.4.12.9.2.4
		-- 1.3.6.1.4.1.6296.101.4.12.9.2.4
		sleY1731RmepControlTimeStamp OBJECT-TYPE
			SYNTAX TimeTicks
			MAX-ACCESS read-only
			STATUS current
			DESCRIPTION
				"Description."
			::= { sleY1731RmepControl 4 }

		
--   1.3.6.1.4.1.6296.101.4.12.9.2.5
-- 1.3.6.1.4.1.6296.101.4.12.9.2.5
		-- 1.3.6.1.4.1.6296.101.4.12.9.2.5
		sleY1731RmepControlReqResult OBJECT-TYPE
			SYNTAX SleControlRequestResultType
			MAX-ACCESS read-only
			STATUS current
			DESCRIPTION
				"Description."
			::= { sleY1731RmepControl 5 }

		
--   1.3.6.1.4.1.6296.101.4.12.9.2.6
-- 1.3.6.1.4.1.6296.101.4.12.9.2.6
		-- 1.3.6.1.4.1.6296.101.4.12.9.2.6
		sleY1731RmepControlIdentifier OBJECT-TYPE
			SYNTAX Integer32 (1..8191)
			MAX-ACCESS read-write
			STATUS current
			DESCRIPTION
				"Remote MEP Id"
			::= { sleY1731RmepControl 6 }

		
--   1.3.6.1.4.1.6296.101.4.12.9.2.7
-- 1.3.6.1.4.1.6296.101.4.12.9.2.7
		-- 1.3.6.1.4.1.6296.101.4.12.9.2.7
		sleY1731RmepControlMegIndex OBJECT-TYPE
			SYNTAX Integer32 (1..65535)
			MAX-ACCESS read-write
			STATUS current
			DESCRIPTION
				"A index of MEG table"
			::= { sleY1731RmepControl 7 }

		
--   1.3.6.1.4.1.6296.101.4.12.9.2.8
-- 1.3.6.1.4.1.6296.101.4.12.9.2.8
		-- 1.3.6.1.4.1.6296.101.4.12.9.2.8
		sleY1731RmepControlIfIndex OBJECT-TYPE
			SYNTAX Integer32
			MAX-ACCESS read-write
			STATUS current
			DESCRIPTION
				"Bridge Port Index whitch the MEP is attached"
			::= { sleY1731RmepControl 8 }

		
--   1.3.6.1.4.1.6296.101.4.12.9.3
-- 1.3.6.1.4.1.6296.101.4.12.9.3
		-- 1.3.6.1.4.1.6296.101.4.12.9.3
		sleY1731RmepNotification OBJECT IDENTIFIER ::= { sleY1731Rmep 3 }

		
--   1.3.6.1.4.1.6296.101.4.12.9.3.1
-- 1.3.6.1.4.1.6296.101.4.12.9.3.1
		-- 1.3.6.1.4.1.6296.101.4.12.9.3.1
		sleY1731RmepCreated NOTIFICATION-TYPE
			OBJECTS { sleY1731RmepControlRequest, sleY1731RmepControlTimeStamp, sleY1731RmepControlReqResult, sleY1731RmepControlIdentifier, sleY1731RmepControlMegIndex, 
				sleY1731RmepControlIfIndex }
			STATUS current
			DESCRIPTION 
				"Description."
			::= { sleY1731RmepNotification 1 }

		
--   1.3.6.1.4.1.6296.101.4.12.9.3.2
-- 1.3.6.1.4.1.6296.101.4.12.9.3.2
		-- 1.3.6.1.4.1.6296.101.4.12.9.3.2
		sleY1731RmepDeleted NOTIFICATION-TYPE
			OBJECTS { sleY1731RmepControlRequest, sleY1731RmepControlTimeStamp, sleY1731RmepControlReqResult, sleY1731RmepControlIdentifier, sleY1731RmepControlMegIndex, 
				sleY1731RmepControlIfIndex }
			STATUS current
			DESCRIPTION 
				"Description."
			::= { sleY1731RmepNotification 2 }

		
--   1.3.6.1.4.1.6296.101.4.12.10
-- 1.3.6.1.4.1.6296.101.4.12.10
		-- 1.3.6.1.4.1.6296.101.4.12.10
		sleY1731LbrMcast OBJECT IDENTIFIER ::= { sleY1731Oam 10 }

		
--   1.3.6.1.4.1.6296.101.4.12.10.1
-- 1.3.6.1.4.1.6296.101.4.12.10.1
		-- 1.3.6.1.4.1.6296.101.4.12.10.1
		sleY1731LbrMcastTable OBJECT-TYPE
			SYNTAX SEQUENCE OF SleY1731LbrMcastEntry
			MAX-ACCESS not-accessible
			STATUS current
			DESCRIPTION
				"Description."
			::= { sleY1731LbrMcast 1 }

		
--   1.3.6.1.4.1.6296.101.4.12.10.1.1
-- 1.3.6.1.4.1.6296.101.4.12.10.1.1
		-- 1.3.6.1.4.1.6296.101.4.12.10.1.1
		sleY1731LbrMcastEntry OBJECT-TYPE
			SYNTAX SleY1731LbrMcastEntry
			MAX-ACCESS not-accessible
			STATUS current
			DESCRIPTION
				"Description."
			INDEX { sleY1731MegIndex, sleY1731MepIdentifier, sleY1731LbrReceiveOrder }
			::= { sleY1731LbrMcastTable 1 }

		
		SleY1731LbrMcastEntry ::=
			SEQUENCE { 
				sleY1731LbrReceiveOrder
					Integer32,
				sleY1731LbrRemoteMacAddress
					OCTET STRING
			 }

--   1.3.6.1.4.1.6296.101.4.12.10.1.1.1
-- 1.3.6.1.4.1.6296.101.4.12.10.1.1.1
		-- 1.3.6.1.4.1.6296.101.4.12.10.1.1.1
		sleY1731LbrReceiveOrder OBJECT-TYPE
			SYNTAX Integer32 (1..65535)
			MAX-ACCESS read-only
			STATUS current
			DESCRIPTION
				"Indicates an index to distinguish among multiple LBRs"
			::= { sleY1731LbrMcastEntry 1 }

		
--   1.3.6.1.4.1.6296.101.4.12.10.1.1.2
-- 1.3.6.1.4.1.6296.101.4.12.10.1.1.2
		-- 1.3.6.1.4.1.6296.101.4.12.10.1.1.2
		sleY1731LbrRemoteMacAddress OBJECT-TYPE
			SYNTAX OCTET STRING (SIZE (6))
			MAX-ACCESS read-only
			STATUS current
			DESCRIPTION
				"Indicates the MAC address of the remote MEP"
			::= { sleY1731LbrMcastEntry 2 }

		
--   1.3.6.1.4.1.6296.101.4.12.11
-- 1.3.6.1.4.1.6296.101.4.12.11
		-- 1.3.6.1.4.1.6296.101.4.12.11
		sleY1731LbrUcast OBJECT IDENTIFIER ::= { sleY1731Oam 11 }

		
--   1.3.6.1.4.1.6296.101.4.12.11.1
-- 1.3.6.1.4.1.6296.101.4.12.11.1
		-- 1.3.6.1.4.1.6296.101.4.12.11.1
		sleY1731LbrUcastTable OBJECT-TYPE
			SYNTAX SEQUENCE OF SleY1731LbrUcastEntry
			MAX-ACCESS not-accessible
			STATUS current
			DESCRIPTION
				"Description."
			::= { sleY1731LbrUcast 1 }

		
--   1.3.6.1.4.1.6296.101.4.12.11.1.1
-- 1.3.6.1.4.1.6296.101.4.12.11.1.1
		-- 1.3.6.1.4.1.6296.101.4.12.11.1.1
		sleY1731LbrUcastEntry OBJECT-TYPE
			SYNTAX SleY1731LbrUcastEntry
			MAX-ACCESS not-accessible
			STATUS current
			DESCRIPTION
				"Description."
			INDEX { sleY1731MegIndex, sleY1731MepIdentifier, sleY1731LbrTransId }
			::= { sleY1731LbrUcastTable 1 }

		
		SleY1731LbrUcastEntry ::=
			SEQUENCE { 
				sleY1731LbrTransId
					Integer32,
				sleY1731LbrRoundTripTime
					Integer32
			 }

--   1.3.6.1.4.1.6296.101.4.12.11.1.1.1
-- 1.3.6.1.4.1.6296.101.4.12.11.1.1.1
		-- 1.3.6.1.4.1.6296.101.4.12.11.1.1.1
		sleY1731LbrTransId OBJECT-TYPE
			SYNTAX Integer32 (1..65535)
			MAX-ACCESS read-only
			STATUS current
			DESCRIPTION
				"Indicates the transaction identifier of LBR message."
			::= { sleY1731LbrUcastEntry 1 }

		
--   1.3.6.1.4.1.6296.101.4.12.11.1.1.2
-- 1.3.6.1.4.1.6296.101.4.12.11.1.1.2
		-- 1.3.6.1.4.1.6296.101.4.12.11.1.1.2
		sleY1731LbrRoundTripTime OBJECT-TYPE
			SYNTAX Integer32 (1..65535)
			MAX-ACCESS read-only
			STATUS current
			DESCRIPTION
				"Indicates the round-trip time of LBR message."
			::= { sleY1731LbrUcastEntry 2 }

		
--   1.3.6.1.4.1.6296.101.4.12.12
-- 1.3.6.1.4.1.6296.101.4.12.12
		-- 1.3.6.1.4.1.6296.101.4.12.12
		sleY1731Ltr OBJECT IDENTIFIER ::= { sleY1731Oam 12 }

		
--   1.3.6.1.4.1.6296.101.4.12.12.1
-- 1.3.6.1.4.1.6296.101.4.12.12.1
		-- 1.3.6.1.4.1.6296.101.4.12.12.1
		sleY1731LtrTable OBJECT-TYPE
			SYNTAX SEQUENCE OF SleY1731LtrEntry
			MAX-ACCESS not-accessible
			STATUS current
			DESCRIPTION
				"Description."
			::= { sleY1731Ltr 1 }

		
--   1.3.6.1.4.1.6296.101.4.12.12.1.1
-- 1.3.6.1.4.1.6296.101.4.12.12.1.1
		-- 1.3.6.1.4.1.6296.101.4.12.12.1.1
		sleY1731LtrEntry OBJECT-TYPE
			SYNTAX SleY1731LtrEntry
			MAX-ACCESS not-accessible
			STATUS current
			DESCRIPTION
				"Description."
			INDEX { sleY1731MegIndex, sleY1731MepIdentifier, sleY1731LtrSeqNumber, sleY1731LtrReceiveOrder }
			::= { sleY1731LtrTable 1 }

		
		SleY1731LtrEntry ::=
			SEQUENCE { 
				sleY1731LtrSeqNumber
					Integer32,
				sleY1731LtrReceiveOrder
					Integer32,
				sleY1731LtrRoundTripTime
					Integer32,
				sleY1731LtrTtl
					Integer32,
				sleY1731LtrForwarded
					INTEGER,
				sleY1731LtrTerminalMep
					INTEGER,
				sleY1731LtrLastEgressIdentifier
					OCTET STRING,
				sleY1731LtrNextEgressIdentifier
					OCTET STRING,
				sleY1731LtrRelay
					INTEGER,
				sleY1731LtrIngress
					INTEGER,
				sleY1731LtrIngressMac
					OCTET STRING,
				sleY1731LtrIngressPort
					Integer32,
				sleY1731LtrEgress
					INTEGER,
				sleY1731LtrEgressMac
					OCTET STRING,
				sleY1731LtrEgressPort
					Integer32
			 }

--   1.3.6.1.4.1.6296.101.4.12.12.1.1.1
-- 1.3.6.1.4.1.6296.101.4.12.12.1.1.1
		-- 1.3.6.1.4.1.6296.101.4.12.12.1.1.1
		sleY1731LtrSeqNumber OBJECT-TYPE
			SYNTAX Integer32 (1..65535)
			MAX-ACCESS read-only
			STATUS current
			DESCRIPTION
				"Indicates the LTM Transaction Identifier returned from a previous Transmit Linktrace Message command,
				indicating the LTM entry to which the LTR entries will be attached
				"
			::= { sleY1731LtrEntry 1 }

		
--   1.3.6.1.4.1.6296.101.4.12.12.1.1.2
-- 1.3.6.1.4.1.6296.101.4.12.12.1.1.2
		-- 1.3.6.1.4.1.6296.101.4.12.12.1.1.2
		sleY1731LtrReceiveOrder OBJECT-TYPE
			SYNTAX Integer32 (1..65535)
			MAX-ACCESS read-only
			STATUS current
			DESCRIPTION
				"Indicates an index to distinguish among multiple LTRs with the same LTR Transaction Identifier field value"
			::= { sleY1731LtrEntry 2 }

		
--   1.3.6.1.4.1.6296.101.4.12.12.1.1.3
-- 1.3.6.1.4.1.6296.101.4.12.12.1.1.3
		-- 1.3.6.1.4.1.6296.101.4.12.12.1.1.3
		sleY1731LtrRoundTripTime OBJECT-TYPE
			SYNTAX Integer32
			MAX-ACCESS read-only
			STATUS current
			DESCRIPTION
				"Indicates the round-trip time of LTR message."
			::= { sleY1731LtrEntry 3 }

		
--    1.3.6.1.4.1.6296.101.4.12.12.1.1.3
-- 1.3.6.1.4.1.6296.101.4.12.12.1.1.4
-- 1.3.6.1.4.1.6296.101.4.12.12.1.1.4
		-- 1.3.6.1.4.1.6296.101.4.12.12.1.1.4
		sleY1731LtrTtl OBJECT-TYPE
			SYNTAX Integer32 (1..64)
			MAX-ACCESS read-only
			STATUS current
			DESCRIPTION
				"Indicates TTL field value for a returned LTR."
			::= { sleY1731LtrEntry 4 }

		
--   1.3.6.1.4.1.6296.101.4.12.12.1.1.5
-- 1.3.6.1.4.1.6296.101.4.12.12.1.1.5
		-- 1.3.6.1.4.1.6296.101.4.12.12.1.1.5
		sleY1731LtrForwarded OBJECT-TYPE
			SYNTAX INTEGER
				{
				false(0),
				true(1)
				}
			MAX-ACCESS read-only
			STATUS current
			DESCRIPTION
				"Indicates if a LTM was forwarded by the responding MP, as returned in the 'FwdYes' flag of the flags field."
			::= { sleY1731LtrEntry 5 }

		
--   1.3.6.1.4.1.6296.101.4.12.12.1.1.6
-- 1.3.6.1.4.1.6296.101.4.12.12.1.1.6
		-- 1.3.6.1.4.1.6296.101.4.12.12.1.1.6
		sleY1731LtrTerminalMep OBJECT-TYPE
			SYNTAX INTEGER
				{
				false(0),
				true(1)
				}
			MAX-ACCESS read-only
			STATUS current
			DESCRIPTION
				"Indicates a boolean value stating whether the forwarded LTM reached a MEP enclosing its MA, as returned in the Terminal MEP flag of the Flags field.  	"
			::= { sleY1731LtrEntry 6 }

		
--   1.3.6.1.4.1.6296.101.4.12.12.1.1.7
-- 1.3.6.1.4.1.6296.101.4.12.12.1.1.7
		-- 1.3.6.1.4.1.6296.101.4.12.12.1.1.7
		sleY1731LtrLastEgressIdentifier OBJECT-TYPE
			SYNTAX OCTET STRING (SIZE (8))
			MAX-ACCESS read-only
			STATUS current
			DESCRIPTION
				"Identifies the MEP Linktrace Initiator that originated, or the Linktrace Responder that forwarded, the LTM to which this LTR is the response"
			::= { sleY1731LtrEntry 7 }

		
--   1.3.6.1.4.1.6296.101.4.12.12.1.1.8
-- 1.3.6.1.4.1.6296.101.4.12.12.1.1.8
		-- 1.3.6.1.4.1.6296.101.4.12.12.1.1.8
		sleY1731LtrNextEgressIdentifier OBJECT-TYPE
			SYNTAX OCTET STRING (SIZE (8))
			MAX-ACCESS read-only
			STATUS current
			DESCRIPTION
				"Identifies the Linktrace Responder that transmitted this LTR, and can forward the LTM to the next hop."
			::= { sleY1731LtrEntry 8 }

		
--   1.3.6.1.4.1.6296.101.4.12.12.1.1.9
-- 1.3.6.1.4.1.6296.101.4.12.12.1.1.9
		-- 1.3.6.1.4.1.6296.101.4.12.12.1.1.9
		sleY1731LtrRelay OBJECT-TYPE
			SYNTAX INTEGER
				{
				rlyHit(1),
				rlyFDB(2),
				rlyMPDB(3)
				}
			MAX-ACCESS read-only
			STATUS current
			DESCRIPTION
				"Indicates the value returned in the Ingress Action Field of the LTM"
			::= { sleY1731LtrEntry 9 }

		
--   1.3.6.1.4.1.6296.101.4.12.12.1.1.10
-- 1.3.6.1.4.1.6296.101.4.12.12.1.1.10
		-- 1.3.6.1.4.1.6296.101.4.12.12.1.1.10
		sleY1731LtrIngress OBJECT-TYPE
			SYNTAX INTEGER
				{
				ingNoTlv(0),
				ingOK(1),
				ingDown(2),
				ingBlocked(3),
				ingVid(4)
				}
			MAX-ACCESS read-only
			STATUS current
			DESCRIPTION
				"Indicates the value returned in the Ingress Action Field of the LTM"
			::= { sleY1731LtrEntry 10 }

		
--   1.3.6.1.4.1.6296.101.4.12.12.1.1.11
-- 1.3.6.1.4.1.6296.101.4.12.12.1.1.11
		-- 1.3.6.1.4.1.6296.101.4.12.12.1.1.11
		sleY1731LtrIngressMac OBJECT-TYPE
			SYNTAX OCTET STRING (SIZE (6))
			MAX-ACCESS read-only
			STATUS current
			DESCRIPTION
				"Indicates MAC address returned in the ingress MAC address field."
			::= { sleY1731LtrEntry 11 }

		
--   1.3.6.1.4.1.6296.101.4.12.12.1.1.12
-- 1.3.6.1.4.1.6296.101.4.12.12.1.1.12
		-- 1.3.6.1.4.1.6296.101.4.12.12.1.1.12
		sleY1731LtrIngressPort OBJECT-TYPE
			SYNTAX Integer32
			MAX-ACCESS read-only
			STATUS current
			DESCRIPTION
				"Indicates Ingress Port ID"
			::= { sleY1731LtrEntry 12 }

		
--   1.3.6.1.4.1.6296.101.4.12.12.1.1.13
-- 1.3.6.1.4.1.6296.101.4.12.12.1.1.13
		-- 1.3.6.1.4.1.6296.101.4.12.12.1.1.13
		sleY1731LtrEgress OBJECT-TYPE
			SYNTAX INTEGER
				{
				egrNoTlv(0),
				egrOK(1),
				egrDown(2),
				egrBlocked(3),
				egrVid(4)
				}
			MAX-ACCESS read-only
			STATUS current
			DESCRIPTION
				"Indicates the value returned in the Egress Action Field of the LTM"
			::= { sleY1731LtrEntry 13 }

		
--   1.3.6.1.4.1.6296.101.4.12.12.1.1.14
-- 1.3.6.1.4.1.6296.101.4.12.12.1.1.14
		-- 1.3.6.1.4.1.6296.101.4.12.12.1.1.14
		sleY1731LtrEgressMac OBJECT-TYPE
			SYNTAX OCTET STRING (SIZE (6))
			MAX-ACCESS read-only
			STATUS current
			DESCRIPTION
				"Indicates MAC address returned in the egress MAC address field."
			::= { sleY1731LtrEntry 14 }

		
--   1.3.6.1.4.1.6296.101.4.12.12.1.1.15
-- 1.3.6.1.4.1.6296.101.4.12.12.1.1.15
		-- 1.3.6.1.4.1.6296.101.4.12.12.1.1.15
		sleY1731LtrEgressPort OBJECT-TYPE
			SYNTAX Integer32
			MAX-ACCESS read-only
			STATUS current
			DESCRIPTION
				"Indicates Egress Port ID"
			::= { sleY1731LtrEntry 15 }

		
--   1.3.6.1.4.1.6296.101.4.12.13
-- 1.3.6.1.4.1.6296.101.4.12.13
		-- 1.3.6.1.4.1.6296.101.4.12.13
		sleY1731ConfigError OBJECT IDENTIFIER ::= { sleY1731Oam 13 }

		
--   1.3.6.1.4.1.6296.101.4.12.13.1
-- 1.3.6.1.4.1.6296.101.4.12.13.1
		-- 1.3.6.1.4.1.6296.101.4.12.13.1
		sleY1731ConfigErrorTable OBJECT-TYPE
			SYNTAX SEQUENCE OF SleY1731ConfigErrorEntry
			MAX-ACCESS not-accessible
			STATUS current
			DESCRIPTION
				"Description."
			::= { sleY1731ConfigError 1 }

		
--   1.3.6.1.4.1.6296.101.4.12.13.1.1
-- 1.3.6.1.4.1.6296.101.4.12.13.1.1
		-- 1.3.6.1.4.1.6296.101.4.12.13.1.1
		sleY1731ConfigErrorEntry OBJECT-TYPE
			SYNTAX SleY1731ConfigErrorEntry
			MAX-ACCESS not-accessible
			STATUS current
			DESCRIPTION
				"Description."
			INDEX { sleY1731ConfigErrorVid, sleY1731ConfigErrorIfIndex }
			::= { sleY1731ConfigErrorTable 1 }

		
		SleY1731ConfigErrorEntry ::=
			SEQUENCE { 
				sleY1731ConfigErrorVid
					Integer32,
				sleY1731ConfigErrorIfIndex
					Integer32,
				sleY1731ConfigErrorType
					BITS
			 }

--   1.3.6.1.4.1.6296.101.4.12.13.1.1.1
-- 1.3.6.1.4.1.6296.101.4.12.13.1.1.1
		-- 1.3.6.1.4.1.6296.101.4.12.13.1.1.1
		sleY1731ConfigErrorVid OBJECT-TYPE
			SYNTAX Integer32 (1..4094)
			MAX-ACCESS read-only
			STATUS current
			DESCRIPTION
				"Indicates the Configuration Error VLAN Identifier"
			::= { sleY1731ConfigErrorEntry 1 }

		
--   1.3.6.1.4.1.6296.101.4.12.13.1.1.2
-- 1.3.6.1.4.1.6296.101.4.12.13.1.1.2
		-- 1.3.6.1.4.1.6296.101.4.12.13.1.1.2
		sleY1731ConfigErrorIfIndex OBJECT-TYPE
			SYNTAX Integer32 (1..65535)
			MAX-ACCESS read-only
			STATUS current
			DESCRIPTION
				"Indicates the Configuration Error Port Number"
			::= { sleY1731ConfigErrorEntry 2 }

		
--   1.3.6.1.4.1.6296.101.4.12.13.1.1.3
-- 1.3.6.1.4.1.6296.101.4.12.13.1.1.3
		-- 1.3.6.1.4.1.6296.101.4.12.13.1.1.3
		sleY1731ConfigErrorType OBJECT-TYPE
			SYNTAX BITS
				{
				y1731leak(0),
				conflictingVids(1),
				excessiveLevels(2),
				overlappedLevels(3)
				}
			MAX-ACCESS read-only
			STATUS current
			DESCRIPTION
				"Indicates the Configuration Error Type"
			::= { sleY1731ConfigErrorEntry 3 }

		
--   1.3.6.1.4.1.6296.101.4.12.14
-- 1.3.6.1.4.1.6296.101.4.12.14
		-- 1.3.6.1.4.1.6296.101.4.12.14
		sleY1731MipCcdb OBJECT IDENTIFIER ::= { sleY1731Oam 14 }

		
--   1.3.6.1.4.1.6296.101.4.12.14.1
-- 1.3.6.1.4.1.6296.101.4.12.14.1
		-- 1.3.6.1.4.1.6296.101.4.12.14.1
		sleY1731MipCcdbTable OBJECT-TYPE
			SYNTAX SEQUENCE OF SleY1731MipCcdbEntry
			MAX-ACCESS not-accessible
			STATUS current
			DESCRIPTION
				"Description."
			::= { sleY1731MipCcdb 1 }

		
--   1.3.6.1.4.1.6296.101.4.12.14.1.1
-- 1.3.6.1.4.1.6296.101.4.12.14.1.1
		-- 1.3.6.1.4.1.6296.101.4.12.14.1.1
		sleY1731MipCcdbEntry OBJECT-TYPE
			SYNTAX SleY1731MipCcdbEntry
			MAX-ACCESS not-accessible
			STATUS current
			DESCRIPTION
				"Description."
			INDEX { sleY1731MipCcdbIndex }
			::= { sleY1731MipCcdbTable 1 }

		
		SleY1731MipCcdbEntry ::=
			SEQUENCE { 
				sleY1731MipCcdbIndex
					Integer32,
				sleY1731MipCcdbVlanId
					Integer32,
				sleY1731MipCcdbMacAddr
					OCTET STRING,
				sleY1731MipCcdbPort
					Integer32,
				sleY1731MipCcdbKeepTime
					TimeTicks
			 }

--   1.3.6.1.4.1.6296.101.4.12.14.1.1.1
-- 1.3.6.1.4.1.6296.101.4.12.14.1.1.1
		-- 1.3.6.1.4.1.6296.101.4.12.14.1.1.1
		sleY1731MipCcdbIndex OBJECT-TYPE
			SYNTAX Integer32 (1..65535)
			MAX-ACCESS read-only
			STATUS current
			DESCRIPTION
				"Indicates the MIP CCDB's Index"
			::= { sleY1731MipCcdbEntry 1 }

		
--   1.3.6.1.4.1.6296.101.4.12.14.1.1.2
-- 1.3.6.1.4.1.6296.101.4.12.14.1.1.2
		-- 1.3.6.1.4.1.6296.101.4.12.14.1.1.2
		sleY1731MipCcdbVlanId OBJECT-TYPE
			SYNTAX Integer32 (1..4094)
			MAX-ACCESS read-only
			STATUS current
			DESCRIPTION
				"VLAN Id"
			::= { sleY1731MipCcdbEntry 2 }

		
--   1.3.6.1.4.1.6296.101.4.12.14.1.1.3
-- 1.3.6.1.4.1.6296.101.4.12.14.1.1.3
		-- 1.3.6.1.4.1.6296.101.4.12.14.1.1.3
		sleY1731MipCcdbMacAddr OBJECT-TYPE
			SYNTAX OCTET STRING (SIZE (6))
			MAX-ACCESS read-only
			STATUS current
			DESCRIPTION
				"Indicates MAC address of the remote MEP"
			::= { sleY1731MipCcdbEntry 3 }

		
--   1.3.6.1.4.1.6296.101.4.12.14.1.1.4
-- 1.3.6.1.4.1.6296.101.4.12.14.1.1.4
		-- 1.3.6.1.4.1.6296.101.4.12.14.1.1.4
		sleY1731MipCcdbPort OBJECT-TYPE
			SYNTAX Integer32
			MAX-ACCESS read-only
			STATUS current
			DESCRIPTION
				"Indicates the Port number that the CCM output"
			::= { sleY1731MipCcdbEntry 4 }

		
--   1.3.6.1.4.1.6296.101.4.12.14.1.1.5
-- 1.3.6.1.4.1.6296.101.4.12.14.1.1.5
		-- 1.3.6.1.4.1.6296.101.4.12.14.1.1.5
		sleY1731MipCcdbKeepTime OBJECT-TYPE
			SYNTAX TimeTicks
			MAX-ACCESS read-only
			STATUS current
			DESCRIPTION
				"Indicates an up-date time of a entry"
			::= { sleY1731MipCcdbEntry 5 }

		
--   1.3.6.1.4.1.6296.101.4.12.15
-- 1.3.6.1.4.1.6296.101.4.12.15
		-- 1.3.6.1.4.1.6296.101.4.12.15
		sleY1731UplinkRedundancy OBJECT IDENTIFIER ::= { sleY1731Oam 15 }

		
--   1.3.6.1.4.1.6296.101.4.12.15.1
-- 1.3.6.1.4.1.6296.101.4.12.15.1
		-- 1.3.6.1.4.1.6296.101.4.12.15.1
		sleY1731URTable OBJECT-TYPE
			SYNTAX SEQUENCE OF SleY1731UREntry
			MAX-ACCESS not-accessible
			STATUS current
			DESCRIPTION
				"Y1731 Uplink-redundancy information table."
			::= { sleY1731UplinkRedundancy 1 }

		
--   1.3.6.1.4.1.6296.101.4.12.15.1.1
-- 1.3.6.1.4.1.6296.101.4.12.15.1.1
		-- 1.3.6.1.4.1.6296.101.4.12.15.1.1
		sleY1731UREntry OBJECT-TYPE
			SYNTAX SleY1731UREntry
			MAX-ACCESS not-accessible
			STATUS current
			DESCRIPTION
				"key: sleY1731URMegIndex"
			INDEX { sleY1731URMegIndex }
			::= { sleY1731URTable 1 }

		
		SleY1731UREntry ::=
			SEQUENCE { 
				sleY1731URMegIndex
					INTEGER,
				sleY1731URMegName
					OCTET STRING,
				sleY1731URDedicatedVlan
					INTEGER,
				sleY1731UREnableStatus
					INTEGER,
				sleY1731URConnectivityCheckMeg
					OCTET STRING,
				sleY1731URPrimaryMepId
					INTEGER,
				sleY1731URSecondaryMepId
					INTEGER,
				sleY1731URControlVlan
					INTEGER,
				sleY1731URNodeConf
					INTEGER,
				sleY1731URNodeConfPortNum
					INTEGER,
				sleY1731URNodeConfPortStatus
					INTEGER,
				sleY1731URNonRevertive
					INTEGER,
				sleY1731URTrustMemberCount
					INTEGER,
				sleY1731URWaitToRestore
					INTEGER,
				sleY1731URForceSwitch
					INTEGER,
				sleY1731URSFCondition
					INTEGER,
				sleY1731URTrafficVlan
					OCTET STRING,
				sleY1731URState
					INTEGER,
				sleY1731URManualSwitch
					INTEGER
			 }

--   1.3.6.1.4.1.6296.101.4.12.15.1.1.1
-- 1.3.6.1.4.1.6296.101.4.12.15.1.1.1
		-- 1.3.6.1.4.1.6296.101.4.12.15.1.1.1
		sleY1731URMegIndex OBJECT-TYPE
			SYNTAX INTEGER (1..65535)
			MAX-ACCESS read-only
			STATUS current
			DESCRIPTION
				"The MEG index."
			::= { sleY1731UREntry 1 }

		
--   1.3.6.1.4.1.6296.101.4.12.15.1.1.2
-- 1.3.6.1.4.1.6296.101.4.12.15.1.1.2
		-- 1.3.6.1.4.1.6296.101.4.12.15.1.1.2
		sleY1731URMegName OBJECT-TYPE
			SYNTAX OCTET STRING
			MAX-ACCESS read-only
			STATUS current
			DESCRIPTION
				"The MEG name."
			::= { sleY1731UREntry 2 }

		
--   1.3.6.1.4.1.6296.101.4.12.15.1.1.3
-- 1.3.6.1.4.1.6296.101.4.12.15.1.1.3
		-- 1.3.6.1.4.1.6296.101.4.12.15.1.1.3
		sleY1731URDedicatedVlan OBJECT-TYPE
			SYNTAX INTEGER
				{
				disable(0),
				enable(1)
				}
			MAX-ACCESS read-only
			STATUS current
			DESCRIPTION
				"Indicates R-APS node to use dedicated-VLAN
				disable : all VLAN
				enable  : one VLAN"
			::= { sleY1731UREntry 3 }

		
--   1.3.6.1.4.1.6296.101.4.12.15.1.1.4
-- 1.3.6.1.4.1.6296.101.4.12.15.1.1.4
		-- 1.3.6.1.4.1.6296.101.4.12.15.1.1.4
		sleY1731UREnableStatus OBJECT-TYPE
			SYNTAX INTEGER
				{
				disable(0),
				enable(1)
				}
			MAX-ACCESS read-only
			STATUS current
			DESCRIPTION
				"Uplink-redundancy feature
				0 : disable 
				1 : enable"
			::= { sleY1731UREntry 4 }

		
--   1.3.6.1.4.1.6296.101.4.12.15.1.1.5
-- 1.3.6.1.4.1.6296.101.4.12.15.1.1.5
		-- 1.3.6.1.4.1.6296.101.4.12.15.1.1.5
		sleY1731URConnectivityCheckMeg OBJECT-TYPE
			SYNTAX OCTET STRING
			MAX-ACCESS read-only
			STATUS current
			DESCRIPTION
				"Indicates the connectivity check - MEG name."
			::= { sleY1731UREntry 5 }

		
--   1.3.6.1.4.1.6296.101.4.12.15.1.1.6
-- 1.3.6.1.4.1.6296.101.4.12.15.1.1.6
		-- 1.3.6.1.4.1.6296.101.4.12.15.1.1.6
		sleY1731URPrimaryMepId OBJECT-TYPE
			SYNTAX INTEGER (1..8191)
			MAX-ACCESS read-only
			STATUS current
			DESCRIPTION
				"Indicates the connectivity check - primary MEP's ID"
			::= { sleY1731UREntry 6 }

		
--   1.3.6.1.4.1.6296.101.4.12.15.1.1.7
-- 1.3.6.1.4.1.6296.101.4.12.15.1.1.7
		-- 1.3.6.1.4.1.6296.101.4.12.15.1.1.7
		sleY1731URSecondaryMepId OBJECT-TYPE
			SYNTAX INTEGER (1..8191)
			MAX-ACCESS read-only
			STATUS current
			DESCRIPTION
				"Indicates the connectivity check - secondary MEP's ID"
			::= { sleY1731UREntry 7 }

		
--   1.3.6.1.4.1.6296.101.4.12.15.1.1.8
-- 1.3.6.1.4.1.6296.101.4.12.15.1.1.8
		-- 1.3.6.1.4.1.6296.101.4.12.15.1.1.8
		sleY1731URControlVlan OBJECT-TYPE
			SYNTAX INTEGER (1..4094)
			MAX-ACCESS read-only
			STATUS current
			DESCRIPTION
				"Indicates the control VLAN"
			::= { sleY1731UREntry 8 }

		
--   1.3.6.1.4.1.6296.101.4.12.15.1.1.9
-- 1.3.6.1.4.1.6296.101.4.12.15.1.1.9
		-- 1.3.6.1.4.1.6296.101.4.12.15.1.1.9
		sleY1731URNodeConf OBJECT-TYPE
			SYNTAX INTEGER
				{
				none(0),
				master(1),
				slave(2)
				}
			MAX-ACCESS read-only
			STATUS current
			DESCRIPTION
				"Indicates the (master/slave) node of the redundancy"
			::= { sleY1731UREntry 9 }

		
--   1.3.6.1.4.1.6296.101.4.12.15.1.1.10
-- 1.3.6.1.4.1.6296.101.4.12.15.1.1.10
		-- 1.3.6.1.4.1.6296.101.4.12.15.1.1.10
		sleY1731URNodeConfPortNum OBJECT-TYPE
			SYNTAX INTEGER (1..65535)
			MAX-ACCESS read-write
			STATUS current
			DESCRIPTION
				"The port number"
			::= { sleY1731UREntry 10 }

		
--   1.3.6.1.4.1.6296.101.4.12.15.1.1.11
-- 1.3.6.1.4.1.6296.101.4.12.15.1.1.11
		-- 1.3.6.1.4.1.6296.101.4.12.15.1.1.11
		sleY1731URNodeConfPortStatus OBJECT-TYPE
			SYNTAX INTEGER
				{
				none(0),
				disabled(1),
				forwarding(2),
				blocking(3)
				}
			MAX-ACCESS read-only
			STATUS current
			DESCRIPTION
				"The uplink port status
				0: none
				1: disabled
				2: forwarding
				3: blocking"
			::= { sleY1731UREntry 11 }

		
--   1.3.6.1.4.1.6296.101.4.12.15.1.1.12
-- 1.3.6.1.4.1.6296.101.4.12.15.1.1.12
		-- 1.3.6.1.4.1.6296.101.4.12.15.1.1.12
		sleY1731URNonRevertive OBJECT-TYPE
			SYNTAX INTEGER
				{
				false(0),
				ture(1)
				}
			MAX-ACCESS read-only
			STATUS current
			DESCRIPTION
				"The non-revertive mode"
			::= { sleY1731UREntry 12 }

		
--   1.3.6.1.4.1.6296.101.4.12.15.1.1.13
-- 1.3.6.1.4.1.6296.101.4.12.15.1.1.13
		-- 1.3.6.1.4.1.6296.101.4.12.15.1.1.13
		sleY1731URTrustMemberCount OBJECT-TYPE
			SYNTAX INTEGER (1..65535)
			MAX-ACCESS read-only
			STATUS current
			DESCRIPTION
				"Indicates the trust LOC count at link-aggregation port"
			::= { sleY1731UREntry 13 }

		
--   1.3.6.1.4.1.6296.101.4.12.15.1.1.14
-- 1.3.6.1.4.1.6296.101.4.12.15.1.1.14
		-- 1.3.6.1.4.1.6296.101.4.12.15.1.1.14
		sleY1731URWaitToRestore OBJECT-TYPE
			SYNTAX INTEGER (5..720)
			MAX-ACCESS read-only
			STATUS current
			DESCRIPTION
				"Indicates the wait-to-restore time ( 5 - 720 )"
			::= { sleY1731UREntry 14 }

		
--   1.3.6.1.4.1.6296.101.4.12.15.1.1.15
-- 1.3.6.1.4.1.6296.101.4.12.15.1.1.15
		-- 1.3.6.1.4.1.6296.101.4.12.15.1.1.15
		sleY1731URForceSwitch OBJECT-TYPE
			SYNTAX INTEGER
				{
				false(0),
				true(1)
				}
			MAX-ACCESS read-only
			STATUS current
			DESCRIPTION
				"The forced-switch of uplink port
				"
			::= { sleY1731UREntry 15 }

		
--     1.3.6.1.4.1.6296.101.4.12.15.1.1.15
-- 1.3.6.1.4.1.6296.101.4.12.15.1.1.16
-- 1.3.6.1.4.1.6296.101.4.12.15.1.1.16
-- 1.3.6.1.4.1.6296.101.4.12.15.1.1.16
		-- 1.3.6.1.4.1.6296.101.4.12.15.1.1.16
		sleY1731URSFCondition OBJECT-TYPE
			SYNTAX INTEGER
				{
				loc(0),
				locRdi(1)
				}
			MAX-ACCESS read-only
			STATUS current
			DESCRIPTION
				"The sf condition
				"
			::= { sleY1731UREntry 16 }

		
--     1.3.6.1.4.1.6296.101.4.12.15.1.1.15
-- 1.3.6.1.4.1.6296.101.4.12.15.1.1.16
-- 1.3.6.1.4.1.6296.101.4.12.15.1.1.16
-- 1.3.6.1.4.1.6296.101.4.12.15.1.1.17
		-- 1.3.6.1.4.1.6296.101.4.12.15.1.1.17
		sleY1731URTrafficVlan OBJECT-TYPE
			SYNTAX OCTET STRING
			MAX-ACCESS read-only
			STATUS current
			DESCRIPTION
				"The Traffic vlan.
				"
			::= { sleY1731UREntry 17 }

		
--     1.3.6.1.4.1.6296.101.4.12.15.1.1.15
-- 1.3.6.1.4.1.6296.101.4.12.15.1.1.16
-- 1.3.6.1.4.1.6296.101.4.12.15.1.1.16
-- 1.3.6.1.4.1.6296.101.4.12.15.1.1.18
		-- 1.3.6.1.4.1.6296.101.4.12.15.1.1.18
		sleY1731URState OBJECT-TYPE
			SYNTAX INTEGER
				{
				unReady(0),
				ready(1),
				active(2),
				standby(3),
				preActive(4)
				}
			MAX-ACCESS read-only
			STATUS current
			DESCRIPTION
				"The uplink redundancy node state
				none(0)
				unReady(1)
				ready(2)
				active(3)
				standby(4)
				preActive(5)"
			::= { sleY1731UREntry 18 }

		
--   1.3.6.1.4.1.6296.101.4.12.15.1.1.15
-- 1.3.6.1.4.1.6296.101.4.12.15.1.1.19
		-- 1.3.6.1.4.1.6296.101.4.12.15.1.1.19
		sleY1731URManualSwitch OBJECT-TYPE
			SYNTAX INTEGER
				{
				false(0),
				true(1)
				}
			MAX-ACCESS read-only
			STATUS current
			DESCRIPTION
				"The manual-switch of uplink port
				"
			::= { sleY1731UREntry 19 }

		
--   1.3.6.1.4.1.6296.101.4.12.15.2
-- 1.3.6.1.4.1.6296.101.4.12.15.2
		-- 1.3.6.1.4.1.6296.101.4.12.15.2
		sleY1731URControl OBJECT IDENTIFIER ::= { sleY1731UplinkRedundancy 2 }

		
--   1.3.6.1.4.1.6296.101.4.12.15.2.1
-- 1.3.6.1.4.1.6296.101.4.12.15.2.1
		-- 1.3.6.1.4.1.6296.101.4.12.15.2.1
		sleY1731URControlRequest OBJECT-TYPE
			SYNTAX INTEGER
				{
				setDedicatedVlan(1),
				setEnableStatus(2),
				setCCPrimaryMepId(3),
				clearCCPrimaryMepId(4),
				setCCSecondaryMepId(5),
				clearCCSecondaryMepId(6),
				setControlVlan(7),
				clearControlVlan(8),
				setNodeConfiguration(9),
				clearNodeConfiguration(10),
				setNonRevertive(11),
				setTrustMemberCount(12),
				clearTrustMemberCount(13),
				setWaitToRestore(14),
				clearWaitToRestore(15),
				setForceSwitch(16),
				setManualSwitch(17),
				setSFCondition(18),
				setTrafficVlan(19),
				clearTrafficVlan(20)
				}
			MAX-ACCESS read-write
			STATUS current
			DESCRIPTION
				"This attribute identifies the control commands.
				updateAlarmList:
				   the NE updates entries of alarms in the sleAlarmListTable
				   after having changed alarm severities of alarms 
				   (due to change profile pointers in
				   managed entities or after modification of alarm severities 
				   in profiles). This command should be applied once after having 
				   finisled modifications of severties.
				modifyAlarmSeverity: 
				   modifies the severity of an alarm in specific profile.
				createAlarmSeverityProfile: 
				   creates a new profile with default severities.
				   The severities then have to be modified with command changeAlarmSeverity.
				deleteAlarmSeverityProfile: 
				   deletes a profile. Profile 1 is not allowed to be deleted.
				 
				Notifications : none "
			::= { sleY1731URControl 1 }

		
--   1.3.6.1.4.1.6296.101.4.12.15.2.2
-- 1.3.6.1.4.1.6296.101.4.12.15.2.2
		-- 1.3.6.1.4.1.6296.101.4.12.15.2.2
		sleY1731URControlStatus OBJECT-TYPE
			SYNTAX SleControlStatusType
			MAX-ACCESS read-write
			STATUS current
			DESCRIPTION
				"The status of a control request. "
			::= { sleY1731URControl 2 }

		
--   1.3.6.1.4.1.6296.101.4.12.15.2.3
-- 1.3.6.1.4.1.6296.101.4.12.15.2.3
		-- 1.3.6.1.4.1.6296.101.4.12.15.2.3
		sleY1731URControlTimer OBJECT-TYPE
			SYNTAX Gauge32
			MAX-ACCESS read-write
			STATUS current
			DESCRIPTION
				" The maximum wait time for the manager for command ending.
				For long running commands.
				The manager reads this value from the DSLAM. "
			::= { sleY1731URControl 3 }

		
--   1.3.6.1.4.1.6296.101.4.12.15.2.4
-- 1.3.6.1.4.1.6296.101.4.12.15.2.4
		-- 1.3.6.1.4.1.6296.101.4.12.15.2.4
		sleY1731URControlTimeStamp OBJECT-TYPE
			SYNTAX TimeTicks
			MAX-ACCESS read-write
			STATUS current
			DESCRIPTION
				" The time stamp of the last command (end of command). "
			::= { sleY1731URControl 4 }

		
--   1.3.6.1.4.1.6296.101.4.12.15.2.5
-- 1.3.6.1.4.1.6296.101.4.12.15.2.5
		-- 1.3.6.1.4.1.6296.101.4.12.15.2.5
		sleY1731URControlReqResult OBJECT-TYPE
			SYNTAX SleControlRequestResultType
			MAX-ACCESS read-write
			STATUS current
			DESCRIPTION
				"The result of the last user command. "
			::= { sleY1731URControl 5 }

		
--   1.3.6.1.4.1.6296.101.4.12.15.2.6
-- 1.3.6.1.4.1.6296.101.4.12.15.2.6
		-- 1.3.6.1.4.1.6296.101.4.12.15.2.6
		sleY1731URControlMegIndex OBJECT-TYPE
			SYNTAX INTEGER (1..65535)
			MAX-ACCESS read-write
			STATUS current
			DESCRIPTION
				"The MEG index."
			::= { sleY1731URControl 6 }

		
--   1.3.6.1.4.1.6296.101.4.12.15.2.7
-- 1.3.6.1.4.1.6296.101.4.12.15.2.7
		-- 1.3.6.1.4.1.6296.101.4.12.15.2.7
		sleY1731URControlMegName OBJECT-TYPE
			SYNTAX OCTET STRING
			MAX-ACCESS read-write
			STATUS current
			DESCRIPTION
				"The MEG name."
			::= { sleY1731URControl 7 }

		
--   1.3.6.1.4.1.6296.101.4.12.15.2.8
-- 1.3.6.1.4.1.6296.101.4.12.15.2.8
		-- 1.3.6.1.4.1.6296.101.4.12.15.2.8
		sleY1731URControlDedicatedVlan OBJECT-TYPE
			SYNTAX INTEGER
				{
				disable(0),
				enable(1)
				}
			MAX-ACCESS read-write
			STATUS current
			DESCRIPTION
				"Indicates R-APS node to use dedicated-VLAN
				disable : all VLAN
				enable  : one VLAN"
			::= { sleY1731URControl 8 }

		
--   1.3.6.1.4.1.6296.101.4.12.15.2.9
-- 1.3.6.1.4.1.6296.101.4.12.15.2.9
		-- 1.3.6.1.4.1.6296.101.4.12.15.2.9
		sleY1731URControlEnableStatus OBJECT-TYPE
			SYNTAX INTEGER
				{
				disable(0),
				enable(1)
				}
			MAX-ACCESS read-write
			STATUS current
			DESCRIPTION
				"Uplink-redundancy feature
				0 : disable 
				1 : enable"
			::= { sleY1731URControl 9 }

		
--   1.3.6.1.4.1.6296.101.4.12.15.2.10
-- 1.3.6.1.4.1.6296.101.4.12.15.2.10
		-- 1.3.6.1.4.1.6296.101.4.12.15.2.10
		sleY1731URControlConnectivityCheckMeg OBJECT-TYPE
			SYNTAX OCTET STRING
			MAX-ACCESS read-write
			STATUS current
			DESCRIPTION
				"Indicates the connectivity check - MEG name."
			::= { sleY1731URControl 10 }

		
--   1.3.6.1.4.1.6296.101.4.12.15.2.11
-- 1.3.6.1.4.1.6296.101.4.12.15.2.11
		-- 1.3.6.1.4.1.6296.101.4.12.15.2.11
		sleY1731URControlPrimaryMepId OBJECT-TYPE
			SYNTAX INTEGER (1..8191)
			MAX-ACCESS read-write
			STATUS current
			DESCRIPTION
				"Indicates the connectivity check - primary MEP's ID"
			::= { sleY1731URControl 11 }

		
--   1.3.6.1.4.1.6296.101.4.12.15.2.12
-- 1.3.6.1.4.1.6296.101.4.12.15.2.12
		-- 1.3.6.1.4.1.6296.101.4.12.15.2.12
		sleY1731URControlSecondaryMepId OBJECT-TYPE
			SYNTAX INTEGER (1..8191)
			MAX-ACCESS read-write
			STATUS current
			DESCRIPTION
				"Indicates the connectivity check - secondary MEP's ID"
			::= { sleY1731URControl 12 }

		
--   1.3.6.1.4.1.6296.101.4.12.15.2.13
-- 1.3.6.1.4.1.6296.101.4.12.15.2.13
		-- 1.3.6.1.4.1.6296.101.4.12.15.2.13
		sleY1731URControlControlVlan OBJECT-TYPE
			SYNTAX INTEGER (1..4094)
			MAX-ACCESS read-write
			STATUS current
			DESCRIPTION
				"Indicates the control VLAN"
			::= { sleY1731URControl 13 }

		
--   1.3.6.1.4.1.6296.101.4.12.15.2.14
-- 1.3.6.1.4.1.6296.101.4.12.15.2.14
		-- 1.3.6.1.4.1.6296.101.4.12.15.2.14
		sleY1731URControlNodeConf OBJECT-TYPE
			SYNTAX INTEGER
				{
				none(0),
				master(1),
				slave(2)
				}
			MAX-ACCESS read-write
			STATUS current
			DESCRIPTION
				"Indicates the (master/slave) node of the redundancy"
			::= { sleY1731URControl 14 }

		
--   1.3.6.1.4.1.6296.101.4.12.15.2.15
-- 1.3.6.1.4.1.6296.101.4.12.15.2.15
		-- 1.3.6.1.4.1.6296.101.4.12.15.2.15
		sleY1731URControlNodeConfPortNum OBJECT-TYPE
			SYNTAX INTEGER (1..65535)
			MAX-ACCESS read-write
			STATUS current
			DESCRIPTION
				"The port number"
			::= { sleY1731URControl 15 }

		
--   1.3.6.1.4.1.6296.101.4.12.15.2.16
-- 1.3.6.1.4.1.6296.101.4.12.15.2.16
		-- 1.3.6.1.4.1.6296.101.4.12.15.2.16
		sleY1731URControlNonRevertive OBJECT-TYPE
			SYNTAX INTEGER
				{
				false(0),
				ture(1)
				}
			MAX-ACCESS read-write
			STATUS current
			DESCRIPTION
				"The non-revertive mode"
			::= { sleY1731URControl 16 }

		
--   1.3.6.1.4.1.6296.101.4.12.15.2.17
-- 1.3.6.1.4.1.6296.101.4.12.15.2.17
		-- 1.3.6.1.4.1.6296.101.4.12.15.2.17
		sleY1731URControlTrustMemberCount OBJECT-TYPE
			SYNTAX INTEGER (1..65535)
			MAX-ACCESS read-write
			STATUS current
			DESCRIPTION
				"Indicates the trust LOC count at link-aggregation port"
			::= { sleY1731URControl 17 }

		
--   1.3.6.1.4.1.6296.101.4.12.15.2.18
-- 1.3.6.1.4.1.6296.101.4.12.15.2.18
		-- 1.3.6.1.4.1.6296.101.4.12.15.2.18
		sleY1731URControlWaitToRestore OBJECT-TYPE
			SYNTAX INTEGER (5..720)
			MAX-ACCESS read-write
			STATUS current
			DESCRIPTION
				"Indicates the wait-to-restore time ( 5 - 720 )"
			::= { sleY1731URControl 18 }

		
--   1.3.6.1.4.1.6296.101.4.12.15.2.19
-- 1.3.6.1.4.1.6296.101.4.12.15.2.19
		-- 1.3.6.1.4.1.6296.101.4.12.15.2.19
		sleY1731URControlForceSwitch OBJECT-TYPE
			SYNTAX INTEGER
				{
				false(0),
				true(1)
				}
			MAX-ACCESS read-write
			STATUS current
			DESCRIPTION
				"The forced-switch of uplink port"
			::= { sleY1731URControl 19 }

		
--     1.3.6.1.4.1.6296.101.4.12.15.2.19
-- 1.3.6.1.4.1.6296.101.4.12.15.2.20
-- 1.3.6.1.4.1.6296.101.4.12.15.2.20
-- 1.3.6.1.4.1.6296.101.4.12.15.2.20
		-- 1.3.6.1.4.1.6296.101.4.12.15.2.20
		sleY1731URControlSFCondition OBJECT-TYPE
			SYNTAX INTEGER
				{
				loc(0),
				locRdi(1)
				}
			MAX-ACCESS read-write
			STATUS current
			DESCRIPTION
				"The sf condition"
			::= { sleY1731URControl 20 }

		
--  1.3.6.1.4.1.6296.101.4.12.15.2.21
		-- 1.3.6.1.4.1.6296.101.4.12.15.2.21
		sleY1731URControlTrafficVlan OBJECT-TYPE
			SYNTAX OCTET STRING
			MAX-ACCESS read-write
			STATUS current
			DESCRIPTION
				"The Traffic vlan"
			::= { sleY1731URControl 21 }

		
--   1.3.6.1.4.1.6296.101.4.12.15.2.19
-- 1.3.6.1.4.1.6296.101.4.12.15.2.22
		-- 1.3.6.1.4.1.6296.101.4.12.15.2.22
		sleY1731URControlManualSwitch OBJECT-TYPE
			SYNTAX INTEGER
				{
				false(0),
				true(1)
				}
			MAX-ACCESS read-write
			STATUS current
			DESCRIPTION
				"The manual-switch of uplink port"
			::= { sleY1731URControl 22 }

		
--   1.3.6.1.4.1.6296.101.4.12.15.3
-- 1.3.6.1.4.1.6296.101.4.12.15.3
		-- 1.3.6.1.4.1.6296.101.4.12.15.3
		sleY1731URNotification OBJECT IDENTIFIER ::= { sleY1731UplinkRedundancy 3 }

		
--   1.3.6.1.4.1.6296.101.4.12.15.3.1
-- 1.3.6.1.4.1.6296.101.4.12.15.3.1
		-- 1.3.6.1.4.1.6296.101.4.12.15.3.1
		sleY1731URDedicatedVlanChanged NOTIFICATION-TYPE
			OBJECTS { sleY1731URControlRequest, sleY1731URControlTimeStamp, sleY1731URControlReqResult, sleY1731URControlDedicatedVlan }
			STATUS current
			DESCRIPTION 
				"setY1731URDedicatedVlan"
			::= { sleY1731URNotification 1 }

		
--   1.3.6.1.4.1.6296.101.4.12.15.3.2
-- 1.3.6.1.4.1.6296.101.4.12.15.3.2
		-- 1.3.6.1.4.1.6296.101.4.12.15.3.2
		sleY1731UREnableStatusChanged NOTIFICATION-TYPE
			OBJECTS { sleY1731URControlRequest, sleY1731URControlTimeStamp, sleY1731URControlReqResult, sleY1731URControlMegIndex, sleY1731URControlMegName, 
				sleY1731URControlEnableStatus }
			STATUS current
			DESCRIPTION 
				"setY1731UREnableStatus"
			::= { sleY1731URNotification 2 }

		
--   1.3.6.1.4.1.6296.101.4.12.15.3.3
-- 1.3.6.1.4.1.6296.101.4.12.15.3.3
		-- 1.3.6.1.4.1.6296.101.4.12.15.3.3
		sleY1731URCCPrimaryMepIdChanged NOTIFICATION-TYPE
			OBJECTS { sleY1731URControlRequest, sleY1731URControlTimeStamp, sleY1731URControlReqResult, sleY1731URControlMegIndex, sleY1731URControlMegName, 
				sleY1731URControlConnectivityCheckMeg, sleY1731URControlPrimaryMepId }
			STATUS current
			DESCRIPTION 
				"setY1731URCCPrimaryMepId"
			::= { sleY1731URNotification 3 }

		
--   1.3.6.1.4.1.6296.101.4.12.15.3.4
-- 1.3.6.1.4.1.6296.101.4.12.15.3.4
		-- 1.3.6.1.4.1.6296.101.4.12.15.3.4
		sleY1731URCCPrimaryMepIdCleared NOTIFICATION-TYPE
			OBJECTS { sleY1731URControlRequest, sleY1731URControlTimeStamp, sleY1731URControlReqResult, sleY1731URControlMegIndex, sleY1731URControlMegName
				 }
			STATUS current
			DESCRIPTION 
				"delY1731URCCPrimaryMepId"
			::= { sleY1731URNotification 4 }

		
--   1.3.6.1.4.1.6296.101.4.12.15.3.5
-- 1.3.6.1.4.1.6296.101.4.12.15.3.5
		-- 1.3.6.1.4.1.6296.101.4.12.15.3.5
		sleY1731URCCSecondaryMepIdChanged NOTIFICATION-TYPE
			OBJECTS { sleY1731URControlRequest, sleY1731URControlTimeStamp, sleY1731URControlReqResult, sleY1731URControlMegIndex, sleY1731URControlMegName, 
				sleY1731URControlConnectivityCheckMeg, sleY1731URControlSecondaryMepId }
			STATUS current
			DESCRIPTION 
				"setY1731URCCSecondaryMepId"
			::= { sleY1731URNotification 5 }

		
--   1.3.6.1.4.1.6296.101.4.12.15.3.6
-- 1.3.6.1.4.1.6296.101.4.12.15.3.6
		-- 1.3.6.1.4.1.6296.101.4.12.15.3.6
		sleY1731URCCSecondaryMepIdCleared NOTIFICATION-TYPE
			OBJECTS { sleY1731URControlRequest, sleY1731URControlTimeStamp, sleY1731URControlReqResult, sleY1731URControlMegIndex, sleY1731URControlMegName
				 }
			STATUS current
			DESCRIPTION 
				"delY1731URCCSecondaryMepId"
			::= { sleY1731URNotification 6 }

		
--   1.3.6.1.4.1.6296.101.4.12.15.3.7
-- 1.3.6.1.4.1.6296.101.4.12.15.3.7
		-- 1.3.6.1.4.1.6296.101.4.12.15.3.7
		sleY1731URControlVlanChanged NOTIFICATION-TYPE
			OBJECTS { sleY1731URControlRequest, sleY1731URControlTimeStamp, sleY1731URControlReqResult, sleY1731URControlMegIndex, sleY1731URControlMegName, 
				sleY1731URControlControlVlan }
			STATUS current
			DESCRIPTION 
				"setY1731URControlVlan"
			::= { sleY1731URNotification 7 }

		
--   1.3.6.1.4.1.6296.101.4.12.15.3.8
-- 1.3.6.1.4.1.6296.101.4.12.15.3.8
		-- 1.3.6.1.4.1.6296.101.4.12.15.3.8
		sleY1731URControlVlanCleared NOTIFICATION-TYPE
			OBJECTS { sleY1731URControlRequest, sleY1731URControlTimeStamp, sleY1731URControlReqResult, sleY1731URControlMegIndex, sleY1731URControlMegName
				 }
			STATUS current
			DESCRIPTION 
				"delY1731URControlVlan"
			::= { sleY1731URNotification 8 }

		
--   1.3.6.1.4.1.6296.101.4.12.15.3.9
-- 1.3.6.1.4.1.6296.101.4.12.15.3.9
		-- 1.3.6.1.4.1.6296.101.4.12.15.3.9
		sleY1731URNodeConfChanged NOTIFICATION-TYPE
			OBJECTS { sleY1731URControlRequest, sleY1731URControlTimeStamp, sleY1731URControlReqResult, sleY1731URControlMegIndex, sleY1731URControlMegName, 
				sleY1731URControlNodeConf, sleY1731URControlNodeConfPortNum }
			STATUS current
			DESCRIPTION 
				"setY1731URNodeConf"
			::= { sleY1731URNotification 9 }

		
--   1.3.6.1.4.1.6296.101.4.12.15.3.10
-- 1.3.6.1.4.1.6296.101.4.12.15.3.10
		-- 1.3.6.1.4.1.6296.101.4.12.15.3.10
		sleY1731URNodeConfCleared NOTIFICATION-TYPE
			OBJECTS { sleY1731URControlRequest, sleY1731URControlTimeStamp, sleY1731URControlReqResult, sleY1731URControlMegIndex, sleY1731URControlMegName, 
				sleY1731URControlNodeConf }
			STATUS current
			DESCRIPTION 
				"delY1731URNodeConf"
			::= { sleY1731URNotification 10 }

		
--   1.3.6.1.4.1.6296.101.4.12.15.3.11
-- 1.3.6.1.4.1.6296.101.4.12.15.3.11
		-- 1.3.6.1.4.1.6296.101.4.12.15.3.11
		sleY1731URNonRevertiveChanged NOTIFICATION-TYPE
			OBJECTS { sleY1731URControlRequest, sleY1731URControlTimeStamp, sleY1731URControlReqResult, sleY1731URControlMegIndex, sleY1731URControlMegName, 
				sleY1731URControlNonRevertive }
			STATUS current
			DESCRIPTION 
				"setY1731URNonRevertive"
			::= { sleY1731URNotification 11 }

		
--   1.3.6.1.4.1.6296.101.4.12.15.3.12
-- 1.3.6.1.4.1.6296.101.4.12.15.3.12
		-- 1.3.6.1.4.1.6296.101.4.12.15.3.12
		sleY1731URTrustMemberCountChanged NOTIFICATION-TYPE
			OBJECTS { sleY1731URControlRequest, sleY1731URControlTimeStamp, sleY1731URControlReqResult, sleY1731URControlMegIndex, sleY1731URControlMegName, 
				sleY1731URControlTrustMemberCount }
			STATUS current
			DESCRIPTION 
				"setY1731URTrustMemberCount"
			::= { sleY1731URNotification 12 }

		
--   1.3.6.1.4.1.6296.101.4.12.15.3.13
-- 1.3.6.1.4.1.6296.101.4.12.15.3.13
		-- 1.3.6.1.4.1.6296.101.4.12.15.3.13
		sleY1731URTrustMemberCountCleared NOTIFICATION-TYPE
			OBJECTS { sleY1731URControlRequest, sleY1731URControlTimeStamp, sleY1731URControlReqResult, sleY1731URControlMegIndex, sleY1731URControlMegName
				 }
			STATUS current
			DESCRIPTION 
				"delY1731URTrustMemberCount"
			::= { sleY1731URNotification 13 }

		
--   1.3.6.1.4.1.6296.101.4.12.15.3.14
-- 1.3.6.1.4.1.6296.101.4.12.15.3.14
		-- 1.3.6.1.4.1.6296.101.4.12.15.3.14
		sleY1731URWaitToRestoreChanged NOTIFICATION-TYPE
			OBJECTS { sleY1731URControlRequest, sleY1731URControlTimeStamp, sleY1731URControlReqResult, sleY1731URControlMegIndex, sleY1731URControlMegName, 
				sleY1731URControlWaitToRestore }
			STATUS current
			DESCRIPTION 
				"setY1731URWaitToRestore"
			::= { sleY1731URNotification 14 }

		
--   1.3.6.1.4.1.6296.101.4.12.15.3.15
-- 1.3.6.1.4.1.6296.101.4.12.15.3.15
		-- 1.3.6.1.4.1.6296.101.4.12.15.3.15
		sleY1731URWaitToRestoreCleared NOTIFICATION-TYPE
			OBJECTS { sleY1731URControlRequest, sleY1731URControlTimeStamp, sleY1731URControlReqResult, sleY1731URControlMegIndex, sleY1731URControlMegName
				 }
			STATUS current
			DESCRIPTION 
				"delY1731URWaitToRestore"
			::= { sleY1731URNotification 15 }

		
--   1.3.6.1.4.1.6296.101.4.12.15.3.16
-- 1.3.6.1.4.1.6296.101.4.12.15.3.16
		-- 1.3.6.1.4.1.6296.101.4.12.15.3.16
		sleY1731URForceSwitchChanged NOTIFICATION-TYPE
			OBJECTS { sleY1731URControlRequest, sleY1731URControlTimeStamp, sleY1731URControlReqResult, sleY1731URControlMegIndex, sleY1731URControlMegName, 
				sleY1731URControlForceSwitch }
			STATUS current
			DESCRIPTION 
				"setForceSwitch"
			::= { sleY1731URNotification 16 }

		
--   1.3.6.1.4.1.6296.101.4.12.15.3.17
-- 1.3.6.1.4.1.6296.101.4.12.15.3.17
		-- 1.3.6.1.4.1.6296.101.4.12.15.3.17
		sleY1731URManualSwitchChanged NOTIFICATION-TYPE
			OBJECTS { sleY1731URControlRequest, sleY1731URControlTimeStamp, sleY1731URControlReqResult, sleY1731URControlMegIndex, sleY1731URControlMegName, 
				sleY1731URControlManualSwitch }
			STATUS current
			DESCRIPTION 
				"setManualSwitch"
			::= { sleY1731URNotification 17 }

		
--     1.3.6.1.4.1.6296.101.4.12.15.3.17
-- 1.3.6.1.4.1.6296.101.4.12.15.3.18
-- 1.3.6.1.4.1.6296.101.4.12.15.3.18
-- 1.3.6.1.4.1.6296.101.4.12.15.3.18
		-- 1.3.6.1.4.1.6296.101.4.12.15.3.18
		sleY1731URSFConditionChanged NOTIFICATION-TYPE
			OBJECTS { sleY1731URControlRequest, sleY1731URControlTimeStamp, sleY1731URControlReqResult, sleY1731URControlMegIndex, sleY1731URControlMegName
				 }
			STATUS current
			DESCRIPTION 
				"setSFCondition"
			::= { sleY1731URNotification 18 }

		
--     1.3.6.1.4.1.6296.101.4.12.15.3.17
-- 1.3.6.1.4.1.6296.101.4.12.15.3.18
-- 1.3.6.1.4.1.6296.101.4.12.15.3.18
-- 1.3.6.1.4.1.6296.101.4.12.15.3.19
		-- 1.3.6.1.4.1.6296.101.4.12.15.3.19
		sleY1731URTrafficVlanChanged NOTIFICATION-TYPE
			OBJECTS { sleY1731URControlRequest, sleY1731URControlTimeStamp, sleY1731URControlReqResult, sleY1731URControlMegIndex, sleY1731URControlMegName, 
				sleY1731URControlTrafficVlan }
			STATUS current
			DESCRIPTION 
				"setTrafficVlan."
			::= { sleY1731URNotification 19 }

		
--     1.3.6.1.4.1.6296.101.4.12.15.3.17
-- 1.3.6.1.4.1.6296.101.4.12.15.3.18
-- 1.3.6.1.4.1.6296.101.4.12.15.3.18
-- 1.3.6.1.4.1.6296.101.4.12.15.3.20
		-- 1.3.6.1.4.1.6296.101.4.12.15.3.20
		sleY1731URTrafficVlanCleared NOTIFICATION-TYPE
			OBJECTS { sleY1731URControlRequest, sleY1731URControlTimeStamp, sleY1731URControlReqResult, sleY1731URControlMegIndex }
			STATUS current
			DESCRIPTION 
				"clearTrafficVlan."
			::= { sleY1731URNotification 20 }

		
--      1.3.6.1.4.1.6296.101.4.12.6
-- 1.3.6.1.4.1.6296.101.4.12.6
-- 1.3.6.1.4.1.6296.101.4.12.16
-- 1.3.6.1.4.1.6296.101.4.12.16
-- 1.3.6.1.4.1.6296.101.4.12.16
		-- 1.3.6.1.4.1.6296.101.4.12.16
		sleY1731LocRefMep OBJECT IDENTIFIER ::= { sleY1731Oam 16 }

		
--      1.3.6.1.4.1.6296.101.4.12.6.1
-- 1.3.6.1.4.1.6296.101.4.12.6.1
-- 1.3.6.1.4.1.6296.101.4.12.16.1
-- 1.3.6.1.4.1.6296.101.4.12.16.1
-- 1.3.6.1.4.1.6296.101.4.12.16.1
		-- 1.3.6.1.4.1.6296.101.4.12.16.1
		sleY1731LocRefMepTable OBJECT-TYPE
			SYNTAX SEQUENCE OF SleY1731LocRefMepEntry
			MAX-ACCESS not-accessible
			STATUS current
			DESCRIPTION
				"Description."
			::= { sleY1731LocRefMep 1 }

		
--      1.3.6.1.4.1.6296.101.4.12.6.1.1
-- 1.3.6.1.4.1.6296.101.4.12.6.1.1
-- 1.3.6.1.4.1.6296.101.4.12.16.1.1
-- 1.3.6.1.4.1.6296.101.4.12.16.1.1
-- 1.3.6.1.4.1.6296.101.4.12.16.1.1
		-- 1.3.6.1.4.1.6296.101.4.12.16.1.1
		sleY1731LocRefMepEntry OBJECT-TYPE
			SYNTAX SleY1731LocRefMepEntry
			MAX-ACCESS not-accessible
			STATUS current
			DESCRIPTION
				"Description."
			INDEX { sleY1731MegIndex, sleY1731MepIdentifier, sleY1731CcMacAddress }
			::= { sleY1731LocRefMepTable 1 }

		
		SleY1731LocRefMepEntry ::=
			SEQUENCE { 
				sleY1731LRMepIndex
					Integer32,
				sleY1731LRMepDMegIndex
					Integer32,
				sleY1731LRMepDMepIdentifier
					Integer32,
				sleY1731LRMepDRmepIdentifier
					Integer32
			 }

--      1.3.6.1.4.1.6296.101.4.12.6.1.1.1
-- 1.3.6.1.4.1.6296.101.4.12.6.1.1.1
-- 1.3.6.1.4.1.6296.101.4.12.16.1.1.1
-- 1.3.6.1.4.1.6296.101.4.12.16.1.1.1
-- 1.3.6.1.4.1.6296.101.4.12.16.1.1.1
		-- 1.3.6.1.4.1.6296.101.4.12.16.1.1.1
		sleY1731LRMepIndex OBJECT-TYPE
			SYNTAX Integer32 (1..65535)
			MAX-ACCESS read-only
			STATUS current
			DESCRIPTION
				"Indicates the index of the LOC reference MEP."
			::= { sleY1731LocRefMepEntry 1 }

		
--      1.3.6.1.4.1.6296.101.4.12.6.1.1.1
-- 1.3.6.1.4.1.6296.101.4.12.6.1.1.1
-- 1.3.6.1.4.1.6296.101.4.12.16.1.1.2
-- 1.3.6.1.4.1.6296.101.4.12.16.1.1.2
-- 1.3.6.1.4.1.6296.101.4.12.16.1.1.2
		-- 1.3.6.1.4.1.6296.101.4.12.16.1.1.2
		sleY1731LRMepDMegIndex OBJECT-TYPE
			SYNTAX Integer32 (1..65535)
			MAX-ACCESS read-only
			STATUS current
			DESCRIPTION
				"Indicates the MEG's Index of Down MEP"
			::= { sleY1731LocRefMepEntry 2 }

		
--      1.3.6.1.4.1.6296.101.4.12.6.1.1.1
-- 1.3.6.1.4.1.6296.101.4.12.6.1.1.1
-- 1.3.6.1.4.1.6296.101.4.12.16.1.1.3
-- 1.3.6.1.4.1.6296.101.4.12.16.1.1.3
-- 1.3.6.1.4.1.6296.101.4.12.16.1.1.3
		-- 1.3.6.1.4.1.6296.101.4.12.16.1.1.3
		sleY1731LRMepDMepIdentifier OBJECT-TYPE
			SYNTAX Integer32 (1..8191)
			MAX-ACCESS read-only
			STATUS current
			DESCRIPTION
				"Indicates the identifier of Down MEP."
			::= { sleY1731LocRefMepEntry 3 }

		
--      1.3.6.1.4.1.6296.101.4.12.6.1.1.1
-- 1.3.6.1.4.1.6296.101.4.12.6.1.1.1
-- 1.3.6.1.4.1.6296.101.4.12.16.1.1.4
-- 1.3.6.1.4.1.6296.101.4.12.16.1.1.4
-- 1.3.6.1.4.1.6296.101.4.12.16.1.1.4
		-- 1.3.6.1.4.1.6296.101.4.12.16.1.1.4
		sleY1731LRMepDRmepIdentifier OBJECT-TYPE
			SYNTAX Integer32 (1..8191)
			MAX-ACCESS read-only
			STATUS current
			DESCRIPTION
				"Indicates the identifier of Remote MEP."
			::= { sleY1731LocRefMepEntry 4 }

		
--      1.3.6.1.4.1.6296.101.4.12.6.2
-- 1.3.6.1.4.1.6296.101.4.12.6.2
-- 1.3.6.1.4.1.6296.101.4.12.16.2
-- 1.3.6.1.4.1.6296.101.4.12.16.2
-- 1.3.6.1.4.1.6296.101.4.12.16.2
		-- 1.3.6.1.4.1.6296.101.4.12.16.2
		sleY1731LocRefMepControl OBJECT IDENTIFIER ::= { sleY1731LocRefMep 2 }

		
--      1.3.6.1.4.1.6296.101.4.12.6.2.1
-- 1.3.6.1.4.1.6296.101.4.12.6.2.1
-- 1.3.6.1.4.1.6296.101.4.12.16.2.1
-- 1.3.6.1.4.1.6296.101.4.12.16.2.1
-- 1.3.6.1.4.1.6296.101.4.12.16.2.1
		-- 1.3.6.1.4.1.6296.101.4.12.16.2.1
		sleY1731LRMepControlRequest OBJECT-TYPE
			SYNTAX INTEGER
				{
				createY1731LocRefMep(1),
				deleteY1731LocRefMep(2)
				}
			MAX-ACCESS read-write
			STATUS current
			DESCRIPTION
				"Description."
			::= { sleY1731LocRefMepControl 1 }

		
--      1.3.6.1.4.1.6296.101.4.12.6.2.2
-- 1.3.6.1.4.1.6296.101.4.12.6.2.2
-- 1.3.6.1.4.1.6296.101.4.12.16.2.2
-- 1.3.6.1.4.1.6296.101.4.12.16.2.2
-- 1.3.6.1.4.1.6296.101.4.12.16.2.2
		-- 1.3.6.1.4.1.6296.101.4.12.16.2.2
		sleY1731LRMepControlStatus OBJECT-TYPE
			SYNTAX SleControlStatusType
			MAX-ACCESS read-only
			STATUS current
			DESCRIPTION
				"Description."
			::= { sleY1731LocRefMepControl 2 }

		
--      1.3.6.1.4.1.6296.101.4.12.6.2.3
-- 1.3.6.1.4.1.6296.101.4.12.6.2.3
-- 1.3.6.1.4.1.6296.101.4.12.16.2.3
-- 1.3.6.1.4.1.6296.101.4.12.16.2.3
-- 1.3.6.1.4.1.6296.101.4.12.16.2.3
		-- 1.3.6.1.4.1.6296.101.4.12.16.2.3
		sleY1731LRMepControlTimer OBJECT-TYPE
			SYNTAX Gauge32
			MAX-ACCESS read-write
			STATUS current
			DESCRIPTION
				"Description."
			::= { sleY1731LocRefMepControl 3 }

		
--      1.3.6.1.4.1.6296.101.4.12.6.2.4
-- 1.3.6.1.4.1.6296.101.4.12.6.2.4
-- 1.3.6.1.4.1.6296.101.4.12.16.2.4
-- 1.3.6.1.4.1.6296.101.4.12.16.2.4
-- 1.3.6.1.4.1.6296.101.4.12.16.2.4
		-- 1.3.6.1.4.1.6296.101.4.12.16.2.4
		sleY1731LRMepControlTimeStamp OBJECT-TYPE
			SYNTAX TimeTicks
			MAX-ACCESS read-only
			STATUS current
			DESCRIPTION
				"Description."
			::= { sleY1731LocRefMepControl 4 }

		
--      1.3.6.1.4.1.6296.101.4.12.6.2.5
-- 1.3.6.1.4.1.6296.101.4.12.6.2.5
-- 1.3.6.1.4.1.6296.101.4.12.16.2.5
-- 1.3.6.1.4.1.6296.101.4.12.16.2.5
-- 1.3.6.1.4.1.6296.101.4.12.16.2.5
		-- 1.3.6.1.4.1.6296.101.4.12.16.2.5
		sleY1731LRMepControlReqResult OBJECT-TYPE
			SYNTAX SleControlRequestResultType
			MAX-ACCESS read-only
			STATUS current
			DESCRIPTION
				"Result of the last command."
			::= { sleY1731LocRefMepControl 5 }

		
--      1.3.6.1.4.1.6296.101.4.12.6.2.6
-- 1.3.6.1.4.1.6296.101.4.12.6.2.6
-- 1.3.6.1.4.1.6296.101.4.12.16.2.6
-- 1.3.6.1.4.1.6296.101.4.12.16.2.6
-- 1.3.6.1.4.1.6296.101.4.12.16.2.6
		-- 1.3.6.1.4.1.6296.101.4.12.16.2.6
		sleY1731LRMepControlMegIndex OBJECT-TYPE
			SYNTAX Integer32 (1..65535)
			MAX-ACCESS read-write
			STATUS current
			DESCRIPTION
				"Indicates the MEG's Index of Up MEP."
			::= { sleY1731LocRefMepControl 6 }

		
--      1.3.6.1.4.1.6296.101.4.12.6.2.7
-- 1.3.6.1.4.1.6296.101.4.12.6.2.7
-- 1.3.6.1.4.1.6296.101.4.12.16.2.7
-- 1.3.6.1.4.1.6296.101.4.12.16.2.7
-- 1.3.6.1.4.1.6296.101.4.12.16.2.7
		-- 1.3.6.1.4.1.6296.101.4.12.16.2.7
		sleY1731LRMepControlMepIdentifier OBJECT-TYPE
			SYNTAX Integer32 (1..8191)
			MAX-ACCESS read-write
			STATUS current
			DESCRIPTION
				"Indicates the identifier of Up MEP."
			::= { sleY1731LocRefMepControl 7 }

		
--      1.3.6.1.4.1.6296.101.4.12.6.2.7
-- 1.3.6.1.4.1.6296.101.4.12.6.2.7
-- 1.3.6.1.4.1.6296.101.4.12.16.2.8
-- 1.3.6.1.4.1.6296.101.4.12.16.2.8
-- 1.3.6.1.4.1.6296.101.4.12.16.2.8
		-- 1.3.6.1.4.1.6296.101.4.12.16.2.8
		sleY1731LRMepControlRmepIdentifier OBJECT-TYPE
			SYNTAX Integer32 (1..8191)
			MAX-ACCESS read-write
			STATUS current
			DESCRIPTION
				"Indicates the identifier of RMEP id of Up MEP."
			::= { sleY1731LocRefMepControl 8 }

		
--      1.3.6.1.4.1.6296.101.4.12.6.2.6
-- 1.3.6.1.4.1.6296.101.4.12.6.2.6
-- 1.3.6.1.4.1.6296.101.4.12.16.2.9
-- 1.3.6.1.4.1.6296.101.4.12.16.2.9
-- 1.3.6.1.4.1.6296.101.4.12.16.2.9
		-- 1.3.6.1.4.1.6296.101.4.12.16.2.9
		sleY1731LRMepControlDMegIndex OBJECT-TYPE
			SYNTAX Integer32 (1..65535)
			MAX-ACCESS read-write
			STATUS current
			DESCRIPTION
				"Indicates the MEG's Index of Down MEP."
			::= { sleY1731LocRefMepControl 9 }

		
--      1.3.6.1.4.1.6296.101.4.12.6.2.7
-- 1.3.6.1.4.1.6296.101.4.12.6.2.7
-- 1.3.6.1.4.1.6296.101.4.12.16.2.10
-- 1.3.6.1.4.1.6296.101.4.12.16.2.10
-- 1.3.6.1.4.1.6296.101.4.12.16.2.10
		-- 1.3.6.1.4.1.6296.101.4.12.16.2.10
		sleY1731LRMepControlDMepIdentifier OBJECT-TYPE
			SYNTAX Integer32 (1..8191)
			MAX-ACCESS read-write
			STATUS current
			DESCRIPTION
				"Indicates the identifier of Down MEP."
			::= { sleY1731LocRefMepControl 10 }

		
--      1.3.6.1.4.1.6296.101.4.12.6.2.7
-- 1.3.6.1.4.1.6296.101.4.12.6.2.7
-- 1.3.6.1.4.1.6296.101.4.12.16.2.11
-- 1.3.6.1.4.1.6296.101.4.12.16.2.11
-- 1.3.6.1.4.1.6296.101.4.12.16.2.11
		-- 1.3.6.1.4.1.6296.101.4.12.16.2.11
		sleY1731LRMepControlDRmepIdentifier OBJECT-TYPE
			SYNTAX Integer32 (1..8191)
			MAX-ACCESS read-write
			STATUS current
			DESCRIPTION
				"Indicates the identifier of RMEP id of Down MEP."
			::= { sleY1731LocRefMepControl 11 }

		
--      1.3.6.1.4.1.6296.101.4.12.6.3
-- 1.3.6.1.4.1.6296.101.4.12.6.3
-- 1.3.6.1.4.1.6296.101.4.12.16.3
-- 1.3.6.1.4.1.6296.101.4.12.16.3
-- 1.3.6.1.4.1.6296.101.4.12.16.3
		-- 1.3.6.1.4.1.6296.101.4.12.16.3
		sleY1731LocRefMepNotification OBJECT IDENTIFIER ::= { sleY1731LocRefMep 3 }

		
--      1.3.6.1.4.1.6296.101.4.12.6.3.1
-- 1.3.6.1.4.1.6296.101.4.12.6.3.1
-- 1.3.6.1.4.1.6296.101.4.12.16.3.1
-- 1.3.6.1.4.1.6296.101.4.12.16.3.1
-- 1.3.6.1.4.1.6296.101.4.12.16.3.1
		-- 1.3.6.1.4.1.6296.101.4.12.16.3.1
		sleY1731LRMepCreated NOTIFICATION-TYPE
			OBJECTS { sleY1731LRMepControlRequest, sleY1731LRMepControlTimeStamp, sleY1731LRMepControlReqResult, sleY1731LRMepControlMegIndex, sleY1731LRMepControlMepIdentifier, 
				sleY1731LRMepControlRmepIdentifier, sleY1731LRMepControlDMegIndex, sleY1731LRMepControlDMepIdentifier, sleY1731LRMepControlDRmepIdentifier }
			STATUS current
			DESCRIPTION 
				"createY1731LocRefMep"
			::= { sleY1731LocRefMepNotification 1 }

		
--      1.3.6.1.4.1.6296.101.4.12.6.3.1
-- 1.3.6.1.4.1.6296.101.4.12.6.3.1
-- 1.3.6.1.4.1.6296.101.4.12.16.3.3
-- 1.3.6.1.4.1.6296.101.4.12.16.3.3
-- 1.3.6.1.4.1.6296.101.4.12.16.3.3
		-- 1.3.6.1.4.1.6296.101.4.12.16.3.3
		sleY1731LRMEPDeleted NOTIFICATION-TYPE
			OBJECTS { sleY1731LRMepControlRequest, sleY1731LRMepControlTimeStamp, sleY1731LRMepControlReqResult, sleY1731LRMepControlMegIndex, sleY1731LRMepControlMepIdentifier, 
				sleY1731LRMepControlRmepIdentifier, sleY1731LRMepControlDMegIndex, sleY1731LRMepControlDMepIdentifier, sleY1731LRMepControlDRmepIdentifier }
			STATUS current
			DESCRIPTION 
				"deleteY1731LocRefMep"
			::= { sleY1731LocRefMepNotification 3 }

		
--   1.3.6.1.4.1.6296.101.4.13
-- 1.3.6.1.4.1.6296.101.4.13
		-- 1.3.6.1.4.1.6296.101.4.13
		sleCfmOam OBJECT IDENTIFIER ::= { sleFaultMgmt 13 }

		
--   1.3.6.1.4.1.6296.101.4.13.1
-- 1.3.6.1.4.1.6296.101.4.13.1
		-- 1.3.6.1.4.1.6296.101.4.13.1
		sleCfmBase OBJECT IDENTIFIER ::= { sleCfmOam 1 }

		
--   1.3.6.1.4.1.6296.101.4.13.1.1
-- 1.3.6.1.4.1.6296.101.4.13.1.1
		-- 1.3.6.1.4.1.6296.101.4.13.1.1
		sleCfmBaseGroup OBJECT IDENTIFIER ::= { sleCfmBase 1 }

		
--   1.3.6.1.4.1.6296.101.4.13.1.1.1
-- 1.3.6.1.4.1.6296.101.4.13.1.1.1
		-- 1.3.6.1.4.1.6296.101.4.13.1.1.1
		sleCfmEnable OBJECT-TYPE
			SYNTAX INTEGER
				{
				disable(0),
				enable(1)
				}
			MAX-ACCESS read-only
			STATUS current
			DESCRIPTION
				"Enables/Ddisables IEEE 802.1ag CFM OAM function"
			::= { sleCfmBaseGroup 1 }

		
--   1.3.6.1.4.1.6296.101.4.13.1.1.2
-- 1.3.6.1.4.1.6296.101.4.13.1.1.2
		-- 1.3.6.1.4.1.6296.101.4.13.1.1.2
		sleCfmLtrCacheHoldTime OBJECT-TYPE
			SYNTAX Integer32 (1..65535)
			MAX-ACCESS read-only
			STATUS current
			DESCRIPTION
				"Indicates the time that cache entries will be retained"
			::= { sleCfmBaseGroup 2 }

		
--   1.3.6.1.4.1.6296.101.4.13.1.1.3
-- 1.3.6.1.4.1.6296.101.4.13.1.1.3
		-- 1.3.6.1.4.1.6296.101.4.13.1.1.3
		sleCfmLtrCacheSize OBJECT-TYPE
			SYNTAX Integer32 (1..4095)
			MAX-ACCESS read-only
			STATUS current
			DESCRIPTION
				"Indicates the number of entries in the traceroute cache"
			::= { sleCfmBaseGroup 3 }

		
--   1.3.6.1.4.1.6296.101.4.13.1.1.4
-- 1.3.6.1.4.1.6296.101.4.13.1.1.4
		-- 1.3.6.1.4.1.6296.101.4.13.1.1.4
		sleCfmSnmpServerTraps OBJECT-TYPE
			SYNTAX BITS
				{
				rdiccm(0),
				macstatus(1),
				remoteccm(2),
				errorccm(3),
				xconccm(4)
				}
			MAX-ACCESS read-only
			STATUS current
			DESCRIPTION
				"Indicates the SNMP traps"
			::= { sleCfmBaseGroup 4 }

		
--   1.3.6.1.4.1.6296.101.4.13.1.1.5
-- 1.3.6.1.4.1.6296.101.4.13.1.1.5
		-- 1.3.6.1.4.1.6296.101.4.13.1.1.5
		sleCfmXcheckStartDelay OBJECT-TYPE
			SYNTAX Integer32 (1..65535)
			MAX-ACCESS read-only
			STATUS current
			DESCRIPTION
				"Indicates the delay before the cross-check is started"
			::= { sleCfmBaseGroup 5 }

		
--   1.3.6.1.4.1.6296.101.4.13.1.2
-- 1.3.6.1.4.1.6296.101.4.13.1.2
		-- 1.3.6.1.4.1.6296.101.4.13.1.2
		sleCfmBaseControl OBJECT IDENTIFIER ::= { sleCfmBase 2 }

		
--   1.3.6.1.4.1.6296.101.4.13.1.2.1
-- 1.3.6.1.4.1.6296.101.4.13.1.2.1
		-- 1.3.6.1.4.1.6296.101.4.13.1.2.1
		sleCfmBaseControlRequest OBJECT-TYPE
			SYNTAX INTEGER
				{
				setCfmEnable(1),
				setCfmLtrCacheProfile(2),
				setCfmSnmpProfile(3),
				setCfmXcheckProfile(4),
				destroyMipCcdb(5),
				destroyLtrCache(6),
				createCfmTrunkPort(7),
				deleteCfmTrunkPort(8)
				}
			MAX-ACCESS read-write
			STATUS current
			DESCRIPTION
				" This attribute identifies the control commands.
				updateAlarmList:
				   the NE updates entries of alarms in the sleAlarmListTable
				   after having changed alarm severities of alarms 
				   (due to change profile pointers in
				   managed entities or after modification of alarm severities 
				   in profiles). This command should be applied once after having 
				   finisled modifications of severties.
				modifyAlarmSeverity: 
				   modifies the severity of an alarm in specific profile.
				createAlarmSeverityProfile: 
				   creates a new profile with default severities.
				   The severities then have to be modified with command changeAlarmSeverity.
				deleteAlarmSeverityProfile: 
				   deletes a profile. Profile 1 is not allowed to be deleted.
				 
				Notifications : none "
			::= { sleCfmBaseControl 1 }

		
--   1.3.6.1.4.1.6296.101.4.13.1.2.2
-- 1.3.6.1.4.1.6296.101.4.13.1.2.2
		-- 1.3.6.1.4.1.6296.101.4.13.1.2.2
		sleCfmBaseControlStatus OBJECT-TYPE
			SYNTAX SleControlStatusType
			MAX-ACCESS read-only
			STATUS current
			DESCRIPTION
				" The status of a control request. "
			::= { sleCfmBaseControl 2 }

		
--   1.3.6.1.4.1.6296.101.4.13.1.2.3
-- 1.3.6.1.4.1.6296.101.4.13.1.2.3
		-- 1.3.6.1.4.1.6296.101.4.13.1.2.3
		sleCfmBaseControlTimer OBJECT-TYPE
			SYNTAX Gauge32
			MAX-ACCESS read-write
			STATUS current
			DESCRIPTION
				" The maximum wait time for the manager for command ending.
				For long running commands.
				The manager reads this value from the DSLAM. "
			::= { sleCfmBaseControl 3 }

		
--   1.3.6.1.4.1.6296.101.4.13.1.2.4
-- 1.3.6.1.4.1.6296.101.4.13.1.2.4
		-- 1.3.6.1.4.1.6296.101.4.13.1.2.4
		sleCfmBaseControlTimeStamp OBJECT-TYPE
			SYNTAX TimeTicks
			MAX-ACCESS read-only
			STATUS current
			DESCRIPTION
				" The time stamp of the last command (end of command). "
			::= { sleCfmBaseControl 4 }

		
--   1.3.6.1.4.1.6296.101.4.13.1.2.5
-- 1.3.6.1.4.1.6296.101.4.13.1.2.5
		-- 1.3.6.1.4.1.6296.101.4.13.1.2.5
		sleCfmBaseControlReqResult OBJECT-TYPE
			SYNTAX SleControlRequestResultType
			MAX-ACCESS read-only
			STATUS current
			DESCRIPTION
				" The result of the last user command. "
			::= { sleCfmBaseControl 5 }

		
--   1.3.6.1.4.1.6296.101.4.13.1.2.6
-- 1.3.6.1.4.1.6296.101.4.13.1.2.6
		-- 1.3.6.1.4.1.6296.101.4.13.1.2.6
		sleCfmBaseControlEnable OBJECT-TYPE
			SYNTAX INTEGER
				{
				disable(0),
				enable(1)
				}
			MAX-ACCESS read-write
			STATUS current
			DESCRIPTION
				"Enables/Ddisables IEEE 802.1ag CFM OAM function"
			::= { sleCfmBaseControl 6 }

		
--   1.3.6.1.4.1.6296.101.4.13.1.2.7
-- 1.3.6.1.4.1.6296.101.4.13.1.2.7
		-- 1.3.6.1.4.1.6296.101.4.13.1.2.7
		sleCfmBaseControlLtrCacheHoldTime OBJECT-TYPE
			SYNTAX Integer32 (1..65535)
			MAX-ACCESS read-write
			STATUS current
			DESCRIPTION
				"Indicates the time that cache entries will be retained"
			::= { sleCfmBaseControl 7 }

		
--   1.3.6.1.4.1.6296.101.4.13.1.2.8
-- 1.3.6.1.4.1.6296.101.4.13.1.2.8
		-- 1.3.6.1.4.1.6296.101.4.13.1.2.8
		sleCfmBaseControlLtrCacheSize OBJECT-TYPE
			SYNTAX Integer32 (1..4095)
			MAX-ACCESS read-write
			STATUS current
			DESCRIPTION
				"Indicates the number of entries in the traceroute cache"
			::= { sleCfmBaseControl 8 }

		
--   1.3.6.1.4.1.6296.101.4.13.1.2.9
-- 1.3.6.1.4.1.6296.101.4.13.1.2.9
		-- 1.3.6.1.4.1.6296.101.4.13.1.2.9
		sleCfmBaseControlSnmpServerTraps OBJECT-TYPE
			SYNTAX BITS
				{
				ridccm(0),
				macstatus(1),
				remoteccm(2),
				errorccm(3),
				xconccm(4)
				}
			MAX-ACCESS read-write
			STATUS current
			DESCRIPTION
				"Indicates the SNMP traps"
			::= { sleCfmBaseControl 9 }

		
--   1.3.6.1.4.1.6296.101.4.13.1.2.10
-- 1.3.6.1.4.1.6296.101.4.13.1.2.10
		-- 1.3.6.1.4.1.6296.101.4.13.1.2.10
		sleCfmBaseControlXcheckStartDelay OBJECT-TYPE
			SYNTAX Integer32 (1..65535)
			MAX-ACCESS read-write
			STATUS current
			DESCRIPTION
				"Indicates the delay before the cross-check is started"
			::= { sleCfmBaseControl 10 }

		
--   1.3.6.1.4.1.6296.101.4.13.1.2.11
-- 1.3.6.1.4.1.6296.101.4.13.1.2.11
		-- 1.3.6.1.4.1.6296.101.4.13.1.2.11
		sleCfmBaseControlTrunkIndex OBJECT-TYPE
			SYNTAX INTEGER (1..65535)
			MAX-ACCESS read-write
			STATUS current
			DESCRIPTION
				"Trunk Port Index"
			::= { sleCfmBaseControl 11 }

		
--   1.3.6.1.4.1.6296.101.4.13.1.2.12
-- 1.3.6.1.4.1.6296.101.4.13.1.2.12
		-- 1.3.6.1.4.1.6296.101.4.13.1.2.12
		sleCfmBaseControlTrunkMdName OBJECT-TYPE
			SYNTAX OCTET STRING
			MAX-ACCESS read-write
			STATUS current
			DESCRIPTION
				"trunk port md name."
			::= { sleCfmBaseControl 12 }

		
--   1.3.6.1.4.1.6296.101.4.13.1.2.13
-- 1.3.6.1.4.1.6296.101.4.13.1.2.13
		-- 1.3.6.1.4.1.6296.101.4.13.1.2.13
		sleCfmBaseControlTrunkMaVid OBJECT-TYPE
			SYNTAX Integer32 (1..4094)
			MAX-ACCESS read-write
			STATUS current
			DESCRIPTION
				"Indicates the MA's VID"
			::= { sleCfmBaseControl 13 }

		
--   1.3.6.1.4.1.6296.101.4.13.1.3
-- 1.3.6.1.4.1.6296.101.4.13.1.3
		-- 1.3.6.1.4.1.6296.101.4.13.1.3
		sleCfmBaseNotification OBJECT IDENTIFIER ::= { sleCfmBase 3 }

		
--   1.3.6.1.4.1.6296.101.4.13.1.3.1
-- 1.3.6.1.4.1.6296.101.4.13.1.3.1
		-- 1.3.6.1.4.1.6296.101.4.13.1.3.1
		sleCfmEnableChanged NOTIFICATION-TYPE
			OBJECTS { sleCfmBaseControlStatus, sleCfmBaseControlTimeStamp, sleCfmBaseControlReqResult, sleCfmBaseControlEnable }
			STATUS current
			DESCRIPTION 
				"setCfmEnable"
			::= { sleCfmBaseNotification 1 }

		
--   1.3.6.1.4.1.6296.101.4.13.1.3.2
-- 1.3.6.1.4.1.6296.101.4.13.1.3.2
		-- 1.3.6.1.4.1.6296.101.4.13.1.3.2
		sleCfmLtrCacheProfileChanged NOTIFICATION-TYPE
			OBJECTS { sleCfmBaseControlStatus, sleCfmBaseControlTimeStamp, sleCfmBaseControlReqResult, sleCfmBaseControlLtrCacheHoldTime, sleCfmBaseControlLtrCacheSize
				 }
			STATUS current
			DESCRIPTION 
				"setCfmLtrCacheProfile"
			::= { sleCfmBaseNotification 2 }

		
--   1.3.6.1.4.1.6296.101.4.13.1.3.3
-- 1.3.6.1.4.1.6296.101.4.13.1.3.3
		-- 1.3.6.1.4.1.6296.101.4.13.1.3.3
		sleCfmSnmpServerTrapsChanged NOTIFICATION-TYPE
			OBJECTS { sleCfmBaseControlStatus, sleCfmBaseControlTimeStamp, sleCfmBaseControlReqResult, sleCfmBaseControlSnmpServerTraps }
			STATUS current
			DESCRIPTION 
				"setCfmSnmpProfile"
			::= { sleCfmBaseNotification 3 }

		
--   1.3.6.1.4.1.6296.101.4.13.1.3.4
-- 1.3.6.1.4.1.6296.101.4.13.1.3.4
		-- 1.3.6.1.4.1.6296.101.4.13.1.3.4
		sleCfmXcheckStartDelayChanged NOTIFICATION-TYPE
			OBJECTS { sleCfmBaseControlStatus, sleCfmBaseControlTimeStamp, sleCfmBaseControlReqResult, sleCfmBaseControlXcheckStartDelay }
			STATUS current
			DESCRIPTION 
				"setCfmXcheckProfile"
			::= { sleCfmBaseNotification 4 }

		
--   1.3.6.1.4.1.6296.101.4.13.1.3.5
-- 1.3.6.1.4.1.6296.101.4.13.1.3.5
		-- 1.3.6.1.4.1.6296.101.4.13.1.3.5
		sleCfmMipCcdbDestroyed NOTIFICATION-TYPE
			OBJECTS { sleCfmBaseControlRequest, sleCfmBaseControlTimeStamp, sleCfmBaseControlReqResult }
			STATUS current
			DESCRIPTION 
				"destroyMipCcdb"
			::= { sleCfmBaseNotification 5 }

		
--   1.3.6.1.4.1.6296.101.4.13.1.3.6
-- 1.3.6.1.4.1.6296.101.4.13.1.3.6
		-- 1.3.6.1.4.1.6296.101.4.13.1.3.6
		sleCfmLtrCacheDestroyed NOTIFICATION-TYPE
			OBJECTS { sleCfmBaseControlRequest, sleCfmBaseControlTimeStamp, sleCfmBaseControlReqResult }
			STATUS current
			DESCRIPTION 
				"destroyLtrCache"
			::= { sleCfmBaseNotification 6 }

		
--   1.3.6.1.4.1.6296.101.4.13.1.3.7
-- 1.3.6.1.4.1.6296.101.4.13.1.3.7
		-- 1.3.6.1.4.1.6296.101.4.13.1.3.7
		sleCfmTrunkPortCreated NOTIFICATION-TYPE
			OBJECTS { sleCfmBaseControlStatus, sleCfmBaseControlTimeStamp, sleCfmBaseControlReqResult, sleCfmBaseControlTrunkIndex, sleCfmBaseControlTrunkMdName, 
				sleCfmBaseControlTrunkMaVid }
			STATUS current
			DESCRIPTION 
				"createCfmTrunkPort"
			::= { sleCfmBaseNotification 7 }

		
--   1.3.6.1.4.1.6296.101.4.13.1.3.8
-- 1.3.6.1.4.1.6296.101.4.13.1.3.8
		-- 1.3.6.1.4.1.6296.101.4.13.1.3.8
		sleCfmTrunkPortDeleted NOTIFICATION-TYPE
			OBJECTS { sleCfmBaseControlStatus, sleCfmBaseControlTimeStamp, sleCfmBaseControlReqResult, sleCfmBaseControlTrunkIndex }
			STATUS current
			DESCRIPTION 
				"deleteCfmTrunkPort"
			::= { sleCfmBaseNotification 8 }

		
--   1.3.6.1.4.1.6296.101.4.13.1.4
-- 1.3.6.1.4.1.6296.101.4.13.1.4
		-- 1.3.6.1.4.1.6296.101.4.13.1.4
		sleCfmTrunkTable OBJECT-TYPE
			SYNTAX SEQUENCE OF SleCfmTrunkEntry
			MAX-ACCESS not-accessible
			STATUS current
			DESCRIPTION
				"Description."
			::= { sleCfmBase 4 }

		
--   1.3.6.1.4.1.6296.101.4.13.1.4.1
-- 1.3.6.1.4.1.6296.101.4.13.1.4.1
		-- 1.3.6.1.4.1.6296.101.4.13.1.4.1
		sleCfmTrunkEntry OBJECT-TYPE
			SYNTAX SleCfmTrunkEntry
			MAX-ACCESS not-accessible
			STATUS current
			DESCRIPTION
				"Description."
			INDEX { sleCfmTrunkIndex }
			::= { sleCfmTrunkTable 1 }

		
		SleCfmTrunkEntry ::=
			SEQUENCE { 
				sleCfmTrunkIndex
					INTEGER,
				sleCfmTrunkMdName
					OCTET STRING,
				sleCfmTrunkMaVid
					INTEGER
			 }

--   1.3.6.1.4.1.6296.101.4.13.1.4.1.1
-- 1.3.6.1.4.1.6296.101.4.13.1.4.1.1
		-- 1.3.6.1.4.1.6296.101.4.13.1.4.1.1
		sleCfmTrunkIndex OBJECT-TYPE
			SYNTAX INTEGER (0..65535)
			MAX-ACCESS read-only
			STATUS current
			DESCRIPTION
				"trunk port index."
			::= { sleCfmTrunkEntry 1 }

		
--   1.3.6.1.4.1.6296.101.4.13.1.4.1.2
-- 1.3.6.1.4.1.6296.101.4.13.1.4.1.2
		-- 1.3.6.1.4.1.6296.101.4.13.1.4.1.2
		sleCfmTrunkMdName OBJECT-TYPE
			SYNTAX OCTET STRING (SIZE (1..12))
			MAX-ACCESS read-only
			STATUS current
			DESCRIPTION
				"trunk port md name."
			::= { sleCfmTrunkEntry 2 }

		
--   1.3.6.1.4.1.6296.101.4.13.1.4.1.3
-- 1.3.6.1.4.1.6296.101.4.13.1.4.1.3
		-- 1.3.6.1.4.1.6296.101.4.13.1.4.1.3
		sleCfmTrunkMaVid OBJECT-TYPE
			SYNTAX INTEGER (1..4094)
			MAX-ACCESS read-only
			STATUS current
			DESCRIPTION
				"Indicates the MA's VID"
			::= { sleCfmTrunkEntry 3 }

		
--   1.3.6.1.4.1.6296.101.4.13.2
-- 1.3.6.1.4.1.6296.101.4.13.2
		-- 1.3.6.1.4.1.6296.101.4.13.2
		sleCfmMd OBJECT IDENTIFIER ::= { sleCfmOam 2 }

		
--   1.3.6.1.4.1.6296.101.4.13.2.1
-- 1.3.6.1.4.1.6296.101.4.13.2.1
		-- 1.3.6.1.4.1.6296.101.4.13.2.1
		sleCfmMdTable OBJECT-TYPE
			SYNTAX SEQUENCE OF SleCfmMdEntry
			MAX-ACCESS not-accessible
			STATUS current
			DESCRIPTION
				"Description."
			::= { sleCfmMd 1 }

		
--   1.3.6.1.4.1.6296.101.4.13.2.1.1
-- 1.3.6.1.4.1.6296.101.4.13.2.1.1
		-- 1.3.6.1.4.1.6296.101.4.13.2.1.1
		sleCfmMdEntry OBJECT-TYPE
			SYNTAX SleCfmMdEntry
			MAX-ACCESS not-accessible
			STATUS current
			DESCRIPTION
				"Description."
			INDEX { sleCfmMdIndex }
			::= { sleCfmMdTable 1 }

		
		SleCfmMdEntry ::=
			SEQUENCE { 
				sleCfmMdIndex
					Integer32,
				sleCfmMdName
					OCTET STRING,
				sleCfmMdLevel
					Integer32,
				sleCfmMdMepEnable
					INTEGER,
				sleCfmMdCcEnable
					INTEGER,
				sleCfmMdCcInterval
					Integer32,
				sleCfmMdCcPriority
					Integer32,
				sleCfmMdCcLossThreshold
					Integer32,
				sleCfmMdCcHoldTime
					Integer32,
				sleCfmMdFaultPriority
					INTEGER,
				sleCfmMdFaultKeepTime
					Integer32,
				sleCfmMdFaultClearTime
					Integer32,
				sleCfmMdXcheckEnable
					INTEGER
			 }

--   1.3.6.1.4.1.6296.101.4.13.2.1.1.1
-- 1.3.6.1.4.1.6296.101.4.13.2.1.1.1
		-- 1.3.6.1.4.1.6296.101.4.13.2.1.1.1
		sleCfmMdIndex OBJECT-TYPE
			SYNTAX Integer32 (1..65535)
			MAX-ACCESS read-only
			STATUS current
			DESCRIPTION
				"Indicates the MD's Index"
			::= { sleCfmMdEntry 1 }

		
--   1.3.6.1.4.1.6296.101.4.13.2.1.1.2
-- 1.3.6.1.4.1.6296.101.4.13.2.1.1.2
		-- 1.3.6.1.4.1.6296.101.4.13.2.1.1.2
		sleCfmMdName OBJECT-TYPE
			SYNTAX OCTET STRING (SIZE (1..12))
			MAX-ACCESS read-only
			STATUS current
			DESCRIPTION
				"The MD's name"
			::= { sleCfmMdEntry 2 }

		
--   1.3.6.1.4.1.6296.101.4.13.2.1.1.3
-- 1.3.6.1.4.1.6296.101.4.13.2.1.1.3
		-- 1.3.6.1.4.1.6296.101.4.13.2.1.1.3
		sleCfmMdLevel OBJECT-TYPE
			SYNTAX Integer32 (0..7)
			MAX-ACCESS read-only
			STATUS current
			DESCRIPTION
				"Indicates the MD's level"
			::= { sleCfmMdEntry 3 }

		
--   1.3.6.1.4.1.6296.101.4.13.2.1.1.4
-- 1.3.6.1.4.1.6296.101.4.13.2.1.1.4
		-- 1.3.6.1.4.1.6296.101.4.13.2.1.1.4
		sleCfmMdMepEnable OBJECT-TYPE
			SYNTAX INTEGER
				{
				disable(0),
				enable(1)
				}
			MAX-ACCESS read-only
			STATUS current
			DESCRIPTION
				"Enables/Disables CFM OAM for MEPs"
			::= { sleCfmMdEntry 4 }

		
--   1.3.6.1.4.1.6296.101.4.13.2.1.1.5
-- 1.3.6.1.4.1.6296.101.4.13.2.1.1.5
		-- 1.3.6.1.4.1.6296.101.4.13.2.1.1.5
		sleCfmMdCcEnable OBJECT-TYPE
			SYNTAX INTEGER
				{
				disable(0),
				enable(1)
				}
			MAX-ACCESS read-only
			STATUS current
			DESCRIPTION
				"Enables/Disables MEPs to send Continuity Check messages"
			::= { sleCfmMdEntry 5 }

		
--   1.3.6.1.4.1.6296.101.4.13.2.1.1.6
-- 1.3.6.1.4.1.6296.101.4.13.2.1.1.6
		-- 1.3.6.1.4.1.6296.101.4.13.2.1.1.6
		sleCfmMdCcInterval OBJECT-TYPE
			SYNTAX Integer32 (2..7)
			MAX-ACCESS read-only
			STATUS current
			DESCRIPTION
				"Indicates the interval between CCM transmissions"
			::= { sleCfmMdEntry 6 }

		
--   1.3.6.1.4.1.6296.101.4.13.2.1.1.7
-- 1.3.6.1.4.1.6296.101.4.13.2.1.1.7
		-- 1.3.6.1.4.1.6296.101.4.13.2.1.1.7
		sleCfmMdCcPriority OBJECT-TYPE
			SYNTAX Integer32 (0..7)
			MAX-ACCESS read-only
			STATUS current
			DESCRIPTION
				"Indicates the CCM Priority"
			::= { sleCfmMdEntry 7 }

		
--   1.3.6.1.4.1.6296.101.4.13.2.1.1.8
-- 1.3.6.1.4.1.6296.101.4.13.2.1.1.8
		-- 1.3.6.1.4.1.6296.101.4.13.2.1.1.8
		sleCfmMdCcLossThreshold OBJECT-TYPE
			SYNTAX Integer32 (2..255)
			MAX-ACCESS read-only
			STATUS current
			DESCRIPTION
				"Indicates the minimum number of CCMs that can be missed before declaring that a MEP is down"
			::= { sleCfmMdEntry 8 }

		
--   1.3.6.1.4.1.6296.101.4.13.2.1.1.9
-- 1.3.6.1.4.1.6296.101.4.13.2.1.1.9
		-- 1.3.6.1.4.1.6296.101.4.13.2.1.1.9
		sleCfmMdCcHoldTime OBJECT-TYPE
			SYNTAX Integer32 (1..65535)
			MAX-ACCESS read-only
			STATUS current
			DESCRIPTION
				"Indicates the time that data of a missing MEP is kept"
			::= { sleCfmMdEntry 9 }

		
--   1.3.6.1.4.1.6296.101.4.13.2.1.1.10
-- 1.3.6.1.4.1.6296.101.4.13.2.1.1.10
		-- 1.3.6.1.4.1.6296.101.4.13.2.1.1.10
		sleCfmMdFaultPriority OBJECT-TYPE
			SYNTAX INTEGER
				{
				rdiccm(1),
				macstatus(2),
				remoteccm(3),
				errorccm(4),
				xconccm(5)
				}
			MAX-ACCESS read-only
			STATUS current
			DESCRIPTION
				"Indicates the lowest priority for fault alarm"
			::= { sleCfmMdEntry 10 }

		
--   1.3.6.1.4.1.6296.101.4.13.2.1.1.11
-- 1.3.6.1.4.1.6296.101.4.13.2.1.1.11
		-- 1.3.6.1.4.1.6296.101.4.13.2.1.1.11
		sleCfmMdFaultKeepTime OBJECT-TYPE
			SYNTAX Integer32 (0..1023)
			MAX-ACCESS read-only
			STATUS current
			DESCRIPTION
				"Indicates the keep time for the fault alarm"
			::= { sleCfmMdEntry 11 }

		
--   1.3.6.1.4.1.6296.101.4.13.2.1.1.12
-- 1.3.6.1.4.1.6296.101.4.13.2.1.1.12
		-- 1.3.6.1.4.1.6296.101.4.13.2.1.1.12
		sleCfmMdFaultClearTime OBJECT-TYPE
			SYNTAX Integer32 (0..1023)
			MAX-ACCESS read-only
			STATUS current
			DESCRIPTION
				"Indicates the clear time for the fault alarm"
			::= { sleCfmMdEntry 12 }

		
--   1.3.6.1.4.1.6296.101.4.13.2.1.1.13
-- 1.3.6.1.4.1.6296.101.4.13.2.1.1.13
		-- 1.3.6.1.4.1.6296.101.4.13.2.1.1.13
		sleCfmMdXcheckEnable OBJECT-TYPE
			SYNTAX INTEGER
				{
				disable(0),
				enable(1)
				}
			MAX-ACCESS read-only
			STATUS current
			DESCRIPTION
				"Enables/Disables CFM cross-check for a specific MEG"
			::= { sleCfmMdEntry 13 }

		
--   1.3.6.1.4.1.6296.101.4.13.2.2
-- 1.3.6.1.4.1.6296.101.4.13.2.2
		-- 1.3.6.1.4.1.6296.101.4.13.2.2
		sleCfmMdControl OBJECT IDENTIFIER ::= { sleCfmMd 2 }

		
--   1.3.6.1.4.1.6296.101.4.13.2.2.1
-- 1.3.6.1.4.1.6296.101.4.13.2.2.1
		-- 1.3.6.1.4.1.6296.101.4.13.2.2.1
		sleCfmMdControlRequest OBJECT-TYPE
			SYNTAX INTEGER
				{
				createCfmMd(1),
				deleteCfmMd(2),
				setCfmMdMepEnable(3),
				setCfmMdCcEnable(4),
				setCfmMdCcProfile(5),
				setCfmMdFaultProfile(6),
				setCfmMdXcheckEnable(7),
				destroyCfmMdError(8),
				destroyCfmMdRmep(9)
				}
			MAX-ACCESS read-write
			STATUS current
			DESCRIPTION
				"Description."
			::= { sleCfmMdControl 1 }

		
--   1.3.6.1.4.1.6296.101.4.13.2.2.2
-- 1.3.6.1.4.1.6296.101.4.13.2.2.2
		-- 1.3.6.1.4.1.6296.101.4.13.2.2.2
		sleCfmMdControlStatus OBJECT-TYPE
			SYNTAX SleControlStatusType
			MAX-ACCESS read-only
			STATUS current
			DESCRIPTION
				"Description."
			::= { sleCfmMdControl 2 }

		
--   1.3.6.1.4.1.6296.101.4.13.2.2.3
-- 1.3.6.1.4.1.6296.101.4.13.2.2.3
		-- 1.3.6.1.4.1.6296.101.4.13.2.2.3
		sleCfmMdControlTimer OBJECT-TYPE
			SYNTAX Gauge32
			MAX-ACCESS read-write
			STATUS current
			DESCRIPTION
				"Description."
			::= { sleCfmMdControl 3 }

		
--   1.3.6.1.4.1.6296.101.4.13.2.2.4
-- 1.3.6.1.4.1.6296.101.4.13.2.2.4
		-- 1.3.6.1.4.1.6296.101.4.13.2.2.4
		sleCfmMdControlTimeStamp OBJECT-TYPE
			SYNTAX TimeTicks
			MAX-ACCESS read-only
			STATUS current
			DESCRIPTION
				"Description."
			::= { sleCfmMdControl 4 }

		
--   1.3.6.1.4.1.6296.101.4.13.2.2.5
-- 1.3.6.1.4.1.6296.101.4.13.2.2.5
		-- 1.3.6.1.4.1.6296.101.4.13.2.2.5
		sleCfmMdControlReqResult OBJECT-TYPE
			SYNTAX SleControlRequestResultType
			MAX-ACCESS read-only
			STATUS current
			DESCRIPTION
				"Description."
			::= { sleCfmMdControl 5 }

		
--   1.3.6.1.4.1.6296.101.4.13.2.2.6
-- 1.3.6.1.4.1.6296.101.4.13.2.2.6
		-- 1.3.6.1.4.1.6296.101.4.13.2.2.6
		sleCfmMdControlIndex OBJECT-TYPE
			SYNTAX Integer32 (1..65535)
			MAX-ACCESS read-write
			STATUS current
			DESCRIPTION
				"Indicates the MD's Index"
			::= { sleCfmMdControl 6 }

		
--   1.3.6.1.4.1.6296.101.4.13.2.2.7
-- 1.3.6.1.4.1.6296.101.4.13.2.2.7
		-- 1.3.6.1.4.1.6296.101.4.13.2.2.7
		sleCfmMdControlName OBJECT-TYPE
			SYNTAX OCTET STRING (SIZE (1..12))
			MAX-ACCESS read-write
			STATUS current
			DESCRIPTION
				"The MD's name"
			::= { sleCfmMdControl 7 }

		
--   1.3.6.1.4.1.6296.101.4.13.2.2.8
-- 1.3.6.1.4.1.6296.101.4.13.2.2.8
		-- 1.3.6.1.4.1.6296.101.4.13.2.2.8
		sleCfmMdControlLevel OBJECT-TYPE
			SYNTAX Integer32 (0..7)
			MAX-ACCESS read-write
			STATUS current
			DESCRIPTION
				"Indicates the MD's level"
			::= { sleCfmMdControl 8 }

		
--   1.3.6.1.4.1.6296.101.4.13.2.2.9
-- 1.3.6.1.4.1.6296.101.4.13.2.2.9
		-- 1.3.6.1.4.1.6296.101.4.13.2.2.9
		sleCfmMdControlMepEnable OBJECT-TYPE
			SYNTAX INTEGER
				{
				disable(0),
				enable(1)
				}
			MAX-ACCESS read-write
			STATUS current
			DESCRIPTION
				"Enables/Disables CFM OAM for MEPs"
			::= { sleCfmMdControl 9 }

		
--   1.3.6.1.4.1.6296.101.4.13.2.2.10
-- 1.3.6.1.4.1.6296.101.4.13.2.2.10
		-- 1.3.6.1.4.1.6296.101.4.13.2.2.10
		sleCfmMdControlCcEnable OBJECT-TYPE
			SYNTAX INTEGER
				{
				disable(0),
				enable(1)
				}
			MAX-ACCESS read-write
			STATUS current
			DESCRIPTION
				"Enables/Disables MEPs to send Continuity Check messages"
			::= { sleCfmMdControl 10 }

		
--   1.3.6.1.4.1.6296.101.4.13.2.2.11
-- 1.3.6.1.4.1.6296.101.4.13.2.2.11
		-- 1.3.6.1.4.1.6296.101.4.13.2.2.11
		sleCfmMdControlCcInterval OBJECT-TYPE
			SYNTAX Integer32 (2..7)
			MAX-ACCESS read-write
			STATUS current
			DESCRIPTION
				"Indicates the interval between CCM transmissions"
			::= { sleCfmMdControl 11 }

		
--   1.3.6.1.4.1.6296.101.4.13.2.2.12
-- 1.3.6.1.4.1.6296.101.4.13.2.2.12
		-- 1.3.6.1.4.1.6296.101.4.13.2.2.12
		sleCfmMdControlCcPriority OBJECT-TYPE
			SYNTAX Integer32 (0..7)
			MAX-ACCESS read-write
			STATUS current
			DESCRIPTION
				"Indicates the CCM Priority"
			::= { sleCfmMdControl 12 }

		
--   1.3.6.1.4.1.6296.101.4.13.2.2.13
-- 1.3.6.1.4.1.6296.101.4.13.2.2.13
		-- 1.3.6.1.4.1.6296.101.4.13.2.2.13
		sleCfmMdControlCcLossThreshold OBJECT-TYPE
			SYNTAX Integer32 (2..255)
			MAX-ACCESS read-write
			STATUS current
			DESCRIPTION
				"Indicates the minimum number of CCMs that can be missed before declaring that a MEP is down"
			::= { sleCfmMdControl 13 }

		
--   1.3.6.1.4.1.6296.101.4.13.2.2.14
-- 1.3.6.1.4.1.6296.101.4.13.2.2.14
		-- 1.3.6.1.4.1.6296.101.4.13.2.2.14
		sleCfmMdControlCcHoldTime OBJECT-TYPE
			SYNTAX Integer32 (1..65535)
			MAX-ACCESS read-write
			STATUS current
			DESCRIPTION
				"Indicates the time that data of a missing MEP is kept"
			::= { sleCfmMdControl 14 }

		
--   1.3.6.1.4.1.6296.101.4.13.2.2.15
-- 1.3.6.1.4.1.6296.101.4.13.2.2.15
		-- 1.3.6.1.4.1.6296.101.4.13.2.2.15
		sleCfmMdControlFaultPriority OBJECT-TYPE
			SYNTAX INTEGER
				{
				rdiccm(1),
				macstatus(2),
				remoteccm(3),
				errorccm(4),
				xconccm(5)
				}
			MAX-ACCESS read-write
			STATUS current
			DESCRIPTION
				"Indicates the lowest priority for fault alarm"
			::= { sleCfmMdControl 15 }

		
--   1.3.6.1.4.1.6296.101.4.13.2.2.16
-- 1.3.6.1.4.1.6296.101.4.13.2.2.16
		-- 1.3.6.1.4.1.6296.101.4.13.2.2.16
		sleCfmMdControlFaultKeepTime OBJECT-TYPE
			SYNTAX Integer32 (0..1023)
			MAX-ACCESS read-write
			STATUS current
			DESCRIPTION
				"Indicates the keep time for the fault alarm"
			::= { sleCfmMdControl 16 }

		
--   1.3.6.1.4.1.6296.101.4.13.2.2.17
-- 1.3.6.1.4.1.6296.101.4.13.2.2.17
		-- 1.3.6.1.4.1.6296.101.4.13.2.2.17
		sleCfmMdControlFaultClearTime OBJECT-TYPE
			SYNTAX Integer32 (0..1023)
			MAX-ACCESS read-write
			STATUS current
			DESCRIPTION
				"Indicates the clear time for the fault alarm"
			::= { sleCfmMdControl 17 }

		
--   1.3.6.1.4.1.6296.101.4.13.2.2.18
-- 1.3.6.1.4.1.6296.101.4.13.2.2.18
		-- 1.3.6.1.4.1.6296.101.4.13.2.2.18
		sleCfmMdControlXcheckEnable OBJECT-TYPE
			SYNTAX INTEGER
				{
				disable(0),
				enable(1)
				}
			MAX-ACCESS read-write
			STATUS current
			DESCRIPTION
				"Enables/Disables CFM cross-check for a specific MEG"
			::= { sleCfmMdControl 18 }

		
--   1.3.6.1.4.1.6296.101.4.13.2.3
-- 1.3.6.1.4.1.6296.101.4.13.2.3
		-- 1.3.6.1.4.1.6296.101.4.13.2.3
		sleCfmMdNotification OBJECT IDENTIFIER ::= { sleCfmMd 3 }

		
--   1.3.6.1.4.1.6296.101.4.13.2.3.1
-- 1.3.6.1.4.1.6296.101.4.13.2.3.1
		-- 1.3.6.1.4.1.6296.101.4.13.2.3.1
		sleCfmMdCreated NOTIFICATION-TYPE
			OBJECTS { sleCfmMdControlRequest, sleCfmMdControlTimeStamp, sleCfmMdControlReqResult, sleCfmMdControlName, sleCfmMdControlLevel
				 }
			STATUS current
			DESCRIPTION 
				"createCfmMd"
			::= { sleCfmMdNotification 1 }

		
--   1.3.6.1.4.1.6296.101.4.13.2.3.2
-- 1.3.6.1.4.1.6296.101.4.13.2.3.2
		-- 1.3.6.1.4.1.6296.101.4.13.2.3.2
		sleCfmMdDeleted NOTIFICATION-TYPE
			OBJECTS { sleCfmMdControlRequest, sleCfmMdControlTimeStamp, sleCfmMdControlReqResult, sleCfmMdControlName }
			STATUS current
			DESCRIPTION 
				"deleteCfmMd"
			::= { sleCfmMdNotification 2 }

		
--   1.3.6.1.4.1.6296.101.4.13.2.3.3
-- 1.3.6.1.4.1.6296.101.4.13.2.3.3
		-- 1.3.6.1.4.1.6296.101.4.13.2.3.3
		sleCfmMdMepEnableChanged NOTIFICATION-TYPE
			OBJECTS { sleCfmMdControlRequest, sleCfmMdControlTimeStamp, sleCfmMdControlReqResult, sleCfmMdControlIndex, sleCfmMdControlMepEnable
				 }
			STATUS current
			DESCRIPTION 
				"setCfmMepEnable"
			::= { sleCfmMdNotification 3 }

		
--   1.3.6.1.4.1.6296.101.4.13.2.3.4
-- 1.3.6.1.4.1.6296.101.4.13.2.3.4
		-- 1.3.6.1.4.1.6296.101.4.13.2.3.4
		sleCfmMdCcEnableChanged NOTIFICATION-TYPE
			OBJECTS { sleCfmMdControlRequest, sleCfmMdControlTimeStamp, sleCfmMdControlReqResult, sleCfmMdControlIndex, sleCfmMdControlCcEnable
				 }
			STATUS current
			DESCRIPTION 
				"setCfmMdCcEnable"
			::= { sleCfmMdNotification 4 }

		
--   1.3.6.1.4.1.6296.101.4.13.2.3.5
-- 1.3.6.1.4.1.6296.101.4.13.2.3.5
		-- 1.3.6.1.4.1.6296.101.4.13.2.3.5
		sleCfmMdCcProfileChanged NOTIFICATION-TYPE
			OBJECTS { sleCfmMdControlRequest, sleCfmMdControlTimeStamp, sleCfmMdControlReqResult, sleCfmMdControlIndex, sleCfmMdControlCcInterval, 
				sleCfmMdControlCcPriority, sleCfmMdControlCcLossThreshold, sleCfmMdControlCcHoldTime }
			STATUS current
			DESCRIPTION 
				"setCfmMdCcProfile"
			::= { sleCfmMdNotification 5 }

		
--   1.3.6.1.4.1.6296.101.4.13.2.3.6
-- 1.3.6.1.4.1.6296.101.4.13.2.3.6
		-- 1.3.6.1.4.1.6296.101.4.13.2.3.6
		sleCfmMdFaultProfileChanged NOTIFICATION-TYPE
			OBJECTS { sleCfmMdControlRequest, sleCfmMdControlTimeStamp, sleCfmMdControlReqResult, sleCfmMdControlIndex, sleCfmMdControlFaultPriority, 
				sleCfmMdControlFaultKeepTime, sleCfmMdControlFaultClearTime }
			STATUS current
			DESCRIPTION 
				"setCfmMdFaultProfile"
			::= { sleCfmMdNotification 6 }

		
--   1.3.6.1.4.1.6296.101.4.13.2.3.7
-- 1.3.6.1.4.1.6296.101.4.13.2.3.7
		-- 1.3.6.1.4.1.6296.101.4.13.2.3.7
		sleCfmMdXcheckEnableChanged NOTIFICATION-TYPE
			OBJECTS { sleCfmMdControlRequest, sleCfmMdControlTimeStamp, sleCfmMdControlReqResult, sleCfmMdControlIndex, sleCfmMdControlXcheckEnable
				 }
			STATUS current
			DESCRIPTION 
				"setCfmMdXcheckEnable"
			::= { sleCfmMdNotification 7 }

		
--   1.3.6.1.4.1.6296.101.4.13.2.3.8
-- 1.3.6.1.4.1.6296.101.4.13.2.3.8
		-- 1.3.6.1.4.1.6296.101.4.13.2.3.8
		sleCfmMdErrorDestoryed NOTIFICATION-TYPE
			OBJECTS { sleCfmMdControlRequest, sleCfmMdControlTimeStamp, sleCfmMdControlReqResult, sleCfmMdControlIndex }
			STATUS current
			DESCRIPTION 
				"destroyCfmMdError"
			::= { sleCfmMdNotification 8 }

		
--   1.3.6.1.4.1.6296.101.4.13.2.3.9
-- 1.3.6.1.4.1.6296.101.4.13.2.3.9
		-- 1.3.6.1.4.1.6296.101.4.13.2.3.9
		sleCfmMdRmepDestoryed NOTIFICATION-TYPE
			OBJECTS { sleCfmMdControlRequest, sleCfmMdControlTimeStamp, sleCfmMdControlReqResult, sleCfmMdControlIndex }
			STATUS current
			DESCRIPTION 
				"destroyCfmMdRmep"
			::= { sleCfmMdNotification 9 }

		
--   1.3.6.1.4.1.6296.101.4.13.3
-- 1.3.6.1.4.1.6296.101.4.13.3
		-- 1.3.6.1.4.1.6296.101.4.13.3
		sleCfmMa OBJECT IDENTIFIER ::= { sleCfmOam 3 }

		
--   1.3.6.1.4.1.6296.101.4.13.3.1
-- 1.3.6.1.4.1.6296.101.4.13.3.1
		-- 1.3.6.1.4.1.6296.101.4.13.3.1
		sleCfmMaTable OBJECT-TYPE
			SYNTAX SEQUENCE OF SleCfmMaEntry
			MAX-ACCESS not-accessible
			STATUS current
			DESCRIPTION
				"Description."
			::= { sleCfmMa 1 }

		
--   1.3.6.1.4.1.6296.101.4.13.3.1.1
-- 1.3.6.1.4.1.6296.101.4.13.3.1.1
		-- 1.3.6.1.4.1.6296.101.4.13.3.1.1
		sleCfmMaEntry OBJECT-TYPE
			SYNTAX SleCfmMaEntry
			MAX-ACCESS not-accessible
			STATUS current
			DESCRIPTION
				"Description."
			INDEX { sleCfmMdIndex, sleCfmMaIndex }
			::= { sleCfmMaTable 1 }

		
		SleCfmMaEntry ::=
			SEQUENCE { 
				sleCfmMaIndex
					Integer32,
				sleCfmMaName
					OCTET STRING,
				sleCfmMaVid
					Integer32,
				sleCfmMaMepEnable
					INTEGER,
				sleCfmMaCcEnable
					INTEGER,
				sleCfmMaCcInterval
					Integer32,
				sleCfmMaCcPriority
					Integer32,
				sleCfmMaCcLossThreshold
					Integer32,
				sleCfmMaCcFaultPriority
					INTEGER,
				sleCfmMaCcFaultKeepTime
					Integer32,
				sleCfmMaCcFaultClearTime
					Integer32,
				sleCfmMaXcheckEnable
					INTEGER
			 }

--   1.3.6.1.4.1.6296.101.4.13.3.1.1.1
-- 1.3.6.1.4.1.6296.101.4.13.3.1.1.1
		-- 1.3.6.1.4.1.6296.101.4.13.3.1.1.1
		sleCfmMaIndex OBJECT-TYPE
			SYNTAX Integer32 (1..65535)
			MAX-ACCESS read-only
			STATUS current
			DESCRIPTION
				"Indicates the MA's Index"
			::= { sleCfmMaEntry 1 }

		
--   1.3.6.1.4.1.6296.101.4.13.3.1.1.2
-- 1.3.6.1.4.1.6296.101.4.13.3.1.1.2
		-- 1.3.6.1.4.1.6296.101.4.13.3.1.1.2
		sleCfmMaName OBJECT-TYPE
			SYNTAX OCTET STRING (SIZE (1..12))
			MAX-ACCESS read-only
			STATUS current
			DESCRIPTION
				"The MA's name"
			::= { sleCfmMaEntry 2 }

		
--   1.3.6.1.4.1.6296.101.4.13.3.1.1.3
-- 1.3.6.1.4.1.6296.101.4.13.3.1.1.3
		-- 1.3.6.1.4.1.6296.101.4.13.3.1.1.3
		sleCfmMaVid OBJECT-TYPE
			SYNTAX Integer32 (1..4094)
			MAX-ACCESS read-only
			STATUS current
			DESCRIPTION
				"Indicates the MA's VID"
			::= { sleCfmMaEntry 3 }

		
--   1.3.6.1.4.1.6296.101.4.13.3.1.1.4
-- 1.3.6.1.4.1.6296.101.4.13.3.1.1.4
		-- 1.3.6.1.4.1.6296.101.4.13.3.1.1.4
		sleCfmMaMepEnable OBJECT-TYPE
			SYNTAX INTEGER
				{
				disable(0),
				enable(1)
				}
			MAX-ACCESS read-only
			STATUS current
			DESCRIPTION
				"Enables/Disables CFM OAM for MEPs"
			::= { sleCfmMaEntry 4 }

		
--   1.3.6.1.4.1.6296.101.4.13.3.1.1.5
-- 1.3.6.1.4.1.6296.101.4.13.3.1.1.5
		-- 1.3.6.1.4.1.6296.101.4.13.3.1.1.5
		sleCfmMaCcEnable OBJECT-TYPE
			SYNTAX INTEGER
				{
				disable(0),
				enable(1)
				}
			MAX-ACCESS read-only
			STATUS current
			DESCRIPTION
				"Enables/Disables MEPs to send Continuity Check messages"
			::= { sleCfmMaEntry 5 }

		
--   1.3.6.1.4.1.6296.101.4.13.3.1.1.6
-- 1.3.6.1.4.1.6296.101.4.13.3.1.1.6
		-- 1.3.6.1.4.1.6296.101.4.13.3.1.1.6
		sleCfmMaCcInterval OBJECT-TYPE
			SYNTAX Integer32 (2..7)
			MAX-ACCESS read-only
			STATUS current
			DESCRIPTION
				"Indicates the interval between CCM transmissions"
			::= { sleCfmMaEntry 6 }

		
--   1.3.6.1.4.1.6296.101.4.13.3.1.1.7
-- 1.3.6.1.4.1.6296.101.4.13.3.1.1.7
		-- 1.3.6.1.4.1.6296.101.4.13.3.1.1.7
		sleCfmMaCcPriority OBJECT-TYPE
			SYNTAX Integer32 (0..7)
			MAX-ACCESS read-only
			STATUS current
			DESCRIPTION
				"Indicates the CCM Priority"
			::= { sleCfmMaEntry 7 }

		
--   1.3.6.1.4.1.6296.101.4.13.3.1.1.8
-- 1.3.6.1.4.1.6296.101.4.13.3.1.1.8
		-- 1.3.6.1.4.1.6296.101.4.13.3.1.1.8
		sleCfmMaCcLossThreshold OBJECT-TYPE
			SYNTAX Integer32 (2..255)
			MAX-ACCESS read-only
			STATUS current
			DESCRIPTION
				"Indicates the minimum number of CCMs that can be missed before declaring that a MEP is down"
			::= { sleCfmMaEntry 8 }

		
--   1.3.6.1.4.1.6296.101.4.13.3.1.1.9
-- 1.3.6.1.4.1.6296.101.4.13.3.1.1.9
		-- 1.3.6.1.4.1.6296.101.4.13.3.1.1.9
		sleCfmMaCcFaultPriority OBJECT-TYPE
			SYNTAX INTEGER
				{
				rdiccm(1),
				macstatus(2),
				remoteccm(3),
				errorccm(4),
				xconccm(5)
				}
			MAX-ACCESS read-only
			STATUS current
			DESCRIPTION
				"Indicates the lowest priority for fault alarm"
			::= { sleCfmMaEntry 9 }

		
--   1.3.6.1.4.1.6296.101.4.13.3.1.1.10
-- 1.3.6.1.4.1.6296.101.4.13.3.1.1.10
		-- 1.3.6.1.4.1.6296.101.4.13.3.1.1.10
		sleCfmMaCcFaultKeepTime OBJECT-TYPE
			SYNTAX Integer32 (0..1023)
			MAX-ACCESS read-only
			STATUS current
			DESCRIPTION
				"Indicates the keep time for the fault alarm"
			::= { sleCfmMaEntry 10 }

		
--   1.3.6.1.4.1.6296.101.4.13.3.1.1.11
-- 1.3.6.1.4.1.6296.101.4.13.3.1.1.11
		-- 1.3.6.1.4.1.6296.101.4.13.3.1.1.11
		sleCfmMaCcFaultClearTime OBJECT-TYPE
			SYNTAX Integer32 (0..1023)
			MAX-ACCESS read-only
			STATUS current
			DESCRIPTION
				"Indicates the clear time for the fault alarm"
			::= { sleCfmMaEntry 11 }

		
--   1.3.6.1.4.1.6296.101.4.13.3.1.1.12
-- 1.3.6.1.4.1.6296.101.4.13.3.1.1.12
		-- 1.3.6.1.4.1.6296.101.4.13.3.1.1.12
		sleCfmMaXcheckEnable OBJECT-TYPE
			SYNTAX INTEGER
				{
				disable(0),
				enable(1)
				}
			MAX-ACCESS read-only
			STATUS current
			DESCRIPTION
				"Enables/Disables CFM cross-check for a specific MEG"
			::= { sleCfmMaEntry 12 }

		
--   1.3.6.1.4.1.6296.101.4.13.3.2
-- 1.3.6.1.4.1.6296.101.4.13.3.2
		-- 1.3.6.1.4.1.6296.101.4.13.3.2
		sleCfmMaControl OBJECT IDENTIFIER ::= { sleCfmMa 2 }

		
--   1.3.6.1.4.1.6296.101.4.13.3.2.1
-- 1.3.6.1.4.1.6296.101.4.13.3.2.1
		-- 1.3.6.1.4.1.6296.101.4.13.3.2.1
		sleCfmMaControlRequest OBJECT-TYPE
			SYNTAX INTEGER
				{
				createCfmMa(1),
				deleteCfmMa(2),
				setCfmMaMepEnable(3),
				setCfmMaCcEnable(4),
				setCfmMaCcProfile(5),
				setCfmMaFaultProfile(6),
				setCfmMaXcheckEnable(7)
				}
			MAX-ACCESS read-write
			STATUS current
			DESCRIPTION
				"Description."
			::= { sleCfmMaControl 1 }

		
--   1.3.6.1.4.1.6296.101.4.13.3.2.2
-- 1.3.6.1.4.1.6296.101.4.13.3.2.2
		-- 1.3.6.1.4.1.6296.101.4.13.3.2.2
		sleCfmMaControlStatus OBJECT-TYPE
			SYNTAX SleControlStatusType
			MAX-ACCESS read-only
			STATUS current
			DESCRIPTION
				"Description."
			::= { sleCfmMaControl 2 }

		
--   1.3.6.1.4.1.6296.101.4.13.3.2.3
-- 1.3.6.1.4.1.6296.101.4.13.3.2.3
		-- 1.3.6.1.4.1.6296.101.4.13.3.2.3
		sleCfmMaControlTimer OBJECT-TYPE
			SYNTAX Gauge32
			MAX-ACCESS read-write
			STATUS current
			DESCRIPTION
				"Description."
			::= { sleCfmMaControl 3 }

		
--   1.3.6.1.4.1.6296.101.4.13.3.2.4
-- 1.3.6.1.4.1.6296.101.4.13.3.2.4
		-- 1.3.6.1.4.1.6296.101.4.13.3.2.4
		sleCfmMaControlTimeStamp OBJECT-TYPE
			SYNTAX TimeTicks
			MAX-ACCESS read-only
			STATUS current
			DESCRIPTION
				"Description."
			::= { sleCfmMaControl 4 }

		
--   1.3.6.1.4.1.6296.101.4.13.3.2.5
-- 1.3.6.1.4.1.6296.101.4.13.3.2.5
		-- 1.3.6.1.4.1.6296.101.4.13.3.2.5
		sleCfmMaControlReqResult OBJECT-TYPE
			SYNTAX SleControlRequestResultType
			MAX-ACCESS read-only
			STATUS current
			DESCRIPTION
				"Description."
			::= { sleCfmMaControl 5 }

		
--   1.3.6.1.4.1.6296.101.4.13.3.2.6
-- 1.3.6.1.4.1.6296.101.4.13.3.2.6
		-- 1.3.6.1.4.1.6296.101.4.13.3.2.6
		sleCfmMaControlIndex OBJECT-TYPE
			SYNTAX Integer32 (1..65535)
			MAX-ACCESS read-write
			STATUS current
			DESCRIPTION
				"Indicates the MA's Index"
			::= { sleCfmMaControl 6 }

		
--   1.3.6.1.4.1.6296.101.4.13.3.2.7
-- 1.3.6.1.4.1.6296.101.4.13.3.2.7
		-- 1.3.6.1.4.1.6296.101.4.13.3.2.7
		sleCfmMaControlName OBJECT-TYPE
			SYNTAX OCTET STRING (SIZE (1..12))
			MAX-ACCESS read-write
			STATUS current
			DESCRIPTION
				"The MA's name."
			::= { sleCfmMaControl 7 }

		
--   1.3.6.1.4.1.6296.101.4.13.3.2.8
-- 1.3.6.1.4.1.6296.101.4.13.3.2.8
		-- 1.3.6.1.4.1.6296.101.4.13.3.2.8
		sleCfmMaControlVid OBJECT-TYPE
			SYNTAX Integer32 (1..4094)
			MAX-ACCESS read-write
			STATUS current
			DESCRIPTION
				"Indicates the MA's VID"
			::= { sleCfmMaControl 8 }

		
--   1.3.6.1.4.1.6296.101.4.13.3.2.9
-- 1.3.6.1.4.1.6296.101.4.13.3.2.9
		-- 1.3.6.1.4.1.6296.101.4.13.3.2.9
		sleCfmMaControlMdIndex OBJECT-TYPE
			SYNTAX Integer32 (1..65535)
			MAX-ACCESS read-write
			STATUS current
			DESCRIPTION
				"Indicates the MD's Index"
			::= { sleCfmMaControl 9 }

		
--   1.3.6.1.4.1.6296.101.4.13.3.2.10
-- 1.3.6.1.4.1.6296.101.4.13.3.2.10
		-- 1.3.6.1.4.1.6296.101.4.13.3.2.10
		sleCfmMaControlMepEnable OBJECT-TYPE
			SYNTAX INTEGER
				{
				disable(0),
				enable(1)
				}
			MAX-ACCESS read-write
			STATUS current
			DESCRIPTION
				"Enables/Disables CFM OAM for MEPs"
			::= { sleCfmMaControl 10 }

		
--   1.3.6.1.4.1.6296.101.4.13.3.2.11
-- 1.3.6.1.4.1.6296.101.4.13.3.2.11
		-- 1.3.6.1.4.1.6296.101.4.13.3.2.11
		sleCfmMaControlCcEnable OBJECT-TYPE
			SYNTAX INTEGER
				{
				disable(0),
				enable(1)
				}
			MAX-ACCESS read-write
			STATUS current
			DESCRIPTION
				"Enables/Disables MEPs to send Continuity Check messages"
			::= { sleCfmMaControl 11 }

		
--   1.3.6.1.4.1.6296.101.4.13.3.2.12
-- 1.3.6.1.4.1.6296.101.4.13.3.2.12
		-- 1.3.6.1.4.1.6296.101.4.13.3.2.12
		sleCfmMaControlCcInterval OBJECT-TYPE
			SYNTAX Integer32 (2..7)
			MAX-ACCESS read-write
			STATUS current
			DESCRIPTION
				"Indicates the interval between CCM transmissions"
			::= { sleCfmMaControl 12 }

		
--   1.3.6.1.4.1.6296.101.4.13.3.2.13
-- 1.3.6.1.4.1.6296.101.4.13.3.2.13
		-- 1.3.6.1.4.1.6296.101.4.13.3.2.13
		sleCfmMaControlCcPriority OBJECT-TYPE
			SYNTAX Integer32 (0..7)
			MAX-ACCESS read-write
			STATUS current
			DESCRIPTION
				"Indicates the CCM Priority"
			::= { sleCfmMaControl 13 }

		
--   1.3.6.1.4.1.6296.101.4.13.3.2.14
-- 1.3.6.1.4.1.6296.101.4.13.3.2.14
		-- 1.3.6.1.4.1.6296.101.4.13.3.2.14
		sleCfmMaControlCcLossThreshold OBJECT-TYPE
			SYNTAX Integer32 (2..255)
			MAX-ACCESS read-write
			STATUS current
			DESCRIPTION
				"Indicates the minimum number of CCMs that can be missed before declaring that a MEP is down"
			::= { sleCfmMaControl 14 }

		
--   1.3.6.1.4.1.6296.101.4.13.3.2.15
-- 1.3.6.1.4.1.6296.101.4.13.3.2.15
		-- 1.3.6.1.4.1.6296.101.4.13.3.2.15
		sleCfmMaControlFaultPriority OBJECT-TYPE
			SYNTAX INTEGER
				{
				rdiccm(1),
				macstatus(2),
				remoteccm(3),
				errorccm(4),
				xconccm(5)
				}
			MAX-ACCESS read-write
			STATUS current
			DESCRIPTION
				"Indicates the lowest priority for fault alarm"
			::= { sleCfmMaControl 15 }

		
--   1.3.6.1.4.1.6296.101.4.13.3.2.16
-- 1.3.6.1.4.1.6296.101.4.13.3.2.16
		-- 1.3.6.1.4.1.6296.101.4.13.3.2.16
		sleCfmMaControlFaultKeepTime OBJECT-TYPE
			SYNTAX Integer32 (0..1023)
			MAX-ACCESS read-write
			STATUS current
			DESCRIPTION
				"Indicates the keep time for the fault alarm"
			::= { sleCfmMaControl 16 }

		
--   1.3.6.1.4.1.6296.101.4.13.3.2.17
-- 1.3.6.1.4.1.6296.101.4.13.3.2.17
		-- 1.3.6.1.4.1.6296.101.4.13.3.2.17
		sleCfmMaControlFaultClearTime OBJECT-TYPE
			SYNTAX Integer32 (0..1023)
			MAX-ACCESS read-write
			STATUS current
			DESCRIPTION
				"Indicates the clear time for the fault alarm"
			::= { sleCfmMaControl 17 }

		
--   1.3.6.1.4.1.6296.101.4.13.3.2.18
-- 1.3.6.1.4.1.6296.101.4.13.3.2.18
		-- 1.3.6.1.4.1.6296.101.4.13.3.2.18
		sleCfmMaControlXcheckEnable OBJECT-TYPE
			SYNTAX INTEGER
				{
				disable(0),
				enable(1)
				}
			MAX-ACCESS read-write
			STATUS current
			DESCRIPTION
				"Enables/Disables CFM cross-check for a specific MEG"
			::= { sleCfmMaControl 18 }

		
--   1.3.6.1.4.1.6296.101.4.13.3.3
-- 1.3.6.1.4.1.6296.101.4.13.3.3
		-- 1.3.6.1.4.1.6296.101.4.13.3.3
		sleCfmMaNotification OBJECT IDENTIFIER ::= { sleCfmMa 3 }

		
--   1.3.6.1.4.1.6296.101.4.13.3.3.1
-- 1.3.6.1.4.1.6296.101.4.13.3.3.1
		-- 1.3.6.1.4.1.6296.101.4.13.3.3.1
		sleCfmMaCreated NOTIFICATION-TYPE
			OBJECTS { sleCfmMaControlRequest, sleCfmMaControlTimeStamp, sleCfmMaControlReqResult, sleCfmMaControlName, sleCfmMaControlMdIndex, 
				sleCfmMaControlVid }
			STATUS current
			DESCRIPTION 
				"createCfmMa"
			::= { sleCfmMaNotification 1 }

		
--   1.3.6.1.4.1.6296.101.4.13.3.3.2
-- 1.3.6.1.4.1.6296.101.4.13.3.3.2
		-- 1.3.6.1.4.1.6296.101.4.13.3.3.2
		sleCfmMaDeleted NOTIFICATION-TYPE
			OBJECTS { sleCfmMaControlRequest, sleCfmMaControlTimeStamp, sleCfmMaControlReqResult, sleCfmMaControlName, sleCfmMaControlMdIndex
				 }
			STATUS current
			DESCRIPTION 
				"deleteCfmMa"
			::= { sleCfmMaNotification 2 }

		
--   1.3.6.1.4.1.6296.101.4.13.3.3.3
-- 1.3.6.1.4.1.6296.101.4.13.3.3.3
		-- 1.3.6.1.4.1.6296.101.4.13.3.3.3
		sleCfmMaMepEnableChanged NOTIFICATION-TYPE
			OBJECTS { sleCfmMaControlRequest, sleCfmMaControlTimeStamp, sleCfmMaControlReqResult, sleCfmMaControlIndex, sleCfmMaControlMdIndex, 
				sleCfmMaControlMepEnable }
			STATUS current
			DESCRIPTION 
				"setCfmMaMepEnable"
			::= { sleCfmMaNotification 3 }

		
--   1.3.6.1.4.1.6296.101.4.13.3.3.4
-- 1.3.6.1.4.1.6296.101.4.13.3.3.4
		-- 1.3.6.1.4.1.6296.101.4.13.3.3.4
		sleCfmMaCcEnableChanged NOTIFICATION-TYPE
			OBJECTS { sleCfmMaControlRequest, sleCfmMaControlTimeStamp, sleCfmMaControlReqResult, sleCfmMaControlIndex, sleCfmMaControlMdIndex, 
				sleCfmMaControlCcEnable }
			STATUS current
			DESCRIPTION 
				"setCfmMaCcEnable"
			::= { sleCfmMaNotification 4 }

		
--   1.3.6.1.4.1.6296.101.4.13.3.3.5
-- 1.3.6.1.4.1.6296.101.4.13.3.3.5
		-- 1.3.6.1.4.1.6296.101.4.13.3.3.5
		sleCfmMaCcProfileChanged NOTIFICATION-TYPE
			OBJECTS { sleCfmMaControlRequest, sleCfmMaControlTimeStamp, sleCfmMaControlReqResult, sleCfmMaControlIndex, sleCfmMaControlMdIndex, 
				sleCfmMaControlCcInterval, sleCfmMaControlCcPriority, sleCfmMaControlCcLossThreshold }
			STATUS current
			DESCRIPTION 
				"setCfmMaCcProfile"
			::= { sleCfmMaNotification 5 }

		
--   1.3.6.1.4.1.6296.101.4.13.3.3.6
-- 1.3.6.1.4.1.6296.101.4.13.3.3.6
		-- 1.3.6.1.4.1.6296.101.4.13.3.3.6
		sleCfmMaFaultProfileChanged NOTIFICATION-TYPE
			OBJECTS { sleCfmMaControlRequest, sleCfmMaControlTimeStamp, sleCfmMaControlReqResult, sleCfmMaControlIndex, sleCfmMaControlMdIndex, 
				sleCfmMaControlFaultPriority, sleCfmMaControlFaultKeepTime, sleCfmMaControlFaultClearTime }
			STATUS current
			DESCRIPTION 
				"setCfmMaFaultProfile"
			::= { sleCfmMaNotification 6 }

		
--   1.3.6.1.4.1.6296.101.4.13.3.3.7
-- 1.3.6.1.4.1.6296.101.4.13.3.3.7
		-- 1.3.6.1.4.1.6296.101.4.13.3.3.7
		sleCfmMaXcheckEnableChanged NOTIFICATION-TYPE
			OBJECTS { sleCfmMaControlRequest, sleCfmMaControlTimeStamp, sleCfmMaControlReqResult, sleCfmMaControlIndex, sleCfmMaControlMdIndex, 
				sleCfmMaControlXcheckEnable }
			STATUS current
			DESCRIPTION 
				"setCfmMaXcheckEnable"
			::= { sleCfmMaNotification 7 }

		
--   1.3.6.1.4.1.6296.101.4.13.4
-- 1.3.6.1.4.1.6296.101.4.13.4
		-- 1.3.6.1.4.1.6296.101.4.13.4
		sleCfmMep OBJECT IDENTIFIER ::= { sleCfmOam 4 }

		
--   1.3.6.1.4.1.6296.101.4.13.4.1
-- 1.3.6.1.4.1.6296.101.4.13.4.1
		-- 1.3.6.1.4.1.6296.101.4.13.4.1
		sleCfmMepTable OBJECT-TYPE
			SYNTAX SEQUENCE OF SleCfmMepEntry
			MAX-ACCESS not-accessible
			STATUS current
			DESCRIPTION
				"Description."
			::= { sleCfmMep 1 }

		
--   1.3.6.1.4.1.6296.101.4.13.4.1.1
-- 1.3.6.1.4.1.6296.101.4.13.4.1.1
		-- 1.3.6.1.4.1.6296.101.4.13.4.1.1
		sleCfmMepEntry OBJECT-TYPE
			SYNTAX SleCfmMepEntry
			MAX-ACCESS not-accessible
			STATUS current
			DESCRIPTION
				"Description."
			INDEX { sleCfmMdIndex, sleCfmMaIndex, sleCfmMepIfIndex }
			::= { sleCfmMepTable 1 }

		
		SleCfmMepEntry ::=
			SEQUENCE { 
				sleCfmMepIdentifier
					Integer32,
				sleCfmMepIfIndex
					Integer32,
				sleCfmMepDirection
					INTEGER,
				sleCfmMepEnable
					INTEGER,
				sleCfmMepFngState
					INTEGER,
				sleCfmMepCcEnable
					INTEGER,
				sleCfmMepMacAddress
					OCTET STRING,
				sleCfmMepCcPriority
					Integer32,
				sleCfmMepFaultPriority
					INTEGER,
				sleCfmMepFaultKeepTime
					Integer32,
				sleCfmMepFaultClearTime
					Integer32,
				sleCfmMepHighestPrDefect
					INTEGER,
				sleCfmMepDefects
					BITS,
				sleCfmMepCciSentCcms
					Counter32,
				sleCfmMepNextLbmTransId
					Integer32,
				sleCfmMepLbrIn
					Counter32,
				sleCfmMepLbrInOutOfOrder
					Counter32,
				sleCfmMepLtmNextSeqNumber
					Integer32,
				sleCfmMepUnexpLtrIn
					Counter32
			 }

--   1.3.6.1.4.1.6296.101.4.13.4.1.1.1
-- 1.3.6.1.4.1.6296.101.4.13.4.1.1.1
		-- 1.3.6.1.4.1.6296.101.4.13.4.1.1.1
		sleCfmMepIdentifier OBJECT-TYPE
			SYNTAX Integer32 (1..8191)
			MAX-ACCESS read-only
			STATUS current
			DESCRIPTION
				"MEP Id"
			::= { sleCfmMepEntry 1 }

		
--   1.3.6.1.4.1.6296.101.4.13.4.1.1.2
-- 1.3.6.1.4.1.6296.101.4.13.4.1.1.2
		-- 1.3.6.1.4.1.6296.101.4.13.4.1.1.2
		sleCfmMepIfIndex OBJECT-TYPE
			SYNTAX Integer32 (1..8191)
			MAX-ACCESS read-only
			STATUS current
			DESCRIPTION
				"Brige Port Index whitch the MEP is attached"
			::= { sleCfmMepEntry 2 }

		
--   1.3.6.1.4.1.6296.101.4.13.4.1.1.3
-- 1.3.6.1.4.1.6296.101.4.13.4.1.1.3
		-- 1.3.6.1.4.1.6296.101.4.13.4.1.1.3
		sleCfmMepDirection OBJECT-TYPE
			SYNTAX INTEGER
				{
				down(0),
				up(1)
				}
			MAX-ACCESS read-only
			STATUS current
			DESCRIPTION
				"The direction in which the MEP faces on the Bridge port"
			::= { sleCfmMepEntry 3 }

		
--   1.3.6.1.4.1.6296.101.4.13.4.1.1.4
-- 1.3.6.1.4.1.6296.101.4.13.4.1.1.4
		-- 1.3.6.1.4.1.6296.101.4.13.4.1.1.4
		sleCfmMepEnable OBJECT-TYPE
			SYNTAX INTEGER
				{
				disable(0),
				enable(1)
				}
			MAX-ACCESS read-only
			STATUS current
			DESCRIPTION
				"Administrative state of the MEP"
			::= { sleCfmMepEntry 4 }

		
--   1.3.6.1.4.1.6296.101.4.13.4.1.1.5
-- 1.3.6.1.4.1.6296.101.4.13.4.1.1.5
		-- 1.3.6.1.4.1.6296.101.4.13.4.1.1.5
		sleCfmMepFngState OBJECT-TYPE
			SYNTAX INTEGER
				{
				reset(1),
				defect(2),
				reportDefect(3),
				defectReported(4),
				defectCearing(5),
				defectCleared(6)
				}
			MAX-ACCESS read-only
			STATUS current
			DESCRIPTION
				"Current state of the MEP Fault Notification Generator State Machine"
			::= { sleCfmMepEntry 5 }

		
--   1.3.6.1.4.1.6296.101.4.13.4.1.1.6
-- 1.3.6.1.4.1.6296.101.4.13.4.1.1.6
		-- 1.3.6.1.4.1.6296.101.4.13.4.1.1.6
		sleCfmMepCcEnable OBJECT-TYPE
			SYNTAX INTEGER
				{
				disable(0),
				enable(1)
				}
			MAX-ACCESS read-only
			STATUS current
			DESCRIPTION
				"If set to true, the MEP will generate CCM messages"
			::= { sleCfmMepEntry 6 }

		
--   1.3.6.1.4.1.6296.101.4.13.4.1.1.7
-- 1.3.6.1.4.1.6296.101.4.13.4.1.1.7
		-- 1.3.6.1.4.1.6296.101.4.13.4.1.1.7
		sleCfmMepMacAddress OBJECT-TYPE
			SYNTAX OCTET STRING (SIZE (6))
			MAX-ACCESS read-only
			STATUS current
			DESCRIPTION
				"MAC address of the MEP"
			::= { sleCfmMepEntry 7 }

		
--   1.3.6.1.4.1.6296.101.4.13.4.1.1.8
-- 1.3.6.1.4.1.6296.101.4.13.4.1.1.8
		-- 1.3.6.1.4.1.6296.101.4.13.4.1.1.8
		sleCfmMepCcPriority OBJECT-TYPE
			SYNTAX Integer32 (0..7)
			MAX-ACCESS read-only
			STATUS current
			DESCRIPTION
				"Indicates the CCM Priority"
			::= { sleCfmMepEntry 8 }

		
--   1.3.6.1.4.1.6296.101.4.13.4.1.1.9
-- 1.3.6.1.4.1.6296.101.4.13.4.1.1.9
		-- 1.3.6.1.4.1.6296.101.4.13.4.1.1.9
		sleCfmMepFaultPriority OBJECT-TYPE
			SYNTAX INTEGER
				{
				rdiccm(1),
				macstatus(2),
				remoteccm(3),
				errorccm(4),
				xconccm(5)
				}
			MAX-ACCESS read-only
			STATUS current
			DESCRIPTION
				"An integer value specifying the lowest priority defect that is allowed to generate fault alarm"
			::= { sleCfmMepEntry 9 }

		
--   1.3.6.1.4.1.6296.101.4.13.4.1.1.10
-- 1.3.6.1.4.1.6296.101.4.13.4.1.1.10
		-- 1.3.6.1.4.1.6296.101.4.13.4.1.1.10
		sleCfmMepFaultKeepTime OBJECT-TYPE
			SYNTAX Integer32 (0..1023)
			MAX-ACCESS read-only
			STATUS current
			DESCRIPTION
				"The time that defects must be present before a Fault Alarm is issued"
			::= { sleCfmMepEntry 10 }

		
--   1.3.6.1.4.1.6296.101.4.13.4.1.1.11
-- 1.3.6.1.4.1.6296.101.4.13.4.1.1.11
		-- 1.3.6.1.4.1.6296.101.4.13.4.1.1.11
		sleCfmMepFaultClearTime OBJECT-TYPE
			SYNTAX Integer32 (0..1023)
			MAX-ACCESS read-only
			STATUS current
			DESCRIPTION
				"The time that defects must be absent before resetting a Fault Alarm"
			::= { sleCfmMepEntry 11 }

		
--   1.3.6.1.4.1.6296.101.4.13.4.1.1.12
-- 1.3.6.1.4.1.6296.101.4.13.4.1.1.12
		-- 1.3.6.1.4.1.6296.101.4.13.4.1.1.12
		sleCfmMepHighestPrDefect OBJECT-TYPE
			SYNTAX INTEGER
				{
				rdiccm(1),
				macstatus(2),
				remoteccm(3),
				errorccm(4),
				xconccm(5)
				}
			MAX-ACCESS read-only
			STATUS current
			DESCRIPTION
				"The highest priority defect that has been present since the MEPs Fault Notification Generator State Machine was last in the FNG_RESET state"
			::= { sleCfmMepEntry 12 }

		
--   1.3.6.1.4.1.6296.101.4.13.4.1.1.13
-- 1.3.6.1.4.1.6296.101.4.13.4.1.1.13
		-- 1.3.6.1.4.1.6296.101.4.13.4.1.1.13
		sleCfmMepDefects OBJECT-TYPE
			SYNTAX BITS
				{
				rdiccm(0),
				macstatus(1),
				remoteccm(2),
				errorccm(3),
				xconccm(4)
				}
			MAX-ACCESS read-only
			STATUS current
			DESCRIPTION
				"A vector of Boolean defect conditions"
			::= { sleCfmMepEntry 13 }

		
--   1.3.6.1.4.1.6296.101.4.13.4.1.1.14
-- 1.3.6.1.4.1.6296.101.4.13.4.1.1.14
		-- 1.3.6.1.4.1.6296.101.4.13.4.1.1.14
		sleCfmMepCciSentCcms OBJECT-TYPE
			SYNTAX Counter32
			MAX-ACCESS read-only
			STATUS current
			DESCRIPTION
				"Total number of Continuity Check messages transmitted"
			::= { sleCfmMepEntry 14 }

		
--   1.3.6.1.4.1.6296.101.4.13.4.1.1.15
-- 1.3.6.1.4.1.6296.101.4.13.4.1.1.15
		-- 1.3.6.1.4.1.6296.101.4.13.4.1.1.15
		sleCfmMepNextLbmTransId OBJECT-TYPE
			SYNTAX Integer32
			MAX-ACCESS read-only
			STATUS current
			DESCRIPTION
				"Next sequence number/transaction identifier to be sent in a Loopback message"
			::= { sleCfmMepEntry 15 }

		
--   1.3.6.1.4.1.6296.101.4.13.4.1.1.16
-- 1.3.6.1.4.1.6296.101.4.13.4.1.1.16
		-- 1.3.6.1.4.1.6296.101.4.13.4.1.1.16
		sleCfmMepLbrIn OBJECT-TYPE
			SYNTAX Counter32
			MAX-ACCESS read-only
			STATUS current
			DESCRIPTION
				"Total number of valid, in-order Loopback Replies received"
			::= { sleCfmMepEntry 16 }

		
--   1.3.6.1.4.1.6296.101.4.13.4.1.1.17
-- 1.3.6.1.4.1.6296.101.4.13.4.1.1.17
		-- 1.3.6.1.4.1.6296.101.4.13.4.1.1.17
		sleCfmMepLbrInOutOfOrder OBJECT-TYPE
			SYNTAX Counter32
			MAX-ACCESS read-only
			STATUS current
			DESCRIPTION
				"The total number of valid, out-of-order Loopback Replies received"
			::= { sleCfmMepEntry 17 }

		
--   1.3.6.1.4.1.6296.101.4.13.4.1.1.18
-- 1.3.6.1.4.1.6296.101.4.13.4.1.1.18
		-- 1.3.6.1.4.1.6296.101.4.13.4.1.1.18
		sleCfmMepLtmNextSeqNumber OBJECT-TYPE
			SYNTAX Integer32
			MAX-ACCESS read-only
			STATUS current
			DESCRIPTION
				"Next transaction identifier/sequence number to be sent in a Linktrace message."
			::= { sleCfmMepEntry 18 }

		
--   1.3.6.1.4.1.6296.101.4.13.4.1.1.19
-- 1.3.6.1.4.1.6296.101.4.13.4.1.1.19
		-- 1.3.6.1.4.1.6296.101.4.13.4.1.1.19
		sleCfmMepUnexpLtrIn OBJECT-TYPE
			SYNTAX Counter32
			MAX-ACCESS read-only
			STATUS current
			DESCRIPTION
				"The total number of unexpected LTRs received"
			::= { sleCfmMepEntry 19 }

		
--   1.3.6.1.4.1.6296.101.4.13.4.2
-- 1.3.6.1.4.1.6296.101.4.13.4.2
		-- 1.3.6.1.4.1.6296.101.4.13.4.2
		sleCfmMepControl OBJECT IDENTIFIER ::= { sleCfmMep 2 }

		
--   1.3.6.1.4.1.6296.101.4.13.4.2.1
-- 1.3.6.1.4.1.6296.101.4.13.4.2.1
		-- 1.3.6.1.4.1.6296.101.4.13.4.2.1
		sleCfmMepControlRequest OBJECT-TYPE
			SYNTAX INTEGER
				{
				createCfmMep(1),
				deleteCfmMep(2),
				setCfmMepEnable(3),
				setCfmMepCcEnable(4),
				setCfmMepCcProfile(5),
				setCfmMepFaultProfile(6),
				transmitCfmLbm(7),
				transmitCfmLtm(8)
				}
			MAX-ACCESS read-write
			STATUS current
			DESCRIPTION
				"Description."
			::= { sleCfmMepControl 1 }

		
--   1.3.6.1.4.1.6296.101.4.13.4.2.2
-- 1.3.6.1.4.1.6296.101.4.13.4.2.2
		-- 1.3.6.1.4.1.6296.101.4.13.4.2.2
		sleCfmMepControlStatus OBJECT-TYPE
			SYNTAX SleControlStatusType
			MAX-ACCESS read-only
			STATUS current
			DESCRIPTION
				"Description."
			::= { sleCfmMepControl 2 }

		
--   1.3.6.1.4.1.6296.101.4.13.4.2.3
-- 1.3.6.1.4.1.6296.101.4.13.4.2.3
		-- 1.3.6.1.4.1.6296.101.4.13.4.2.3
		sleCfmMepControlTimer OBJECT-TYPE
			SYNTAX Gauge32
			MAX-ACCESS read-write
			STATUS current
			DESCRIPTION
				"Description."
			::= { sleCfmMepControl 3 }

		
--   1.3.6.1.4.1.6296.101.4.13.4.2.4
-- 1.3.6.1.4.1.6296.101.4.13.4.2.4
		-- 1.3.6.1.4.1.6296.101.4.13.4.2.4
		sleCfmMepControlTimeStamp OBJECT-TYPE
			SYNTAX TimeTicks
			MAX-ACCESS read-only
			STATUS current
			DESCRIPTION
				"Description."
			::= { sleCfmMepControl 4 }

		
--   1.3.6.1.4.1.6296.101.4.13.4.2.5
-- 1.3.6.1.4.1.6296.101.4.13.4.2.5
		-- 1.3.6.1.4.1.6296.101.4.13.4.2.5
		sleCfmMepControlReqResult OBJECT-TYPE
			SYNTAX SleControlRequestResultType
			MAX-ACCESS read-only
			STATUS current
			DESCRIPTION
				"Description."
			::= { sleCfmMepControl 5 }

		
--   1.3.6.1.4.1.6296.101.4.13.4.2.6
-- 1.3.6.1.4.1.6296.101.4.13.4.2.6
		-- 1.3.6.1.4.1.6296.101.4.13.4.2.6
		sleCfmMepControlIdentifier OBJECT-TYPE
			SYNTAX Integer32 (1..8191)
			MAX-ACCESS read-write
			STATUS current
			DESCRIPTION
				"MEP Id"
			::= { sleCfmMepControl 6 }

		
--   1.3.6.1.4.1.6296.101.4.13.4.2.7
-- 1.3.6.1.4.1.6296.101.4.13.4.2.7
		-- 1.3.6.1.4.1.6296.101.4.13.4.2.7
		sleCfmMepControlMdIndex OBJECT-TYPE
			SYNTAX Integer32 (1..65535)
			MAX-ACCESS read-write
			STATUS current
			DESCRIPTION
				"A index of MD table"
			::= { sleCfmMepControl 7 }

		
--   1.3.6.1.4.1.6296.101.4.13.4.2.8
-- 1.3.6.1.4.1.6296.101.4.13.4.2.8
		-- 1.3.6.1.4.1.6296.101.4.13.4.2.8
		sleCfmMepControlMaIndex OBJECT-TYPE
			SYNTAX Integer32 (1..65535)
			MAX-ACCESS read-write
			STATUS current
			DESCRIPTION
				"The MA's Index"
			::= { sleCfmMepControl 8 }

		
--   1.3.6.1.4.1.6296.101.4.13.4.2.9
-- 1.3.6.1.4.1.6296.101.4.13.4.2.9
		-- 1.3.6.1.4.1.6296.101.4.13.4.2.9
		sleCfmMepControlIfIndex OBJECT-TYPE
			SYNTAX Integer32
			MAX-ACCESS read-write
			STATUS current
			DESCRIPTION
				"Bridge Port Index whitch the MEP is attached"
			::= { sleCfmMepControl 9 }

		
--   1.3.6.1.4.1.6296.101.4.13.4.2.10
-- 1.3.6.1.4.1.6296.101.4.13.4.2.10
		-- 1.3.6.1.4.1.6296.101.4.13.4.2.10
		sleCfmMepControlDirection OBJECT-TYPE
			SYNTAX INTEGER
				{
				down(0),
				up(1)
				}
			MAX-ACCESS read-write
			STATUS current
			DESCRIPTION
				"The direction in which the MEP faces on the Bridge port"
			::= { sleCfmMepControl 10 }

		
--   1.3.6.1.4.1.6296.101.4.13.4.2.11
-- 1.3.6.1.4.1.6296.101.4.13.4.2.11
		-- 1.3.6.1.4.1.6296.101.4.13.4.2.11
		sleCfmMepControlEnable OBJECT-TYPE
			SYNTAX INTEGER
				{
				disable(0),
				enable(1)
				}
			MAX-ACCESS read-write
			STATUS current
			DESCRIPTION
				"Administrative state of the MEP"
			::= { sleCfmMepControl 11 }

		
--   1.3.6.1.4.1.6296.101.4.13.4.2.12
-- 1.3.6.1.4.1.6296.101.4.13.4.2.12
		-- 1.3.6.1.4.1.6296.101.4.13.4.2.12
		sleCfmMepControlCcEnable OBJECT-TYPE
			SYNTAX INTEGER
				{
				disable(0),
				enable(1)
				}
			MAX-ACCESS read-write
			STATUS current
			DESCRIPTION
				"If set to true, the MEP will generate CCM messages"
			::= { sleCfmMepControl 12 }

		
--   1.3.6.1.4.1.6296.101.4.13.4.2.13
-- 1.3.6.1.4.1.6296.101.4.13.4.2.13
		-- 1.3.6.1.4.1.6296.101.4.13.4.2.13
		sleCfmMepControlCcPriority OBJECT-TYPE
			SYNTAX Integer32 (0..7)
			MAX-ACCESS read-write
			STATUS current
			DESCRIPTION
				"Indicates the CCM Priority"
			::= { sleCfmMepControl 13 }

		
--   1.3.6.1.4.1.6296.101.4.13.4.2.14
-- 1.3.6.1.4.1.6296.101.4.13.4.2.14
		-- 1.3.6.1.4.1.6296.101.4.13.4.2.14
		sleCfmMepControlFaultPriority OBJECT-TYPE
			SYNTAX INTEGER
				{
				rdiccm(1),
				macstatus(2),
				remoteccm(3),
				errorccm(4),
				xconccm(5)
				}
			MAX-ACCESS read-write
			STATUS current
			DESCRIPTION
				"An integer value specifying the lowest priority defect that is allowed to generate fault alarm"
			::= { sleCfmMepControl 14 }

		
--   1.3.6.1.4.1.6296.101.4.13.4.2.15
-- 1.3.6.1.4.1.6296.101.4.13.4.2.15
		-- 1.3.6.1.4.1.6296.101.4.13.4.2.15
		sleCfmMepControlFaultKeepTime OBJECT-TYPE
			SYNTAX Integer32 (0..1023)
			MAX-ACCESS read-write
			STATUS current
			DESCRIPTION
				"The time that defects must be present before a Fault Alarm is issued"
			::= { sleCfmMepControl 15 }

		
--   1.3.6.1.4.1.6296.101.4.13.4.2.16
-- 1.3.6.1.4.1.6296.101.4.13.4.2.16
		-- 1.3.6.1.4.1.6296.101.4.13.4.2.16
		sleCfmMepControlFaultClearTime OBJECT-TYPE
			SYNTAX Integer32 (0..1023)
			MAX-ACCESS read-write
			STATUS current
			DESCRIPTION
				"The time that defects must be absent before resetting a Fault Alarm"
			::= { sleCfmMepControl 16 }

		
--   1.3.6.1.4.1.6296.101.4.13.4.2.17
-- 1.3.6.1.4.1.6296.101.4.13.4.2.17
		-- 1.3.6.1.4.1.6296.101.4.13.4.2.17
		sleCfmMepControlTransmitLbmDestMacAddress OBJECT-TYPE
			SYNTAX OCTET STRING (SIZE (6))
			MAX-ACCESS read-write
			STATUS current
			DESCRIPTION
				"The Target MAC Address Field to be transmitted"
			::= { sleCfmMepControl 17 }

		
--   1.3.6.1.4.1.6296.101.4.13.4.2.18
-- 1.3.6.1.4.1.6296.101.4.13.4.2.18
		-- 1.3.6.1.4.1.6296.101.4.13.4.2.18
		sleCfmMepControlTransmitLbmDestMepId OBJECT-TYPE
			SYNTAX Integer32 (1..8191)
			MAX-ACCESS read-write
			STATUS current
			DESCRIPTION
				"The Maintenance association End Point Identifier of another MEP in the same Maintenance Association to which the LBM is to be sent"
			::= { sleCfmMepControl 18 }

		
--   1.3.6.1.4.1.6296.101.4.13.4.2.19
-- 1.3.6.1.4.1.6296.101.4.13.4.2.19
		-- 1.3.6.1.4.1.6296.101.4.13.4.2.19
		sleCfmMepControlTransmitLbmDestIsMepId OBJECT-TYPE
			SYNTAX INTEGER
				{
				false(0),
				true(1)
				}
			MAX-ACCESS read-write
			STATUS current
			DESCRIPTION
				"True indicates that MEPID of the target MEP is used for  Loopback transmission"
			::= { sleCfmMepControl 19 }

		
--   1.3.6.1.4.1.6296.101.4.13.4.2.20
-- 1.3.6.1.4.1.6296.101.4.13.4.2.20
		-- 1.3.6.1.4.1.6296.101.4.13.4.2.20
		sleCfmMepControlTransmitLbmCount OBJECT-TYPE
			SYNTAX Integer32 (1..6000)
			MAX-ACCESS read-write
			STATUS current
			DESCRIPTION
				"The number of Loopback messages to be transmitted"
			::= { sleCfmMepControl 20 }

		
--   1.3.6.1.4.1.6296.101.4.13.4.2.21
-- 1.3.6.1.4.1.6296.101.4.13.4.2.21
		-- 1.3.6.1.4.1.6296.101.4.13.4.2.21
		sleCfmMepControlTransmitLbmInterval OBJECT-TYPE
			SYNTAX Integer32 (2..4)
			MAX-ACCESS read-write
			STATUS current
			DESCRIPTION
				"Indicates the interval for sending LBM"
			::= { sleCfmMepControl 21 }

		
--   1.3.6.1.4.1.6296.101.4.13.4.2.22
-- 1.3.6.1.4.1.6296.101.4.13.4.2.22
		-- 1.3.6.1.4.1.6296.101.4.13.4.2.22
		sleCfmMepControlTransmitLbmTimeout OBJECT-TYPE
			SYNTAX Integer32 (1..1000)
			MAX-ACCESS read-write
			STATUS current
			DESCRIPTION
				"Indicates the waiting time for receiving the expected LBR"
			::= { sleCfmMepControl 22 }

		
--   1.3.6.1.4.1.6296.101.4.13.4.2.23
-- 1.3.6.1.4.1.6296.101.4.13.4.2.23
		-- 1.3.6.1.4.1.6296.101.4.13.4.2.23
		sleCfmMepControlTransmitLbmPriority OBJECT-TYPE
			SYNTAX Integer32 (0..7)
			MAX-ACCESS read-write
			STATUS current
			DESCRIPTION
				"Priority. 3 bit value to be used in the VLAN tag"
			::= { sleCfmMepControl 23 }

		
--   1.3.6.1.4.1.6296.101.4.13.4.2.24
-- 1.3.6.1.4.1.6296.101.4.13.4.2.24
		-- 1.3.6.1.4.1.6296.101.4.13.4.2.24
		sleCfmMepControlTransmitLtmTargetMacAddress OBJECT-TYPE
			SYNTAX OCTET STRING (SIZE (6))
			MAX-ACCESS read-write
			STATUS current
			DESCRIPTION
				"The Target MAC Address Field to be transmitted: A unicast  destination MAC address."
			::= { sleCfmMepControl 24 }

		
--   1.3.6.1.4.1.6296.101.4.13.4.2.25
-- 1.3.6.1.4.1.6296.101.4.13.4.2.25
		-- 1.3.6.1.4.1.6296.101.4.13.4.2.25
		sleCfmMepControlTransmitLtmTargetMepId OBJECT-TYPE
			SYNTAX Integer32 (1..8191)
			MAX-ACCESS read-write
			STATUS current
			DESCRIPTION
				"An indication of the Target MAC Address Field to be  transmitted"
			::= { sleCfmMepControl 25 }

		
--   1.3.6.1.4.1.6296.101.4.13.4.2.26
-- 1.3.6.1.4.1.6296.101.4.13.4.2.26
		-- 1.3.6.1.4.1.6296.101.4.13.4.2.26
		sleCfmMepControlTransmitLtmTargetIsMepId OBJECT-TYPE
			SYNTAX INTEGER
				{
				false(0),
				true(1)
				}
			MAX-ACCESS read-write
			STATUS current
			DESCRIPTION
				"True indicates that MEPID of the target MEP is used for  Linktrace transmission."
			::= { sleCfmMepControl 26 }

		
--   1.3.6.1.4.1.6296.101.4.13.4.2.27
-- 1.3.6.1.4.1.6296.101.4.13.4.2.27
		-- 1.3.6.1.4.1.6296.101.4.13.4.2.27
		sleCfmMepControlTransmitLtmFlags OBJECT-TYPE
			SYNTAX BITS { useFDBonly(0) }
			MAX-ACCESS read-write
			STATUS current
			DESCRIPTION
				"The flags field for LTMs transmitted by the MEP"
			::= { sleCfmMepControl 27 }

		
--   1.3.6.1.4.1.6296.101.4.13.4.2.28
-- 1.3.6.1.4.1.6296.101.4.13.4.2.28
		-- 1.3.6.1.4.1.6296.101.4.13.4.2.28
		sleCfmMepControlTransmitLtmTtl OBJECT-TYPE
			SYNTAX Integer32 (1..64)
			MAX-ACCESS read-write
			STATUS current
			DESCRIPTION
				"The LTM TTL field"
			::= { sleCfmMepControl 28 }

		
--   1.3.6.1.4.1.6296.101.4.13.4.3
-- 1.3.6.1.4.1.6296.101.4.13.4.3
		-- 1.3.6.1.4.1.6296.101.4.13.4.3
		sleCfmMepNotification OBJECT IDENTIFIER ::= { sleCfmMep 3 }

		
--   1.3.6.1.4.1.6296.101.4.13.4.3.1
-- 1.3.6.1.4.1.6296.101.4.13.4.3.1
		-- 1.3.6.1.4.1.6296.101.4.13.4.3.1
		sleCfmMepCreated NOTIFICATION-TYPE
			OBJECTS { sleCfmMepControlRequest, sleCfmMepControlTimeStamp, sleCfmMepControlReqResult, sleCfmMepControlIdentifier, sleCfmMepControlMdIndex, 
				sleCfmMepControlMaIndex, sleCfmMepControlIfIndex, sleCfmMepControlDirection }
			STATUS current
			DESCRIPTION 
				"createCfmMep"
			::= { sleCfmMepNotification 1 }

		
--   1.3.6.1.4.1.6296.101.4.13.4.3.2
-- 1.3.6.1.4.1.6296.101.4.13.4.3.2
		-- 1.3.6.1.4.1.6296.101.4.13.4.3.2
		sleCfmMepDeleted NOTIFICATION-TYPE
			OBJECTS { sleCfmMepControlRequest, sleCfmMepControlTimeStamp, sleCfmMepControlReqResult, sleCfmMepControlIdentifier, sleCfmMepControlMdIndex, 
				sleCfmMepControlMaIndex }
			STATUS current
			DESCRIPTION 
				"deleteCfmMep"
			::= { sleCfmMepNotification 2 }

		
--   1.3.6.1.4.1.6296.101.4.13.4.3.3
-- 1.3.6.1.4.1.6296.101.4.13.4.3.3
		-- 1.3.6.1.4.1.6296.101.4.13.4.3.3
		sleCfmMepEnableChanged NOTIFICATION-TYPE
			OBJECTS { sleCfmMepControlRequest, sleCfmMepControlTimeStamp, sleCfmMepControlReqResult, sleCfmMepControlIdentifier, sleCfmMepControlMdIndex, 
				sleCfmMepControlMaIndex, sleCfmMepControlEnable }
			STATUS current
			DESCRIPTION 
				"setCfmMepEnable"
			::= { sleCfmMepNotification 3 }

		
--   1.3.6.1.4.1.6296.101.4.13.4.3.4
-- 1.3.6.1.4.1.6296.101.4.13.4.3.4
		-- 1.3.6.1.4.1.6296.101.4.13.4.3.4
		sleCfmMepCcEnableChanged NOTIFICATION-TYPE
			OBJECTS { sleCfmMepControlRequest, sleCfmMepControlTimeStamp, sleCfmMepControlReqResult, sleCfmMepControlIdentifier, sleCfmMepControlMdIndex, 
				sleCfmMepControlMaIndex, sleCfmMepControlCcEnable }
			STATUS current
			DESCRIPTION 
				"setCfmMepCcEnable"
			::= { sleCfmMepNotification 4 }

		
--   1.3.6.1.4.1.6296.101.4.13.4.3.5
-- 1.3.6.1.4.1.6296.101.4.13.4.3.5
		-- 1.3.6.1.4.1.6296.101.4.13.4.3.5
		sleCfmMepCcProfileChanged NOTIFICATION-TYPE
			OBJECTS { sleCfmMepControlRequest, sleCfmMepControlTimeStamp, sleCfmMepControlReqResult, sleCfmMepControlIdentifier, sleCfmMepControlMdIndex, 
				sleCfmMepControlMaIndex, sleCfmMdControlCcPriority }
			STATUS current
			DESCRIPTION 
				"setCfmMepCcProfile"
			::= { sleCfmMepNotification 5 }

		
--   1.3.6.1.4.1.6296.101.4.13.4.3.6
-- 1.3.6.1.4.1.6296.101.4.13.4.3.6
		-- 1.3.6.1.4.1.6296.101.4.13.4.3.6
		sleCfmMepFaultProfileChanged NOTIFICATION-TYPE
			OBJECTS { sleCfmMepControlRequest, sleCfmMepControlTimeStamp, sleCfmMepControlReqResult, sleCfmMepControlIdentifier, sleCfmMepControlMdIndex, 
				sleCfmMepControlMaIndex, sleCfmMepControlFaultPriority, sleCfmMepControlFaultKeepTime, sleCfmMepControlFaultClearTime }
			STATUS current
			DESCRIPTION 
				"setCfmMepFaultProfile"
			::= { sleCfmMepNotification 6 }

		
--   1.3.6.1.4.1.6296.101.4.13.5
-- 1.3.6.1.4.1.6296.101.4.13.5
		-- 1.3.6.1.4.1.6296.101.4.13.5
		sleCfmMip OBJECT IDENTIFIER ::= { sleCfmOam 5 }

		
--   1.3.6.1.4.1.6296.101.4.13.5.1
-- 1.3.6.1.4.1.6296.101.4.13.5.1
		-- 1.3.6.1.4.1.6296.101.4.13.5.1
		sleCfmMipTable OBJECT-TYPE
			SYNTAX SEQUENCE OF SleCfmMipEntry
			MAX-ACCESS not-accessible
			STATUS current
			DESCRIPTION
				"Description."
			::= { sleCfmMip 1 }

		
--   1.3.6.1.4.1.6296.101.4.13.5.1.1
-- 1.3.6.1.4.1.6296.101.4.13.5.1.1
		-- 1.3.6.1.4.1.6296.101.4.13.5.1.1
		sleCfmMipEntry OBJECT-TYPE
			SYNTAX SleCfmMipEntry
			MAX-ACCESS not-accessible
			STATUS current
			DESCRIPTION
				"Description."
			INDEX { sleCfmMipPort }
			::= { sleCfmMipTable 1 }

		
		SleCfmMipEntry ::=
			SEQUENCE { 
				sleCfmMipPort
					Integer32,
				sleCfmMipLevel
					Integer32,
				sleCfmMipType
					INTEGER
			 }

--   1.3.6.1.4.1.6296.101.4.13.5.1.1.1
-- 1.3.6.1.4.1.6296.101.4.13.5.1.1.1
		-- 1.3.6.1.4.1.6296.101.4.13.5.1.1.1
		sleCfmMipPort OBJECT-TYPE
			SYNTAX Integer32 (1..65535)
			MAX-ACCESS read-only
			STATUS current
			DESCRIPTION
				"Indicates the port number"
			::= { sleCfmMipEntry 1 }

		
--   1.3.6.1.4.1.6296.101.4.13.5.1.1.2
-- 1.3.6.1.4.1.6296.101.4.13.5.1.1.2
		-- 1.3.6.1.4.1.6296.101.4.13.5.1.1.2
		sleCfmMipLevel OBJECT-TYPE
			SYNTAX Integer32 (0..7)
			MAX-ACCESS read-only
			STATUS current
			DESCRIPTION
				"Indicates the MIP's level"
			::= { sleCfmMipEntry 2 }

		
--   1.3.6.1.4.1.6296.101.4.13.5.1.1.3
-- 1.3.6.1.4.1.6296.101.4.13.5.1.1.3
		-- 1.3.6.1.4.1.6296.101.4.13.5.1.1.3
		sleCfmMipType OBJECT-TYPE
			SYNTAX INTEGER
				{
				static(1),
				dynamic(2)
				}
			MAX-ACCESS read-only
			STATUS current
			DESCRIPTION
				"Indicate the MIP’s type"
			::= { sleCfmMipEntry 3 }

		
--   1.3.6.1.4.1.6296.101.4.13.5.2
-- 1.3.6.1.4.1.6296.101.4.13.5.2
		-- 1.3.6.1.4.1.6296.101.4.13.5.2
		sleCfmMipControl OBJECT IDENTIFIER ::= { sleCfmMip 2 }

		
--   1.3.6.1.4.1.6296.101.4.13.5.2.1
-- 1.3.6.1.4.1.6296.101.4.13.5.2.1
		-- 1.3.6.1.4.1.6296.101.4.13.5.2.1
		sleCfmMipControlRequest OBJECT-TYPE
			SYNTAX INTEGER
				{
				createCfmMip(1),
				deleteCfmMip(2)
				}
			MAX-ACCESS read-write
			STATUS current
			DESCRIPTION
				"Description."
			::= { sleCfmMipControl 1 }

		
--   1.3.6.1.4.1.6296.101.4.13.5.2.2
-- 1.3.6.1.4.1.6296.101.4.13.5.2.2
		-- 1.3.6.1.4.1.6296.101.4.13.5.2.2
		sleCfmMipControlStatus OBJECT-TYPE
			SYNTAX SleControlStatusType
			MAX-ACCESS read-only
			STATUS current
			DESCRIPTION
				"Description."
			::= { sleCfmMipControl 2 }

		
--   1.3.6.1.4.1.6296.101.4.13.5.2.3
-- 1.3.6.1.4.1.6296.101.4.13.5.2.3
		-- 1.3.6.1.4.1.6296.101.4.13.5.2.3
		sleCfmMipControlTimer OBJECT-TYPE
			SYNTAX Gauge32
			MAX-ACCESS read-write
			STATUS current
			DESCRIPTION
				"Description."
			::= { sleCfmMipControl 3 }

		
--   1.3.6.1.4.1.6296.101.4.13.5.2.4
-- 1.3.6.1.4.1.6296.101.4.13.5.2.4
		-- 1.3.6.1.4.1.6296.101.4.13.5.2.4
		sleCfmMipControlTimeStamp OBJECT-TYPE
			SYNTAX TimeTicks
			MAX-ACCESS read-only
			STATUS current
			DESCRIPTION
				"Description."
			::= { sleCfmMipControl 4 }

		
--   1.3.6.1.4.1.6296.101.4.13.5.2.5
-- 1.3.6.1.4.1.6296.101.4.13.5.2.5
		-- 1.3.6.1.4.1.6296.101.4.13.5.2.5
		sleCfmMipControlReqResult OBJECT-TYPE
			SYNTAX SleControlRequestResultType
			MAX-ACCESS read-only
			STATUS current
			DESCRIPTION
				"Description."
			::= { sleCfmMipControl 5 }

		
--   1.3.6.1.4.1.6296.101.4.13.5.2.6
-- 1.3.6.1.4.1.6296.101.4.13.5.2.6
		-- 1.3.6.1.4.1.6296.101.4.13.5.2.6
		sleCfmMipControlPort OBJECT-TYPE
			SYNTAX Integer32 (1..65535)
			MAX-ACCESS read-write
			STATUS current
			DESCRIPTION
				"Indicates the port number"
			::= { sleCfmMipControl 6 }

		
--   1.3.6.1.4.1.6296.101.4.13.5.2.7
-- 1.3.6.1.4.1.6296.101.4.13.5.2.7
		-- 1.3.6.1.4.1.6296.101.4.13.5.2.7
		sleCfmMipControlLevel OBJECT-TYPE
			SYNTAX Integer32 (0..7)
			MAX-ACCESS read-write
			STATUS current
			DESCRIPTION
				"Indicates the MIP's level"
			::= { sleCfmMipControl 7 }

		
--   1.3.6.1.4.1.6296.101.4.13.5.3
-- 1.3.6.1.4.1.6296.101.4.13.5.3
		-- 1.3.6.1.4.1.6296.101.4.13.5.3
		sleCfmMipNotification OBJECT IDENTIFIER ::= { sleCfmMip 3 }

		
--   1.3.6.1.4.1.6296.101.4.13.5.3.1
-- 1.3.6.1.4.1.6296.101.4.13.5.3.1
		-- 1.3.6.1.4.1.6296.101.4.13.5.3.1
		sleCfmMipCreated NOTIFICATION-TYPE
			OBJECTS { sleCfmMipControlRequest, sleCfmMipControlTimeStamp, sleCfmMipControlReqResult, sleCfmMipControlPort, sleCfmMipControlLevel
				 }
			STATUS current
			DESCRIPTION 
				"createCfmMip"
			::= { sleCfmMipNotification 1 }

		
--   1.3.6.1.4.1.6296.101.4.13.5.3.2
-- 1.3.6.1.4.1.6296.101.4.13.5.3.2
		-- 1.3.6.1.4.1.6296.101.4.13.5.3.2
		sleCfmMipDeleted NOTIFICATION-TYPE
			OBJECTS { sleCfmMipControlRequest, sleCfmMipControlTimeStamp, sleCfmMipControlReqResult, sleCfmMipControlPort }
			STATUS current
			DESCRIPTION 
				"deleteCfmMip"
			::= { sleCfmMipNotification 2 }

		
--   1.3.6.1.4.1.6296.101.4.13.6
-- 1.3.6.1.4.1.6296.101.4.13.6
		-- 1.3.6.1.4.1.6296.101.4.13.6
		sleCfmXcheck OBJECT IDENTIFIER ::= { sleCfmOam 6 }

		
--   1.3.6.1.4.1.6296.101.4.13.6.1
-- 1.3.6.1.4.1.6296.101.4.13.6.1
		-- 1.3.6.1.4.1.6296.101.4.13.6.1
		sleCfmXcheckTable OBJECT-TYPE
			SYNTAX SEQUENCE OF SleCfmXcheckEntry
			MAX-ACCESS not-accessible
			STATUS current
			DESCRIPTION
				"Description."
			::= { sleCfmXcheck 1 }

		
--   1.3.6.1.4.1.6296.101.4.13.6.1.1
-- 1.3.6.1.4.1.6296.101.4.13.6.1.1
		-- 1.3.6.1.4.1.6296.101.4.13.6.1.1
		sleCfmXcheckEntry OBJECT-TYPE
			SYNTAX SleCfmXcheckEntry
			MAX-ACCESS not-accessible
			STATUS current
			DESCRIPTION
				"Description."
			INDEX { sleCfmMdIndex, sleCfmMaIndex, sleCfmXcheckMepIdentifier }
			::= { sleCfmXcheckTable 1 }

		
		SleCfmXcheckEntry ::=
			SEQUENCE { 
				sleCfmXcheckMepIdentifier
					Integer32,
				sleCfmXcheckMepState
					INTEGER
			 }

--   1.3.6.1.4.1.6296.101.4.13.6.1.1.1
-- 1.3.6.1.4.1.6296.101.4.13.6.1.1.1
		-- 1.3.6.1.4.1.6296.101.4.13.6.1.1.1
		sleCfmXcheckMepIdentifier OBJECT-TYPE
			SYNTAX Integer32 (1..8191)
			MAX-ACCESS read-only
			STATUS current
			DESCRIPTION
				"Indicates the remote MEP's Id"
			::= { sleCfmXcheckEntry 1 }

		
--   1.3.6.1.4.1.6296.101.4.13.6.1.1.2
-- 1.3.6.1.4.1.6296.101.4.13.6.1.1.2
		-- 1.3.6.1.4.1.6296.101.4.13.6.1.1.2
		sleCfmXcheckMepState OBJECT-TYPE
			SYNTAX INTEGER
				{
				unknown(0),
				missing(1),
				up(2)
				}
			MAX-ACCESS read-only
			STATUS current
			DESCRIPTION
				"Indicates the cross-check MEP’s state"
			::= { sleCfmXcheckEntry 2 }

		
--   1.3.6.1.4.1.6296.101.4.13.6.2
-- 1.3.6.1.4.1.6296.101.4.13.6.2
		-- 1.3.6.1.4.1.6296.101.4.13.6.2
		sleCfmXcheckControl OBJECT IDENTIFIER ::= { sleCfmXcheck 2 }

		
--   1.3.6.1.4.1.6296.101.4.13.6.2.1
-- 1.3.6.1.4.1.6296.101.4.13.6.2.1
		-- 1.3.6.1.4.1.6296.101.4.13.6.2.1
		sleCfmXcheckControlRequest OBJECT-TYPE
			SYNTAX INTEGER
				{
				createCfmXcheckMep(1),
				deleteCfmXcheckMep(2)
				}
			MAX-ACCESS read-write
			STATUS current
			DESCRIPTION
				"Description."
			::= { sleCfmXcheckControl 1 }

		
--   1.3.6.1.4.1.6296.101.4.13.6.2.2
-- 1.3.6.1.4.1.6296.101.4.13.6.2.2
		-- 1.3.6.1.4.1.6296.101.4.13.6.2.2
		sleCfmXcheckControlStatus OBJECT-TYPE
			SYNTAX SleControlStatusType
			MAX-ACCESS read-only
			STATUS current
			DESCRIPTION
				"Description."
			::= { sleCfmXcheckControl 2 }

		
--   1.3.6.1.4.1.6296.101.4.13.6.2.3
-- 1.3.6.1.4.1.6296.101.4.13.6.2.3
		-- 1.3.6.1.4.1.6296.101.4.13.6.2.3
		sleCfmXcheckControlTimer OBJECT-TYPE
			SYNTAX Gauge32
			MAX-ACCESS read-write
			STATUS current
			DESCRIPTION
				"Description."
			::= { sleCfmXcheckControl 3 }

		
--   1.3.6.1.4.1.6296.101.4.13.6.2.4
-- 1.3.6.1.4.1.6296.101.4.13.6.2.4
		-- 1.3.6.1.4.1.6296.101.4.13.6.2.4
		sleCfmXcheckControlTimeStamp OBJECT-TYPE
			SYNTAX TimeTicks
			MAX-ACCESS read-only
			STATUS current
			DESCRIPTION
				"Description."
			::= { sleCfmXcheckControl 4 }

		
--   1.3.6.1.4.1.6296.101.4.13.6.2.5
-- 1.3.6.1.4.1.6296.101.4.13.6.2.5
		-- 1.3.6.1.4.1.6296.101.4.13.6.2.5
		sleCfmXcheckControlReqResult OBJECT-TYPE
			SYNTAX SleControlRequestResultType
			MAX-ACCESS read-only
			STATUS current
			DESCRIPTION
				"Description."
			::= { sleCfmXcheckControl 5 }

		
--   1.3.6.1.4.1.6296.101.4.13.6.2.6
-- 1.3.6.1.4.1.6296.101.4.13.6.2.6
		-- 1.3.6.1.4.1.6296.101.4.13.6.2.6
		sleCfmXcheckControlMepIdentifier OBJECT-TYPE
			SYNTAX Integer32 (1..8191)
			MAX-ACCESS read-write
			STATUS current
			DESCRIPTION
				"Indicates the remote MEP's Id"
			::= { sleCfmXcheckControl 6 }

		
--   1.3.6.1.4.1.6296.101.4.13.6.2.7
-- 1.3.6.1.4.1.6296.101.4.13.6.2.7
		-- 1.3.6.1.4.1.6296.101.4.13.6.2.7
		sleCfmXcheckControlMdIndex OBJECT-TYPE
			SYNTAX Integer32 (1..65535)
			MAX-ACCESS read-write
			STATUS current
			DESCRIPTION
				"Indicates the MD’s Index"
			::= { sleCfmXcheckControl 7 }

		
--   1.3.6.1.4.1.6296.101.4.13.6.2.8
-- 1.3.6.1.4.1.6296.101.4.13.6.2.8
		-- 1.3.6.1.4.1.6296.101.4.13.6.2.8
		sleCfmXcheckControlMaIndex OBJECT-TYPE
			SYNTAX Integer32 (1..65535)
			MAX-ACCESS read-write
			STATUS current
			DESCRIPTION
				"Indicates the MA's Index"
			::= { sleCfmXcheckControl 8 }

		
--   1.3.6.1.4.1.6296.101.4.13.6.3
-- 1.3.6.1.4.1.6296.101.4.13.6.3
		-- 1.3.6.1.4.1.6296.101.4.13.6.3
		sleCfmXcheckNotification OBJECT IDENTIFIER ::= { sleCfmXcheck 3 }

		
--   1.3.6.1.4.1.6296.101.4.13.6.3.1
-- 1.3.6.1.4.1.6296.101.4.13.6.3.1
		-- 1.3.6.1.4.1.6296.101.4.13.6.3.1
		sleCfmXcheckMepCreated NOTIFICATION-TYPE
			OBJECTS { sleCfmXcheckControlRequest, sleCfmXcheckControlTimeStamp, sleCfmXcheckControlReqResult, sleCfmXcheckControlMepIdentifier, sleCfmXcheckControlMdIndex, 
				sleCfmXcheckControlMaIndex }
			STATUS current
			DESCRIPTION 
				"createCfmXcheckMep"
			::= { sleCfmXcheckNotification 1 }

		
--   1.3.6.1.4.1.6296.101.4.13.6.3.2
-- 1.3.6.1.4.1.6296.101.4.13.6.3.2
		-- 1.3.6.1.4.1.6296.101.4.13.6.3.2
		sleCfmXcheckMepDeleted NOTIFICATION-TYPE
			OBJECTS { sleCfmXcheckControlRequest, sleCfmXcheckControlTimeStamp, sleCfmXcheckControlReqResult, sleCfmXcheckControlMepIdentifier, sleCfmXcheckControlMdIndex, 
				sleCfmXcheckControlMaIndex }
			STATUS current
			DESCRIPTION 
				"deleteCfmXcheckMep"
			::= { sleCfmXcheckNotification 2 }

		
--   1.3.6.1.4.1.6296.101.4.13.7
-- 1.3.6.1.4.1.6296.101.4.13.7
		-- 1.3.6.1.4.1.6296.101.4.13.7
		sleCfmRmep OBJECT IDENTIFIER ::= { sleCfmOam 7 }

		
--   1.3.6.1.4.1.6296.101.4.13.7.1
-- 1.3.6.1.4.1.6296.101.4.13.7.1
		-- 1.3.6.1.4.1.6296.101.4.13.7.1
		sleCfmRmepTable OBJECT-TYPE
			SYNTAX SEQUENCE OF SleCfmRmepEntry
			MAX-ACCESS not-accessible
			STATUS current
			DESCRIPTION
				"Description."
			::= { sleCfmRmep 1 }

		
--   1.3.6.1.4.1.6296.101.4.13.7.1.1
-- 1.3.6.1.4.1.6296.101.4.13.7.1.1
		-- 1.3.6.1.4.1.6296.101.4.13.7.1.1
		sleCfmRmepEntry OBJECT-TYPE
			SYNTAX SleCfmRmepEntry
			MAX-ACCESS not-accessible
			STATUS current
			DESCRIPTION
				"Description."
			INDEX { sleCfmMdIndex, sleCfmMaIndex, sleCfmMepIdentifier, sleCfmRmepIdentifier }
			::= { sleCfmRmepTable 1 }

		
		SleCfmRmepEntry ::=
			SEQUENCE { 
				sleCfmRmepIdentifier
					Integer32,
				sleCfmRmepState
					INTEGER,
				sleCfmRmepMacAddress
					OCTET STRING,
				sleCfmRmepIfIndex
					Integer32,
				sleCfmRmepRdi
					INTEGER,
				sleCfmRmepPortStatus
					INTEGER,
				sleCfmRmepInterfaceStatus
					INTEGER
			 }

--   1.3.6.1.4.1.6296.101.4.13.7.1.1.1
-- 1.3.6.1.4.1.6296.101.4.13.7.1.1.1
		-- 1.3.6.1.4.1.6296.101.4.13.7.1.1.1
		sleCfmRmepIdentifier OBJECT-TYPE
			SYNTAX Integer32 (1..8191)
			MAX-ACCESS read-only
			STATUS current
			DESCRIPTION
				"Indicates the remote MEP's Id"
			::= { sleCfmRmepEntry 1 }

		
--   1.3.6.1.4.1.6296.101.4.13.7.1.1.2
-- 1.3.6.1.4.1.6296.101.4.13.7.1.1.2
		-- 1.3.6.1.4.1.6296.101.4.13.7.1.1.2
		sleCfmRmepState OBJECT-TYPE
			SYNTAX INTEGER
				{
				idle(1),
				start(2),
				failed(3),
				ok(4)
				}
			MAX-ACCESS read-only
			STATUS current
			DESCRIPTION
				"Indicates the operational state of the remote MEP State machines"
			::= { sleCfmRmepEntry 2 }

		
--   1.3.6.1.4.1.6296.101.4.13.7.1.1.3
-- 1.3.6.1.4.1.6296.101.4.13.7.1.1.3
		-- 1.3.6.1.4.1.6296.101.4.13.7.1.1.3
		sleCfmRmepMacAddress OBJECT-TYPE
			SYNTAX OCTET STRING (SIZE (6))
			MAX-ACCESS read-only
			STATUS current
			DESCRIPTION
				"Indicates the MAC address of the remote MEP"
			::= { sleCfmRmepEntry 3 }

		
--   1.3.6.1.4.1.6296.101.4.13.7.1.1.4
-- 1.3.6.1.4.1.6296.101.4.13.7.1.1.4
		-- 1.3.6.1.4.1.6296.101.4.13.7.1.1.4
		sleCfmRmepIfIndex OBJECT-TYPE
			SYNTAX Integer32
			MAX-ACCESS read-only
			STATUS current
			DESCRIPTION
				"Indicates the port number of the remote MEP"
			::= { sleCfmRmepEntry 4 }

		
--   
-- 
-- 1.3.6.1.4.1.6296.101.4.13.7.1.1.5
-- 1.3.6.1.4.1.6296.101.4.13.7.1.1.5
		-- 1.3.6.1.4.1.6296.101.4.13.7.1.1.5
		sleCfmRmepRdi OBJECT-TYPE
			SYNTAX INTEGER
				{
				false(0),
				true(1)
				}
			MAX-ACCESS read-only
			STATUS current
			DESCRIPTION
				"Indicates State of the RDI bit in the last received CCM (true for RDI=1), or false if none has been received"
			::= { sleCfmRmepEntry 5 }

		
--   1.3.6.1.4.1.6296.101.4.13.7.1.1.6
-- 1.3.6.1.4.1.6296.101.4.13.7.1.1.6
		-- 1.3.6.1.4.1.6296.101.4.13.7.1.1.6
		sleCfmRmepPortStatus OBJECT-TYPE
			SYNTAX INTEGER
				{
				none(1),
				up(2),
				down(3)
				}
			MAX-ACCESS read-only
			STATUS current
			DESCRIPTION
				"Indicates the Port status of the remote MEP"
			::= { sleCfmRmepEntry 6 }

		
--   1.3.6.1.4.1.6296.101.4.13.7.1.1.7
-- 1.3.6.1.4.1.6296.101.4.13.7.1.1.7
		-- 1.3.6.1.4.1.6296.101.4.13.7.1.1.7
		sleCfmRmepInterfaceStatus OBJECT-TYPE
			SYNTAX INTEGER
				{
				none(1),
				up(2),
				down(3)
				}
			MAX-ACCESS read-only
			STATUS current
			DESCRIPTION
				"Indicates the interface status of the remote MEP"
			::= { sleCfmRmepEntry 7 }

		
--   1.3.6.1.4.1.6296.101.4.13.8
-- 1.3.6.1.4.1.6296.101.4.13.8
		-- 1.3.6.1.4.1.6296.101.4.13.8
		sleCfmLtr OBJECT IDENTIFIER ::= { sleCfmOam 8 }

		
--   1.3.6.1.4.1.6296.101.4.13.8.1
-- 1.3.6.1.4.1.6296.101.4.13.8.1
		-- 1.3.6.1.4.1.6296.101.4.13.8.1
		sleCfmLtrTable OBJECT-TYPE
			SYNTAX SEQUENCE OF SleCfmLtrEntry
			MAX-ACCESS not-accessible
			STATUS current
			DESCRIPTION
				"Description."
			::= { sleCfmLtr 1 }

		
--   1.3.6.1.4.1.6296.101.4.13.8.1.1
-- 1.3.6.1.4.1.6296.101.4.13.8.1.1
		-- 1.3.6.1.4.1.6296.101.4.13.8.1.1
		sleCfmLtrEntry OBJECT-TYPE
			SYNTAX SleCfmLtrEntry
			MAX-ACCESS not-accessible
			STATUS current
			DESCRIPTION
				"Description."
			INDEX { sleCfmMdIndex, sleCfmMaIndex, sleCfmMepIdentifier, sleCfmLtrSeqNumber, sleCfmLtrReceiveOrder
				 }
			::= { sleCfmLtrTable 1 }

		
		SleCfmLtrEntry ::=
			SEQUENCE { 
				sleCfmLtrSeqNumber
					Integer32,
				sleCfmLtrReceiveOrder
					Integer32,
				sleCfmLtrTtl
					Integer32,
				sleCfmLtrForwarded
					INTEGER,
				sleCfmLtrTerminalMep
					INTEGER,
				sleCfmLtrLastEgressIdentifier
					OCTET STRING,
				sleCfmLtrNextEgressIdentifier
					OCTET STRING,
				sleCfmLtrRelay
					INTEGER,
				sleCfmLtrIngress
					INTEGER,
				sleCfmLtrIngressMac
					OCTET STRING,
				sleCfmLtrIngressPort
					Integer32,
				sleCfmLtrEgress
					INTEGER,
				sleCfmLtrEgressMac
					OCTET STRING,
				sleCfmLtrEgressPort
					Integer32
			 }

--   1.3.6.1.4.1.6296.101.4.13.8.1.1.1
-- 1.3.6.1.4.1.6296.101.4.13.8.1.1.1
		-- 1.3.6.1.4.1.6296.101.4.13.8.1.1.1
		sleCfmLtrSeqNumber OBJECT-TYPE
			SYNTAX Integer32 (1..65535)
			MAX-ACCESS read-only
			STATUS current
			DESCRIPTION
				"Indicates the LTM Transaction Identifier returned from a previous Transmit Linktrace Message command,
				indicating the LTM entry to which the LTR entries will be attached
				"
			::= { sleCfmLtrEntry 1 }

		
--   1.3.6.1.4.1.6296.101.4.13.8.1.1.2
-- 1.3.6.1.4.1.6296.101.4.13.8.1.1.2
		-- 1.3.6.1.4.1.6296.101.4.13.8.1.1.2
		sleCfmLtrReceiveOrder OBJECT-TYPE
			SYNTAX Integer32 (1..65535)
			MAX-ACCESS read-only
			STATUS current
			DESCRIPTION
				"Indicates an index to distinguish among multiple LTRs with the same LTR Transaction Identifier field value"
			::= { sleCfmLtrEntry 2 }

		
--   1.3.6.1.4.1.6296.101.4.13.8.1.1.3
-- 1.3.6.1.4.1.6296.101.4.13.8.1.1.3
		-- 1.3.6.1.4.1.6296.101.4.13.8.1.1.3
		sleCfmLtrTtl OBJECT-TYPE
			SYNTAX Integer32 (1..64)
			MAX-ACCESS read-only
			STATUS current
			DESCRIPTION
				"Indicates TTL field value for a returned LTR."
			::= { sleCfmLtrEntry 3 }

		
--   1.3.6.1.4.1.6296.101.4.13.8.1.1.4
-- 1.3.6.1.4.1.6296.101.4.13.8.1.1.4
		-- 1.3.6.1.4.1.6296.101.4.13.8.1.1.4
		sleCfmLtrForwarded OBJECT-TYPE
			SYNTAX INTEGER
				{
				false(0),
				true(1)
				}
			MAX-ACCESS read-only
			STATUS current
			DESCRIPTION
				"Indicates if a LTM was forwarded by the responding MP, as returned in the 'FwdYes' flag of the flags field."
			::= { sleCfmLtrEntry 4 }

		
--   1.3.6.1.4.1.6296.101.4.13.8.1.1.5
-- 1.3.6.1.4.1.6296.101.4.13.8.1.1.5
		-- 1.3.6.1.4.1.6296.101.4.13.8.1.1.5
		sleCfmLtrTerminalMep OBJECT-TYPE
			SYNTAX INTEGER
				{
				false(0),
				true(1)
				}
			MAX-ACCESS read-only
			STATUS current
			DESCRIPTION
				"Indicates a boolean value stating whether the forwarded LTM reached a MEP enclosing its MA, as returned in the Terminal MEP flag of the Flags field.  	"
			::= { sleCfmLtrEntry 5 }

		
--   1.3.6.1.4.1.6296.101.4.13.8.1.1.6
-- 1.3.6.1.4.1.6296.101.4.13.8.1.1.6
		-- 1.3.6.1.4.1.6296.101.4.13.8.1.1.6
		sleCfmLtrLastEgressIdentifier OBJECT-TYPE
			SYNTAX OCTET STRING (SIZE (8))
			MAX-ACCESS read-only
			STATUS current
			DESCRIPTION
				"Identifies the MEP Linktrace Initiator that originated, or the Linktrace Responder that forwarded, the LTM to which this LTR is the response"
			::= { sleCfmLtrEntry 6 }

		
--   1.3.6.1.4.1.6296.101.4.13.8.1.1.7
-- 1.3.6.1.4.1.6296.101.4.13.8.1.1.7
		-- 1.3.6.1.4.1.6296.101.4.13.8.1.1.7
		sleCfmLtrNextEgressIdentifier OBJECT-TYPE
			SYNTAX OCTET STRING (SIZE (8))
			MAX-ACCESS read-only
			STATUS current
			DESCRIPTION
				"Identifies the Linktrace Responder that transmitted this LTR, and can forward the LTM to the next hop."
			::= { sleCfmLtrEntry 7 }

		
--   1.3.6.1.4.1.6296.101.4.13.8.1.1.8
-- 1.3.6.1.4.1.6296.101.4.13.8.1.1.8
		-- 1.3.6.1.4.1.6296.101.4.13.8.1.1.8
		sleCfmLtrRelay OBJECT-TYPE
			SYNTAX INTEGER
				{
				rlyHit(1),
				rlyFDB(2),
				rlyMPDB(3)
				}
			MAX-ACCESS read-only
			STATUS current
			DESCRIPTION
				"Indicates the value returned in the Ingress Action Field of the LTM"
			::= { sleCfmLtrEntry 8 }

		
--   1.3.6.1.4.1.6296.101.4.13.8.1.1.9
-- 1.3.6.1.4.1.6296.101.4.13.8.1.1.9
		-- 1.3.6.1.4.1.6296.101.4.13.8.1.1.9
		sleCfmLtrIngress OBJECT-TYPE
			SYNTAX INTEGER
				{
				ingNoTlv(0),
				ingOK(1),
				ingDown(2),
				ingBlocked(3),
				ingVid(4)
				}
			MAX-ACCESS read-only
			STATUS current
			DESCRIPTION
				"Indicates the value returned in the Ingress Action Field of the LTM"
			::= { sleCfmLtrEntry 9 }

		
--   1.3.6.1.4.1.6296.101.4.13.8.1.1.10
-- 1.3.6.1.4.1.6296.101.4.13.8.1.1.10
		-- 1.3.6.1.4.1.6296.101.4.13.8.1.1.10
		sleCfmLtrIngressMac OBJECT-TYPE
			SYNTAX OCTET STRING (SIZE (6))
			MAX-ACCESS read-only
			STATUS current
			DESCRIPTION
				"Indicates MAC address returned in the ingress MAC address field."
			::= { sleCfmLtrEntry 10 }

		
--   1.3.6.1.4.1.6296.101.4.13.8.1.1.11
-- 1.3.6.1.4.1.6296.101.4.13.8.1.1.11
		-- 1.3.6.1.4.1.6296.101.4.13.8.1.1.11
		sleCfmLtrIngressPort OBJECT-TYPE
			SYNTAX Integer32
			MAX-ACCESS read-only
			STATUS current
			DESCRIPTION
				"Indicates Ingress Port ID"
			::= { sleCfmLtrEntry 11 }

		
--   1.3.6.1.4.1.6296.101.4.13.8.1.1.12
-- 1.3.6.1.4.1.6296.101.4.13.8.1.1.12
		-- 1.3.6.1.4.1.6296.101.4.13.8.1.1.12
		sleCfmLtrEgress OBJECT-TYPE
			SYNTAX INTEGER
				{
				egrNoTlv(0),
				egrOK(1),
				egrDown(2),
				egrBlocked(3),
				egrVid(4)
				}
			MAX-ACCESS read-only
			STATUS current
			DESCRIPTION
				"Indicates the value returned in the Egress Action Field of the LTM"
			::= { sleCfmLtrEntry 12 }

		
--   1.3.6.1.4.1.6296.101.4.13.8.1.1.13
-- 1.3.6.1.4.1.6296.101.4.13.8.1.1.13
		-- 1.3.6.1.4.1.6296.101.4.13.8.1.1.13
		sleCfmLtrEgressMac OBJECT-TYPE
			SYNTAX OCTET STRING (SIZE (6))
			MAX-ACCESS read-only
			STATUS current
			DESCRIPTION
				"Indicates MAC address returned in the egress MAC address field."
			::= { sleCfmLtrEntry 13 }

		
--   1.3.6.1.4.1.6296.101.4.13.8.1.1.14
-- 1.3.6.1.4.1.6296.101.4.13.8.1.1.14
		-- 1.3.6.1.4.1.6296.101.4.13.8.1.1.14
		sleCfmLtrEgressPort OBJECT-TYPE
			SYNTAX Integer32
			MAX-ACCESS read-only
			STATUS current
			DESCRIPTION
				"Indicates Egress Port ID"
			::= { sleCfmLtrEntry 14 }

		
--   1.3.6.1.4.1.6296.101.4.13.9
-- 1.3.6.1.4.1.6296.101.4.13.9
		-- 1.3.6.1.4.1.6296.101.4.13.9
		sleCfmConfigError OBJECT IDENTIFIER ::= { sleCfmOam 9 }

		
--   1.3.6.1.4.1.6296.101.4.13.9.1
-- 1.3.6.1.4.1.6296.101.4.13.9.1
		-- 1.3.6.1.4.1.6296.101.4.13.9.1
		sleCfmConfigErrorTable OBJECT-TYPE
			SYNTAX SEQUENCE OF SleCfmConfigErrorEntry
			MAX-ACCESS not-accessible
			STATUS current
			DESCRIPTION
				"Description."
			::= { sleCfmConfigError 1 }

		
--   1.3.6.1.4.1.6296.101.4.13.9.1.1
-- 1.3.6.1.4.1.6296.101.4.13.9.1.1
		-- 1.3.6.1.4.1.6296.101.4.13.9.1.1
		sleCfmConfigErrorEntry OBJECT-TYPE
			SYNTAX SleCfmConfigErrorEntry
			MAX-ACCESS not-accessible
			STATUS current
			DESCRIPTION
				"Description."
			INDEX { sleCfmConfigErrorVid, sleCfmConfigErrorIfIndex }
			::= { sleCfmConfigErrorTable 1 }

		
		SleCfmConfigErrorEntry ::=
			SEQUENCE { 
				sleCfmConfigErrorVid
					Integer32,
				sleCfmConfigErrorIfIndex
					Integer32,
				sleCfmConfigErrorType
					BITS
			 }

--   1.3.6.1.4.1.6296.101.4.13.9.1.1.1
-- 1.3.6.1.4.1.6296.101.4.13.9.1.1.1
		-- 1.3.6.1.4.1.6296.101.4.13.9.1.1.1
		sleCfmConfigErrorVid OBJECT-TYPE
			SYNTAX Integer32 (1..4094)
			MAX-ACCESS read-only
			STATUS current
			DESCRIPTION
				"Indicates the Configuration Error VLAN Identifier"
			::= { sleCfmConfigErrorEntry 1 }

		
--   1.3.6.1.4.1.6296.101.4.13.9.1.1.2
-- 1.3.6.1.4.1.6296.101.4.13.9.1.1.2
		-- 1.3.6.1.4.1.6296.101.4.13.9.1.1.2
		sleCfmConfigErrorIfIndex OBJECT-TYPE
			SYNTAX Integer32 (1..65535)
			MAX-ACCESS read-only
			STATUS current
			DESCRIPTION
				"Indicates the Configuration Error Port Number"
			::= { sleCfmConfigErrorEntry 2 }

		
--   1.3.6.1.4.1.6296.101.4.13.9.1.1.3
-- 1.3.6.1.4.1.6296.101.4.13.9.1.1.3
		-- 1.3.6.1.4.1.6296.101.4.13.9.1.1.3
		sleCfmConfigErrorType OBJECT-TYPE
			SYNTAX BITS
				{
				cfmleak(0),
				conflictingVids(1),
				excessiveLevels(2),
				overlappedLevels(3)
				}
			MAX-ACCESS read-only
			STATUS current
			DESCRIPTION
				"Indicates the Configuration Error Type"
			::= { sleCfmConfigErrorEntry 3 }

		
--   1.3.6.1.4.1.6296.101.4.13.10
-- 1.3.6.1.4.1.6296.101.4.13.10
		-- 1.3.6.1.4.1.6296.101.4.13.10
		sleCfmMipCcdb OBJECT IDENTIFIER ::= { sleCfmOam 10 }

		
--   1.3.6.1.4.1.6296.101.4.13.10.1
-- 1.3.6.1.4.1.6296.101.4.13.10.1
		-- 1.3.6.1.4.1.6296.101.4.13.10.1
		sleCfmMipCcdbTable OBJECT-TYPE
			SYNTAX SEQUENCE OF SleCfmMipCcdbEntry
			MAX-ACCESS not-accessible
			STATUS current
			DESCRIPTION
				"Description."
			::= { sleCfmMipCcdb 1 }

		
--   1.3.6.1.4.1.6296.101.4.13.10.1.1
-- 1.3.6.1.4.1.6296.101.4.13.10.1.1
		-- 1.3.6.1.4.1.6296.101.4.13.10.1.1
		sleCfmMipCcdbEntry OBJECT-TYPE
			SYNTAX SleCfmMipCcdbEntry
			MAX-ACCESS not-accessible
			STATUS current
			DESCRIPTION
				"Description."
			INDEX { sleCfmMipCcdbIndex }
			::= { sleCfmMipCcdbTable 1 }

		
		SleCfmMipCcdbEntry ::=
			SEQUENCE { 
				sleCfmMipCcdbIndex
					Integer32,
				sleCfmMipCcdbVlanId
					Integer32,
				sleCfmMipCcdbMacAddr
					OCTET STRING,
				sleCfmMipCcdbPort
					Integer32,
				sleCfmMipCcdbKeepTime
					OCTET STRING
			 }

--   1.3.6.1.4.1.6296.101.4.13.10.1.1.1
-- 1.3.6.1.4.1.6296.101.4.13.10.1.1.1
		-- 1.3.6.1.4.1.6296.101.4.13.10.1.1.1
		sleCfmMipCcdbIndex OBJECT-TYPE
			SYNTAX Integer32 (1..65535)
			MAX-ACCESS read-only
			STATUS current
			DESCRIPTION
				"Indicates the MIP CCDB's Index"
			::= { sleCfmMipCcdbEntry 1 }

		
--   1.3.6.1.4.1.6296.101.4.13.10.1.1.2
-- 1.3.6.1.4.1.6296.101.4.13.10.1.1.2
		-- 1.3.6.1.4.1.6296.101.4.13.10.1.1.2
		sleCfmMipCcdbVlanId OBJECT-TYPE
			SYNTAX Integer32 (1..4094)
			MAX-ACCESS read-only
			STATUS current
			DESCRIPTION
				"VLAN Id"
			::= { sleCfmMipCcdbEntry 2 }

		
--   1.3.6.1.4.1.6296.101.4.13.10.1.1.3
-- 1.3.6.1.4.1.6296.101.4.13.10.1.1.3
		-- 1.3.6.1.4.1.6296.101.4.13.10.1.1.3
		sleCfmMipCcdbMacAddr OBJECT-TYPE
			SYNTAX OCTET STRING (SIZE (6))
			MAX-ACCESS read-only
			STATUS current
			DESCRIPTION
				"Indicates MAC address of the remote MEP"
			::= { sleCfmMipCcdbEntry 3 }

		
--   1.3.6.1.4.1.6296.101.4.13.10.1.1.4
-- 1.3.6.1.4.1.6296.101.4.13.10.1.1.4
		-- 1.3.6.1.4.1.6296.101.4.13.10.1.1.4
		sleCfmMipCcdbPort OBJECT-TYPE
			SYNTAX Integer32 (1..65535)
			MAX-ACCESS read-only
			STATUS current
			DESCRIPTION
				"Indicates the Port number that the CCM output"
			::= { sleCfmMipCcdbEntry 4 }

		
--   1.3.6.1.4.1.6296.101.4.13.10.1.1.5
-- 1.3.6.1.4.1.6296.101.4.13.10.1.1.5
		-- 1.3.6.1.4.1.6296.101.4.13.10.1.1.5
		sleCfmMipCcdbKeepTime OBJECT-TYPE
			SYNTAX OCTET STRING (SIZE (1..20))
			MAX-ACCESS read-only
			STATUS current
			DESCRIPTION
				"Indicates an up-date time of a entry"
			::= { sleCfmMipCcdbEntry 5 }

		
--   1.3.6.1.4.1.6296.101.4.14
-- 1.3.6.1.4.1.6296.101.4.14
		-- 1.3.6.1.4.1.6296.101.4.14
		sleEMLog OBJECT IDENTIFIER ::= { sleFaultMgmt 14 }

		
--   1.3.6.1.4.1.6296.101.4.14.1
-- 1.3.6.1.4.1.6296.101.4.14.1
		-- 1.3.6.1.4.1.6296.101.4.14.1
		sleEMLogInfo OBJECT IDENTIFIER ::= { sleEMLog 1 }

		
--   1.3.6.1.4.1.6296.101.4.14.1.1
-- 1.3.6.1.4.1.6296.101.4.14.1.1
		-- 1.3.6.1.4.1.6296.101.4.14.1.1
		sleEMLogDisableStatus OBJECT-TYPE
			SYNTAX INTEGER
				{
				false(0),
				true(1)
				}
			MAX-ACCESS read-only
			STATUS current
			DESCRIPTION
				"EM log disable."
			::= { sleEMLogInfo 1 }

		
--   1.3.6.1.4.1.6296.101.4.14.1.2
-- 1.3.6.1.4.1.6296.101.4.14.1.2
		-- 1.3.6.1.4.1.6296.101.4.14.1.2
		sleEMLogAction OBJECT-TYPE
			SYNTAX BITS
				{
				syslog(0),
				trap(1),
				recover(2)
				}
			MAX-ACCESS read-only
			STATUS current
			DESCRIPTION
				"Generate syslog message or SNMP Trap or take a recover action
				"
			::= { sleEMLogInfo 2 }

		
--   1.3.6.1.4.1.6296.101.4.14.1.3
-- 1.3.6.1.4.1.6296.101.4.14.1.3
		-- 1.3.6.1.4.1.6296.101.4.14.1.3
		sleEMLogInterval OBJECT-TYPE
			SYNTAX INTEGER (1..1440)
			MAX-ACCESS read-only
			STATUS current
			DESCRIPTION
				"Action interval in minute (Default. 3 mins)"
			::= { sleEMLogInfo 3 }

		
--  1.3.6.1.4.1.6296.101.4.14.1.4
		-- 1.3.6.1.4.1.6296.101.4.14.1.4
		sleEMLogNAKLockStatus OBJECT-TYPE
			SYNTAX INTEGER
				{
				enable(1),
				disable(2)
				}
			MAX-ACCESS read-only
			STATUS current
			DESCRIPTION
				"The status of emlog nak-locking"
			::= { sleEMLogInfo 4 }

		
--  1.3.6.1.4.1.6296.101.4.14.1.5
		-- 1.3.6.1.4.1.6296.101.4.14.1.5
		sleEMLogNakCompensate OBJECT-TYPE
			SYNTAX INTEGER
				{
				enable(1),
				disable(2)
				}
			MAX-ACCESS read-only
			STATUS current
			DESCRIPTION
				"The status of emlog nak-compensate (shadow recovery)"
			::= { sleEMLogInfo 5 }

		
--  1.3.6.1.4.1.6296.101.4.14.1.6
		-- 1.3.6.1.4.1.6296.101.4.14.1.6
		sleEMLogRecoverActionMemLow OBJECT-TYPE
			SYNTAX INTEGER
				{
				switchover(1),
				none(255)
				}
			MAX-ACCESS read-only
			STATUS current
			DESCRIPTION
				"Indicate recover action of memory low"
			::= { sleEMLogInfo 6 }

		
--  1.3.6.1.4.1.6296.101.4.14.1.7
		-- 1.3.6.1.4.1.6296.101.4.14.1.7
		sleEMLogRecoverActionNak OBJECT-TYPE
			SYNTAX INTEGER
				{
				switchover(1),
				none(255)
				}
			MAX-ACCESS read-only
			STATUS current
			DESCRIPTION
				"Indicate recover action of NAK error"
			::= { sleEMLogInfo 7 }

		
--   1.3.6.1.4.1.6296.101.4.14.2
-- 1.3.6.1.4.1.6296.101.4.14.2
		-- 1.3.6.1.4.1.6296.101.4.14.2
		sleEMLogControl OBJECT IDENTIFIER ::= { sleEMLog 2 }

		
--   1.3.6.1.4.1.6296.101.4.14.2.1
-- 1.3.6.1.4.1.6296.101.4.14.2.1
		-- 1.3.6.1.4.1.6296.101.4.14.2.1
		sleEMLogControlRequest OBJECT-TYPE
			SYNTAX INTEGER
				{
				setDisableStatus(1),
				setAction(2),
				setInterval(3),
				setNAKLock(4),
				setNAKCompensate(5),
				setRecoverActionMemLow(6),
				setRecoverActionNAK(7)
				}
			MAX-ACCESS read-write
			STATUS current
			DESCRIPTION
				" This attribute identifies the control commands.
				updateAlarmList:
				   the NE updates entries of alarms in the sleAlarmListTable
				   after having changed alarm severities of alarms 
				   (due to change profile pointers in
				   managed entities or after modification of alarm severities 
				   in profiles). This command should be applied once after having 
				   finisled modifications of severties.
				modifyAlarmSeverity: 
				   modifies the severity of an alarm in specific profile.
				createAlarmSeverityProfile: 
				   creates a new profile with default severities.
				   The severities then have to be modified with command changeAlarmSeverity.
				deleteAlarmSeverityProfile: 
				   deletes a profile. Profile 1 is not allowed to be deleted.
				 
				Notifications : none "
			::= { sleEMLogControl 1 }

		
--   1.3.6.1.4.1.6296.101.4.14.2.2
-- 1.3.6.1.4.1.6296.101.4.14.2.2
		-- 1.3.6.1.4.1.6296.101.4.14.2.2
		sleEMLogControlStatus OBJECT-TYPE
			SYNTAX SleControlStatusType
			MAX-ACCESS read-only
			STATUS current
			DESCRIPTION
				" The status of a control request. "
			::= { sleEMLogControl 2 }

		
--   1.3.6.1.4.1.6296.101.4.14.2.3
-- 1.3.6.1.4.1.6296.101.4.14.2.3
		-- 1.3.6.1.4.1.6296.101.4.14.2.3
		sleEMLogControlTimer OBJECT-TYPE
			SYNTAX Gauge32
			MAX-ACCESS read-write
			STATUS current
			DESCRIPTION
				" The maximum wait time for the manager for command ending.
				For long running commands.
				The manager reads this value from the DSLAM. "
			::= { sleEMLogControl 3 }

		
--   1.3.6.1.4.1.6296.101.4.14.2.4
-- 1.3.6.1.4.1.6296.101.4.14.2.4
		-- 1.3.6.1.4.1.6296.101.4.14.2.4
		sleEMLogControlTimeStamp OBJECT-TYPE
			SYNTAX TimeTicks
			MAX-ACCESS read-only
			STATUS current
			DESCRIPTION
				" The time stamp of the last command (end of command). "
			::= { sleEMLogControl 4 }

		
--   1.3.6.1.4.1.6296.101.4.14.2.5
-- 1.3.6.1.4.1.6296.101.4.14.2.5
		-- 1.3.6.1.4.1.6296.101.4.14.2.5
		sleEMLogControlReqResult OBJECT-TYPE
			SYNTAX SleControlRequestResultType
			MAX-ACCESS read-only
			STATUS current
			DESCRIPTION
				" The result of the last user command. "
			::= { sleEMLogControl 5 }

		
--   1.3.6.1.4.1.6296.101.4.14.2.6
-- 1.3.6.1.4.1.6296.101.4.14.2.6
		-- 1.3.6.1.4.1.6296.101.4.14.2.6
		sleEMLogControlDisableStatus OBJECT-TYPE
			SYNTAX INTEGER
				{
				false(0),
				true(1)
				}
			MAX-ACCESS read-write
			STATUS current
			DESCRIPTION
				"EM log disable."
			::= { sleEMLogControl 6 }

		
--   1.3.6.1.4.1.6296.101.4.14.2.7
-- 1.3.6.1.4.1.6296.101.4.14.2.7
		-- 1.3.6.1.4.1.6296.101.4.14.2.7
		sleEMLogControlAction OBJECT-TYPE
			SYNTAX BITS
				{
				syslog(0),
				trap(1),
				recover(2)
				}
			MAX-ACCESS read-write
			STATUS current
			DESCRIPTION
				"Generate syslog message or SNMP trap."
			::= { sleEMLogControl 7 }

		
--   1.3.6.1.4.1.6296.101.4.14.2.8
-- 1.3.6.1.4.1.6296.101.4.14.2.8
		-- 1.3.6.1.4.1.6296.101.4.14.2.8
		sleEMLogControlInterval OBJECT-TYPE
			SYNTAX INTEGER (1..1440)
			MAX-ACCESS read-write
			STATUS current
			DESCRIPTION
				"Action interval in minute (Default. 3 mins)"
			::= { sleEMLogControl 8 }

		
--  1.3.6.1.4.1.6296.101.4.14.2.9
		-- 1.3.6.1.4.1.6296.101.4.14.2.9
		sleEMLogControlNAKLockStatus OBJECT-TYPE
			SYNTAX INTEGER
				{
				enable(1),
				disable(2)
				}
			MAX-ACCESS read-write
			STATUS current
			DESCRIPTION
				"The status of emlog nak-locking"
			::= { sleEMLogControl 9 }

		
--  1.3.6.1.4.1.6296.101.4.14.2.10
		-- 1.3.6.1.4.1.6296.101.4.14.2.10
		sleEMLogControlNAKCompensate OBJECT-TYPE
			SYNTAX INTEGER
				{
				enable(1),
				disable(2)
				}
			MAX-ACCESS read-write
			STATUS current
			DESCRIPTION
				"The status of emlog nak-compensate (shadow recovery)"
			::= { sleEMLogControl 10 }

		
--  1.3.6.1.4.1.6296.101.4.14.2.11
		-- 1.3.6.1.4.1.6296.101.4.14.2.11
		sleEMLogControlRecoverActionMemLow OBJECT-TYPE
			SYNTAX INTEGER
				{
				switchover(1),
				none(255)
				}
			MAX-ACCESS read-write
			STATUS current
			DESCRIPTION
				"Indicate recover action of memory low"
			::= { sleEMLogControl 11 }

		
--  1.3.6.1.4.1.6296.101.4.14.2.12
		-- 1.3.6.1.4.1.6296.101.4.14.2.12
		sleEMLogControlRecoverActionNAK OBJECT-TYPE
			SYNTAX INTEGER
				{
				switchover(1),
				none(255)
				}
			MAX-ACCESS read-write
			STATUS current
			DESCRIPTION
				"Indicate recover action of NAK error
				"
			::= { sleEMLogControl 12 }

		
--   1.3.6.1.4.1.6296.101.4.14.3
-- 1.3.6.1.4.1.6296.101.4.14.3
		-- 1.3.6.1.4.1.6296.101.4.14.3
		sleEMLogNotification OBJECT IDENTIFIER ::= { sleEMLog 3 }

		
--   1.3.6.1.4.1.6296.101.4.14.3.1
-- 1.3.6.1.4.1.6296.101.4.14.3.1
		-- 1.3.6.1.4.1.6296.101.4.14.3.1
		sleEMLogDisableStatusChanged NOTIFICATION-TYPE
			OBJECTS { sleEMLogControlRequest, sleEMLogControlTimeStamp, sleEMLogControlReqResult, sleEMLogControlDisableStatus }
			STATUS current
			DESCRIPTION 
				"Description."
			::= { sleEMLogNotification 1 }

		
--   1.3.6.1.4.1.6296.101.4.14.3.2
-- 1.3.6.1.4.1.6296.101.4.14.3.2
		-- 1.3.6.1.4.1.6296.101.4.14.3.2
		sleEMLogActionChanged NOTIFICATION-TYPE
			OBJECTS { sleEMLogControlRequest, sleEMLogControlTimeStamp, sleEMLogControlReqResult, sleEMLogControlAction }
			STATUS current
			DESCRIPTION 
				"Description."
			::= { sleEMLogNotification 2 }

		
--   1.3.6.1.4.1.6296.101.4.14.3.3
-- 1.3.6.1.4.1.6296.101.4.14.3.3
		-- 1.3.6.1.4.1.6296.101.4.14.3.3
		sleEMLogIntervalChanged NOTIFICATION-TYPE
			OBJECTS { sleEMLogControlRequest, sleEMLogControlTimeStamp, sleEMLogControlReqResult, sleEMLogControlInterval }
			STATUS current
			DESCRIPTION 
				"Description."
			::= { sleEMLogNotification 3 }

		
--  1.3.6.1.4.1.6296.101.4.14.3.4
		-- 1.3.6.1.4.1.6296.101.4.14.3.4
		sleEMLogNAKLockChanged NOTIFICATION-TYPE
			OBJECTS { sleEMLogControlRequest, sleEMLogControlTimeStamp, sleEMLogControlReqResult, sleEMLogControlNAKLockStatus }
			STATUS current
			DESCRIPTION 
				"Description."
			::= { sleEMLogNotification 4 }

		
--  1.3.6.1.4.1.6296.101.4.14.3.5
		-- 1.3.6.1.4.1.6296.101.4.14.3.5
		sleEMLogNAKCompensateChanged NOTIFICATION-TYPE
			OBJECTS { sleEMLogControlRequest, sleEMLogControlTimeStamp, sleEMLogControlReqResult, sleEMLogControlNAKCompensate }
			STATUS current
			DESCRIPTION 
				"Description."
			::= { sleEMLogNotification 5 }

		
--  1.3.6.1.4.1.6296.101.4.14.3.6
		-- 1.3.6.1.4.1.6296.101.4.14.3.6
		sleEMLogRecoverActionMemLowChanged NOTIFICATION-TYPE
			OBJECTS { sleEMLogControlRequest, sleEMLogControlTimeStamp, sleEMLogControlReqResult, sleEMLogControlRecoverActionMemLow }
			STATUS current
			DESCRIPTION 
				"Description."
			::= { sleEMLogNotification 6 }

		
--  1.3.6.1.4.1.6296.101.4.14.3.7
		-- 1.3.6.1.4.1.6296.101.4.14.3.7
		sleEMLogRecoverActionNAKChanged NOTIFICATION-TYPE
			OBJECTS { sleEMLogControlRequest, sleEMLogControlTimeStamp, sleEMLogControlReqResult, sleEMLogControlRecoverActionNAK }
			STATUS current
			DESCRIPTION 
				"Description."
			::= { sleEMLogNotification 7 }

		
--   1.3.6.1.4.1.6296.101.4.14.4
-- 1.3.6.1.4.1.6296.101.4.14.4
		-- 1.3.6.1.4.1.6296.101.4.14.4
		sleEMLogDefectInfo OBJECT IDENTIFIER ::= { sleEMLog 4 }

		
		-- 1.3.6.1.4.1.6296.101.4.14.4.1
		sleEMLogDefectCPUHigh OBJECT-TYPE
			SYNTAX BITS
				{
				slot1(0),
				slot2(1),
				slot3(2),
				slot4(3),
				slot5(4),
				slot6(5),
				slot7(6),
				slot8(7)
				}
			MAX-ACCESS read-only
			STATUS current
			DESCRIPTION
				"The CPU high defection information."
			::= { sleEMLogDefectInfo 1 }

		
		-- 1.3.6.1.4.1.6296.101.4.14.4.2
		sleEMLogTemperHigh OBJECT-TYPE
			SYNTAX BITS
				{
				slot1(0),
				slot2(1),
				slot3(2),
				slot4(3),
				slot5(4),
				slot6(5),
				slot7(6),
				slot8(7)
				}
			MAX-ACCESS read-only
			STATUS current
			DESCRIPTION
				"The temperature hish defection information."
			::= { sleEMLogDefectInfo 2 }

		
		-- 1.3.6.1.4.1.6296.101.4.14.4.3
		sleEMLogTemperLow OBJECT-TYPE
			SYNTAX BITS
				{
				slot1(0),
				slot2(1),
				slot3(2),
				slot4(3),
				slot5(4),
				slot6(5),
				slot7(6),
				slot8(7)
				}
			MAX-ACCESS read-only
			STATUS current
			DESCRIPTION
				"The temperature low defection information."
			::= { sleEMLogDefectInfo 3 }

		
		-- 1.3.6.1.4.1.6296.101.4.14.4.4
		sleEMLogMemLow OBJECT-TYPE
			SYNTAX BITS
				{
				slot1(0),
				slot2(1),
				slot3(2),
				slot4(3),
				slot5(4),
				slot6(5),
				slot7(6),
				slot8(7)
				}
			MAX-ACCESS read-only
			STATUS current
			DESCRIPTION
				"The memory low defection information."
			::= { sleEMLogDefectInfo 4 }

		
		-- 1.3.6.1.4.1.6296.101.4.14.4.5
		sleEMLogFanFail OBJECT-TYPE
			SYNTAX BITS
				{
				slot1(0),
				slot2(1),
				slot3(2),
				slot4(3),
				slot5(4),
				slot6(5),
				slot7(6),
				slot8(7)
				}
			MAX-ACCESS read-only
			STATUS current
			DESCRIPTION
				"The fan failure defection information."
			::= { sleEMLogDefectInfo 5 }

		
		-- 1.3.6.1.4.1.6296.101.4.14.4.6
		sleEMLogPhyCRCFail OBJECT-TYPE
			SYNTAX BITS
				{
				slot1(0),
				slot2(1),
				slot3(2),
				slot4(3),
				slot5(4),
				slot6(5),
				slot7(6),
				slot8(7)
				}
			MAX-ACCESS read-only
			STATUS current
			DESCRIPTION
				"The PHY CRC failure defection information."
			::= { sleEMLogDefectInfo 6 }

		
		-- 1.3.6.1.4.1.6296.101.4.14.4.7
		sleEMLogPhyDetectFail OBJECT-TYPE
			SYNTAX BITS
				{
				slot1(0),
				slot2(1),
				slot3(2),
				slot4(3),
				slot5(4),
				slot6(5),
				slot7(6),
				slot8(7)
				}
			MAX-ACCESS read-only
			STATUS current
			DESCRIPTION
				"The PHY detection failure defection information."
			::= { sleEMLogDefectInfo 7 }

		
		-- 1.3.6.1.4.1.6296.101.4.14.4.8
		sleEMLogSFUMateInitFail OBJECT-TYPE
			SYNTAX BITS
				{
				slot1(0),
				slot2(1),
				slot3(2),
				slot4(3),
				slot5(4),
				slot6(5),
				slot7(6),
				slot8(7)
				}
			MAX-ACCESS read-only
			STATUS current
			DESCRIPTION
				"The SFU mate init failure defection information"
			::= { sleEMLogDefectInfo 8 }

		
		-- 1.3.6.1.4.1.6296.101.4.14.4.9
		sleEMLogDaemonHealthBad OBJECT-TYPE
			SYNTAX BITS
				{
				slot1(0),
				slot2(1),
				slot3(2),
				slot4(3),
				slot5(4),
				slot6(5),
				slot7(6),
				slot8(7)
				}
			MAX-ACCESS read-only
			STATUS current
			DESCRIPTION
				"The daemon health bad defection information."
			::= { sleEMLogDefectInfo 9 }

		
		-- 1.3.6.1.4.1.6296.101.4.14.4.10
		sleEMLogGPIURavenLinkDown OBJECT-TYPE
			SYNTAX BITS
				{
				slot1(0),
				slot2(1),
				slot3(2),
				slot4(3),
				slot5(4),
				slot6(5),
				slot7(6),
				slot8(7)
				}
			MAX-ACCESS read-only
			STATUS current
			DESCRIPTION
				"The GPIU raven link down defection information."
			::= { sleEMLogDefectInfo 10 }

		
		-- 1.3.6.1.4.1.6296.101.4.14.4.11
		sleEMLogFANRPMLow OBJECT-TYPE
			SYNTAX BITS
				{
				slot1(0),
				slot2(1),
				slot3(2),
				slot4(3),
				slot5(4),
				slot6(5),
				slot7(6),
				slot8(7)
				}
			MAX-ACCESS read-only
			STATUS current
			DESCRIPTION
				"The FAN RPM Low defection information."
			::= { sleEMLogDefectInfo 11 }

		
		-- 1.3.6.1.4.1.6296.101.4.14.4.12
		sleEMLogNAK OBJECT-TYPE
			SYNTAX BITS
				{
				slot1(0),
				slot2(1),
				slot3(2),
				slot4(3),
				slot5(4),
				slot6(5),
				slot7(6),
				slot8(7)
				}
			MAX-ACCESS read-only
			STATUS current
			DESCRIPTION
				"The NAK Error defection information."
			::= { sleEMLogDefectInfo 12 }

		
--   1.3.6.1.4.1.6296.101.4.15
-- 1.3.6.1.4.1.6296.101.4.15
		-- 1.3.6.1.4.1.6296.101.4.15
		sleRapsRing OBJECT IDENTIFIER ::= { sleFaultMgmt 15 }

		
--   1.3.6.1.4.1.6296.101.4.15.1
-- 1.3.6.1.4.1.6296.101.4.15.1
		-- 1.3.6.1.4.1.6296.101.4.15.1
		sleRapsRingTable OBJECT-TYPE
			SYNTAX SEQUENCE OF SleRapsRingEntry
			MAX-ACCESS not-accessible
			STATUS current
			DESCRIPTION
				"Description."
			::= { sleRapsRing 1 }

		
--   1.3.6.1.4.1.6296.101.4.15.1.1
-- 1.3.6.1.4.1.6296.101.4.15.1.1
		-- 1.3.6.1.4.1.6296.101.4.15.1.1
		sleRapsRingEntry OBJECT-TYPE
			SYNTAX SleRapsRingEntry
			MAX-ACCESS not-accessible
			STATUS current
			DESCRIPTION
				"Description."
			INDEX { sleRapsRingId }
			::= { sleRapsRingTable 1 }

		
		SleRapsRingEntry ::=
			SEQUENCE { 
				sleRapsRingId
					Integer32,
				sleRapsRingType
					INTEGER,
				sleRapsRingLevel
					INTEGER,
				sleRapsRingCtrlVlan
					INTEGER,
				sleRapsRingTrafficVlans
					OCTET STRING,
				sleRapsRingVirtualVlan
					INTEGER,
				sleRapsRingNodeId
					OCTET STRING,
				sleRapsRingEnable
					INTEGER,
				sleRapsRingBridgeRole
					INTEGER,
				sleRapsRingState
					INTEGER,
				sleRapsRingEastPort
					Integer32,
				sleRapsRingEastPortStatus
					INTEGER,
				sleRapsRingWestPort
					Integer32,
				sleRapsRingWestPortStatus
					INTEGER,
				sleRapsRingRplPort
					INTEGER,
				sleRapsRingIcPort
					INTEGER,
				sleRapsRingIcNode
					INTEGER,
				sleRapsRingMultipleFailure
					INTEGER,
				sleRapsRingPropagateTc
					INTEGER,
				sleRapsRingNonRevertive
					INTEGER,
				sleRapsRingForcedSwitch
					INTEGER,
				sleRapsRingManualSwitch
					INTEGER,
				sleRapsRingHoldOffTime
					INTEGER,
				sleRapsRingGuardTime
					INTEGER,
				sleRapsRingWaitToRestore
					INTEGER,
				sleRapsRingWaitToBlock
					INTEGER,
				sleRapsRingInstId
					Integer32,
				sleRapsRingChannel
					INTEGER,
				sleRapsRingPassThrough
					INTEGER,
				sleRapsRingVerifiedTime
					INTEGER
			 }

--   1.3.6.1.4.1.6296.101.4.15.1.1.1
-- 1.3.6.1.4.1.6296.101.4.15.1.1.1
		-- 1.3.6.1.4.1.6296.101.4.15.1.1.1
		sleRapsRingId OBJECT-TYPE
			SYNTAX Integer32 (1..255)
			MAX-ACCESS read-only
			STATUS current
			DESCRIPTION
				"Indicates the Ring’s ID"
			::= { sleRapsRingEntry 1 }

		
--   1.3.6.1.4.1.6296.101.4.15.1.1.2
-- 1.3.6.1.4.1.6296.101.4.15.1.1.2
		-- 1.3.6.1.4.1.6296.101.4.15.1.1.2
		sleRapsRingType OBJECT-TYPE
			SYNTAX INTEGER
				{
				major(1),
				sub(2),
				access(3)
				}
			MAX-ACCESS read-only
			STATUS current
			DESCRIPTION
				"Indicates the Ring’s type"
			::= { sleRapsRingEntry 2 }

		
--   1.3.6.1.4.1.6296.101.4.15.1.1.3
-- 1.3.6.1.4.1.6296.101.4.15.1.1.3
		-- 1.3.6.1.4.1.6296.101.4.15.1.1.3
		sleRapsRingLevel OBJECT-TYPE
			SYNTAX INTEGER (0..7)
			MAX-ACCESS read-only
			STATUS current
			DESCRIPTION
				"Indicates the Ring’s level"
			::= { sleRapsRingEntry 3 }

		
--   1.3.6.1.4.1.6296.101.4.15.1.1.4
-- 1.3.6.1.4.1.6296.101.4.15.1.1.4
		-- 1.3.6.1.4.1.6296.101.4.15.1.1.4
		sleRapsRingCtrlVlan OBJECT-TYPE
			SYNTAX INTEGER (1..4094)
			MAX-ACCESS read-only
			STATUS current
			DESCRIPTION
				"Indicates the Ring Node’s control-vlan"
			::= { sleRapsRingEntry 4 }

		
--   1.3.6.1.4.1.6296.101.4.15.1.1.5
-- 1.3.6.1.4.1.6296.101.4.15.1.1.5
		-- 1.3.6.1.4.1.6296.101.4.15.1.1.5
		sleRapsRingTrafficVlans OBJECT-TYPE
			SYNTAX OCTET STRING
			MAX-ACCESS read-only
			STATUS current
			DESCRIPTION
				"Indicates the Ring Node’s traffic-vlans"
			::= { sleRapsRingEntry 5 }

		
--   1.3.6.1.4.1.6296.101.4.15.1.1.6
-- 1.3.6.1.4.1.6296.101.4.15.1.1.6
		-- 1.3.6.1.4.1.6296.101.4.15.1.1.6
		sleRapsRingVirtualVlan OBJECT-TYPE
			SYNTAX INTEGER (0..4094)
			MAX-ACCESS read-only
			STATUS current
			DESCRIPTION
				"Indicates the Ring Node's virtual-vlan"
			::= { sleRapsRingEntry 6 }

		
--   1.3.6.1.4.1.6296.101.4.15.1.1.7
-- 1.3.6.1.4.1.6296.101.4.15.1.1.7
		-- 1.3.6.1.4.1.6296.101.4.15.1.1.7
		sleRapsRingNodeId OBJECT-TYPE
			SYNTAX OCTET STRING (SIZE (6))
			MAX-ACCESS read-only
			STATUS current
			DESCRIPTION
				"Indicates the Ring Node’s ID"
			::= { sleRapsRingEntry 7 }

		
--   1.3.6.1.4.1.6296.101.4.15.1.1.8
-- 1.3.6.1.4.1.6296.101.4.15.1.1.8
		-- 1.3.6.1.4.1.6296.101.4.15.1.1.8
		sleRapsRingEnable OBJECT-TYPE
			SYNTAX INTEGER
				{
				disable(0),
				enable(1)
				}
			MAX-ACCESS read-only
			STATUS current
			DESCRIPTION
				"Enables/Disables Ring Node"
			::= { sleRapsRingEntry 8 }

		
--   1.3.6.1.4.1.6296.101.4.15.1.1.9
-- 1.3.6.1.4.1.6296.101.4.15.1.1.9
		-- 1.3.6.1.4.1.6296.101.4.15.1.1.9
		sleRapsRingBridgeRole OBJECT-TYPE
			SYNTAX INTEGER
				{
				normal(0),
				rplowner(1),
				rplneighbour(2),
				rplnextneighbour(3)
				}
			MAX-ACCESS read-only
			STATUS current
			DESCRIPTION
				"Indicates the Ring Node’s Role"
			::= { sleRapsRingEntry 9 }

		
--   1.3.6.1.4.1.6296.101.4.15.1.1.10
-- 1.3.6.1.4.1.6296.101.4.15.1.1.10
		-- 1.3.6.1.4.1.6296.101.4.15.1.1.10
		sleRapsRingState OBJECT-TYPE
			SYNTAX INTEGER
				{
				none(0),
				idle(1),
				protection(2),
				manual(3),
				forced(4),
				pending(5),
				required(6)
				}
			MAX-ACCESS read-only
			STATUS current
			DESCRIPTION
				"Indicates the Ring Node’s State"
			::= { sleRapsRingEntry 10 }

		
--   1.3.6.1.4.1.6296.101.4.15.1.1.11
-- 1.3.6.1.4.1.6296.101.4.15.1.1.11
		-- 1.3.6.1.4.1.6296.101.4.15.1.1.11
		sleRapsRingEastPort OBJECT-TYPE
			SYNTAX Integer32
			MAX-ACCESS read-only
			STATUS current
			DESCRIPTION
				"Indicates the Ring Node’s east port"
			::= { sleRapsRingEntry 11 }

		
--   1.3.6.1.4.1.6296.101.4.15.1.1.12
-- 1.3.6.1.4.1.6296.101.4.15.1.1.12
		-- 1.3.6.1.4.1.6296.101.4.15.1.1.12
		sleRapsRingEastPortStatus OBJECT-TYPE
			SYNTAX INTEGER
				{
				none(0),
				disabled(1),
				forwarding(2),
				blocking(3)
				}
			MAX-ACCESS read-only
			STATUS current
			DESCRIPTION
				"Indicates the port status of east port"
			::= { sleRapsRingEntry 12 }

		
--   1.3.6.1.4.1.6296.101.4.15.1.1.13
-- 1.3.6.1.4.1.6296.101.4.15.1.1.13
		-- 1.3.6.1.4.1.6296.101.4.15.1.1.13
		sleRapsRingWestPort OBJECT-TYPE
			SYNTAX Integer32
			MAX-ACCESS read-only
			STATUS current
			DESCRIPTION
				"Indicates the Ring Node’s west port"
			::= { sleRapsRingEntry 13 }

		
--   1.3.6.1.4.1.6296.101.4.15.1.1.14
-- 1.3.6.1.4.1.6296.101.4.15.1.1.14
		-- 1.3.6.1.4.1.6296.101.4.15.1.1.14
		sleRapsRingWestPortStatus OBJECT-TYPE
			SYNTAX INTEGER
				{
				none(0),
				disabled(1),
				forwarding(2),
				blocking(3)
				}
			MAX-ACCESS read-only
			STATUS current
			DESCRIPTION
				"Indicates the port status of west port"
			::= { sleRapsRingEntry 14 }

		
--   1.3.6.1.4.1.6296.101.4.15.1.1.15
-- 1.3.6.1.4.1.6296.101.4.15.1.1.15
		-- 1.3.6.1.4.1.6296.101.4.15.1.1.15
		sleRapsRingRplPort OBJECT-TYPE
			SYNTAX INTEGER
				{
				none(0),
				east(1),
				west(2)
				}
			MAX-ACCESS read-only
			STATUS current
			DESCRIPTION
				"Indicates the Ring’s RPL port"
			::= { sleRapsRingEntry 15 }

		
--   1.3.6.1.4.1.6296.101.4.15.1.1.16
-- 1.3.6.1.4.1.6296.101.4.15.1.1.16
		-- 1.3.6.1.4.1.6296.101.4.15.1.1.16
		sleRapsRingIcPort OBJECT-TYPE
			SYNTAX INTEGER
				{
				none(0),
				east(1),
				west(2)
				}
			MAX-ACCESS read-only
			STATUS current
			DESCRIPTION
				"Indicates the Ring’s interconnection port"
			::= { sleRapsRingEntry 16 }

		
--   1.3.6.1.4.1.6296.101.4.15.1.1.17
-- 1.3.6.1.4.1.6296.101.4.15.1.1.17
		-- 1.3.6.1.4.1.6296.101.4.15.1.1.17
		sleRapsRingIcNode OBJECT-TYPE
			SYNTAX INTEGER
				{
				none(0),
				primary(1),
				secondary(2)
				}
			MAX-ACCESS read-only
			STATUS current
			DESCRIPTION
				"Indicates the primary/secondary node for the minimization of the segmentation"
			::= { sleRapsRingEntry 17 }

		
--   1.3.6.1.4.1.6296.101.4.15.1.1.18
-- 1.3.6.1.4.1.6296.101.4.15.1.1.18
		-- 1.3.6.1.4.1.6296.101.4.15.1.1.18
		sleRapsRingMultipleFailure OBJECT-TYPE
			SYNTAX INTEGER
				{
				none(0),
				primary(1),
				secondary(2)
				}
			MAX-ACCESS read-only
			STATUS current
			DESCRIPTION
				"The multiple failure mode"
			::= { sleRapsRingEntry 18 }

		
--   1.3.6.1.4.1.6296.101.4.15.1.1.19
-- 1.3.6.1.4.1.6296.101.4.15.1.1.19
		-- 1.3.6.1.4.1.6296.101.4.15.1.1.19
		sleRapsRingPropagateTc OBJECT-TYPE
			SYNTAX INTEGER
				{
				false(0),
				true(1)
				}
			MAX-ACCESS read-only
			STATUS current
			DESCRIPTION
				"The propagation TC(topology change)"
			::= { sleRapsRingEntry 19 }

		
--   1.3.6.1.4.1.6296.101.4.15.1.1.20
-- 1.3.6.1.4.1.6296.101.4.15.1.1.20
		-- 1.3.6.1.4.1.6296.101.4.15.1.1.20
		sleRapsRingNonRevertive OBJECT-TYPE
			SYNTAX INTEGER
				{
				false(0),
				true(1)
				}
			MAX-ACCESS read-only
			STATUS current
			DESCRIPTION
				"The Non-Revertive"
			::= { sleRapsRingEntry 20 }

		
--   1.3.6.1.4.1.6296.101.4.15.1.1.21
-- 1.3.6.1.4.1.6296.101.4.15.1.1.21
		-- 1.3.6.1.4.1.6296.101.4.15.1.1.21
		sleRapsRingForcedSwitch OBJECT-TYPE
			SYNTAX INTEGER
				{
				none(0),
				east(1),
				west(2),
				both(3)
				}
			MAX-ACCESS read-only
			STATUS current
			DESCRIPTION
				"Indicates the Forced Switch"
			::= { sleRapsRingEntry 21 }

		
--   1.3.6.1.4.1.6296.101.4.15.1.1.22
-- 1.3.6.1.4.1.6296.101.4.15.1.1.22
		-- 1.3.6.1.4.1.6296.101.4.15.1.1.22
		sleRapsRingManualSwitch OBJECT-TYPE
			SYNTAX INTEGER
				{
				none(0),
				east(1),
				west(2)
				}
			MAX-ACCESS read-only
			STATUS current
			DESCRIPTION
				"Indicates the Manual Switch"
			::= { sleRapsRingEntry 22 }

		
--   1.3.6.1.4.1.6296.101.4.15.1.1.23
-- 1.3.6.1.4.1.6296.101.4.15.1.1.23
		-- 1.3.6.1.4.1.6296.101.4.15.1.1.23
		sleRapsRingHoldOffTime OBJECT-TYPE
			SYNTAX INTEGER (0..10000)
			MAX-ACCESS read-only
			STATUS current
			DESCRIPTION
				"Indicates the hold-off time"
			::= { sleRapsRingEntry 23 }

		
--   1.3.6.1.4.1.6296.101.4.15.1.1.24
-- 1.3.6.1.4.1.6296.101.4.15.1.1.24
		-- 1.3.6.1.4.1.6296.101.4.15.1.1.24
		sleRapsRingGuardTime OBJECT-TYPE
			SYNTAX INTEGER (10..2000)
			MAX-ACCESS read-only
			STATUS current
			DESCRIPTION
				"Indicates the guard time"
			::= { sleRapsRingEntry 24 }

		
--   1.3.6.1.4.1.6296.101.4.15.1.1.25
-- 1.3.6.1.4.1.6296.101.4.15.1.1.25
		-- 1.3.6.1.4.1.6296.101.4.15.1.1.25
		sleRapsRingWaitToRestore OBJECT-TYPE
			SYNTAX INTEGER (1..12)
			MAX-ACCESS read-only
			STATUS current
			DESCRIPTION
				"Indicates the wait-to-restore time"
			::= { sleRapsRingEntry 25 }

		
--   1.3.6.1.4.1.6296.101.4.15.1.1.26
-- 1.3.6.1.4.1.6296.101.4.15.1.1.26
		-- 1.3.6.1.4.1.6296.101.4.15.1.1.26
		sleRapsRingWaitToBlock OBJECT-TYPE
			SYNTAX INTEGER (5..7)
			MAX-ACCESS read-only
			STATUS current
			DESCRIPTION
				"Indicates the wait-to-block time"
			::= { sleRapsRingEntry 26 }

		
--   1.3.6.1.4.1.6296.101.4.15.1.1.27
-- 1.3.6.1.4.1.6296.101.4.15.1.1.27
		-- 1.3.6.1.4.1.6296.101.4.15.1.1.27
		sleRapsRingInstId OBJECT-TYPE
			SYNTAX Integer32 (1..255)
			MAX-ACCESS read-only
			STATUS current
			DESCRIPTION
				"Indicates the ring instance ID."
			::= { sleRapsRingEntry 27 }

		
--   1.3.6.1.4.1.6296.101.4.15.1.1.28
-- 1.3.6.1.4.1.6296.101.4.15.1.1.28
		-- 1.3.6.1.4.1.6296.101.4.15.1.1.28
		sleRapsRingChannel OBJECT-TYPE
			SYNTAX INTEGER
				{
				none(0),
				virtual(1),
				abstract(2)
				}
			MAX-ACCESS read-only
			STATUS current
			DESCRIPTION
				"Indicates the R-APS channel type."
			::= { sleRapsRingEntry 28 }

		
--   1.3.6.1.4.1.6296.101.4.15.1.1.29
-- 1.3.6.1.4.1.6296.101.4.15.1.1.29
		-- 1.3.6.1.4.1.6296.101.4.15.1.1.29
		sleRapsRingPassThrough OBJECT-TYPE
			SYNTAX INTEGER
				{
				false(0),
				true(1)
				}
			MAX-ACCESS read-only
			STATUS current
			DESCRIPTION
				"Indicates the pass-through funtion."
			::= { sleRapsRingEntry 29 }

		
--   1.3.6.1.4.1.6296.101.4.15.1.1.30
-- 1.3.6.1.4.1.6296.101.4.15.1.1.30
		-- 1.3.6.1.4.1.6296.101.4.15.1.1.30
		sleRapsRingVerifiedTime OBJECT-TYPE
			SYNTAX INTEGER (0..10000)
			MAX-ACCESS read-only
			STATUS current
			DESCRIPTION
				"Indicates the verified time"
			::= { sleRapsRingEntry 30 }

		
--   1.3.6.1.4.1.6296.101.4.15.2
-- 1.3.6.1.4.1.6296.101.4.15.2
		-- 1.3.6.1.4.1.6296.101.4.15.2
		sleRapsRingControl OBJECT IDENTIFIER ::= { sleRapsRing 2 }

		
--   1.3.6.1.4.1.6296.101.4.15.2.1
-- 1.3.6.1.4.1.6296.101.4.15.2.1
		-- 1.3.6.1.4.1.6296.101.4.15.2.1
		sleRapsRingControlRequest OBJECT-TYPE
			SYNTAX INTEGER
				{
				createRapsRing(1),
				deleteRapsRing(2),
				setRapsRingChannel(3),
				setRapsRingEnable(4),
				setRapsRingPorts(5),
				destroyRapsRingPorts(6),
				setRapsRingRplPort(7),
				setRapsRingIcPort(8),
				destroyRapsRingIcPort(9),
				setRapsRingMultipleFailure(10),
				setRapsRingPropagateTc(11),
				setRapsRingNonRevertive(12),
				setRapsRingForcedSwitch(13),
				setRapsRingManualSwitch(14),
				setRapsRingClearSwitch(15),
				setRapsRingHoldOffTime(16),
				setRapsRingGuardTime(17),
				setRapsRingWtrTime(18),
				setRapsRingWtbTime(19),
				setRapsRingPassThrough(20),
				setRapsRingVrfTime(21)
				}
			MAX-ACCESS read-write
			STATUS current
			DESCRIPTION
				"Description."
			::= { sleRapsRingControl 1 }

		
--   1.3.6.1.4.1.6296.101.4.15.2.2
-- 1.3.6.1.4.1.6296.101.4.15.2.2
		-- 1.3.6.1.4.1.6296.101.4.15.2.2
		sleRapsRingControlStatus OBJECT-TYPE
			SYNTAX SleControlStatusType
			MAX-ACCESS read-only
			STATUS current
			DESCRIPTION
				"Description."
			::= { sleRapsRingControl 2 }

		
--   1.3.6.1.4.1.6296.101.4.15.2.3
-- 1.3.6.1.4.1.6296.101.4.15.2.3
		-- 1.3.6.1.4.1.6296.101.4.15.2.3
		sleRapsRingControlTimer OBJECT-TYPE
			SYNTAX Gauge32
			MAX-ACCESS read-write
			STATUS current
			DESCRIPTION
				"Description."
			::= { sleRapsRingControl 3 }

		
--   1.3.6.1.4.1.6296.101.4.15.2.4
-- 1.3.6.1.4.1.6296.101.4.15.2.4
		-- 1.3.6.1.4.1.6296.101.4.15.2.4
		sleRapsRingControlTimeStamp OBJECT-TYPE
			SYNTAX TimeTicks
			MAX-ACCESS read-only
			STATUS current
			DESCRIPTION
				"Description."
			::= { sleRapsRingControl 4 }

		
--   1.3.6.1.4.1.6296.101.4.15.2.5
-- 1.3.6.1.4.1.6296.101.4.15.2.5
		-- 1.3.6.1.4.1.6296.101.4.15.2.5
		sleRapsRingControlReqResult OBJECT-TYPE
			SYNTAX SleControlRequestResultType
			MAX-ACCESS read-only
			STATUS current
			DESCRIPTION
				"Description."
			::= { sleRapsRingControl 5 }

		
--   1.3.6.1.4.1.6296.101.4.15.2.6
-- 1.3.6.1.4.1.6296.101.4.15.2.6
		-- 1.3.6.1.4.1.6296.101.4.15.2.6
		sleRapsRingControlId OBJECT-TYPE
			SYNTAX Integer32 (1..255)
			MAX-ACCESS read-write
			STATUS current
			DESCRIPTION
				"Indicates the Ring’s ID"
			::= { sleRapsRingControl 6 }

		
--   1.3.6.1.4.1.6296.101.4.15.2.7
-- 1.3.6.1.4.1.6296.101.4.15.2.7
		-- 1.3.6.1.4.1.6296.101.4.15.2.7
		sleRapsRingControlType OBJECT-TYPE
			SYNTAX INTEGER
				{
				major(1),
				sub(2),
				access(3)
				}
			MAX-ACCESS read-write
			STATUS current
			DESCRIPTION
				"Indicates the Ring’s type"
			::= { sleRapsRingControl 7 }

		
--   1.3.6.1.4.1.6296.101.4.15.2.8
-- 1.3.6.1.4.1.6296.101.4.15.2.8
		-- 1.3.6.1.4.1.6296.101.4.15.2.8
		sleRapsRingControlLevel OBJECT-TYPE
			SYNTAX INTEGER (0..7)
			MAX-ACCESS read-write
			STATUS current
			DESCRIPTION
				"Indicates the Ring’s level"
			::= { sleRapsRingControl 8 }

		
--   1.3.6.1.4.1.6296.101.4.15.2.9
-- 1.3.6.1.4.1.6296.101.4.15.2.9
		-- 1.3.6.1.4.1.6296.101.4.15.2.9
		sleRapsRingControlCtrlVlan OBJECT-TYPE
			SYNTAX INTEGER (1..4094)
			MAX-ACCESS read-write
			STATUS current
			DESCRIPTION
				"Indicates the Ring Node’s control-vlan"
			::= { sleRapsRingControl 9 }

		
--   1.3.6.1.4.1.6296.101.4.15.2.10
-- 1.3.6.1.4.1.6296.101.4.15.2.10
		-- 1.3.6.1.4.1.6296.101.4.15.2.10
		sleRapsRingControlTrafficVlans OBJECT-TYPE
			SYNTAX OCTET STRING
			MAX-ACCESS read-write
			STATUS current
			DESCRIPTION
				"Indicates the Ring Node’s traffic-vlans"
			::= { sleRapsRingControl 10 }

		
--   1.3.6.1.4.1.6296.101.4.15.2.11
-- 1.3.6.1.4.1.6296.101.4.15.2.11
		-- 1.3.6.1.4.1.6296.101.4.15.2.11
		sleRapsRingControlChannel OBJECT-TYPE
			SYNTAX INTEGER
				{
				none(0),
				virtual(1),
				abstract(2)
				}
			MAX-ACCESS read-write
			STATUS current
			DESCRIPTION
				"Indicates the Ring Node's channel"
			::= { sleRapsRingControl 11 }

		
--   1.3.6.1.4.1.6296.101.4.15.2.12
-- 1.3.6.1.4.1.6296.101.4.15.2.12
		-- 1.3.6.1.4.1.6296.101.4.15.2.12
		sleRapsRingControlEnable OBJECT-TYPE
			SYNTAX INTEGER
				{
				disable(0),
				enable(1)
				}
			MAX-ACCESS read-write
			STATUS current
			DESCRIPTION
				"IEnables/Disables Ring Node"
			::= { sleRapsRingControl 12 }

		
--   1.3.6.1.4.1.6296.101.4.15.2.13
-- 1.3.6.1.4.1.6296.101.4.15.2.13
		-- 1.3.6.1.4.1.6296.101.4.15.2.13
		sleRapsRingControlEastPort OBJECT-TYPE
			SYNTAX Integer32
			MAX-ACCESS read-write
			STATUS current
			DESCRIPTION
				"Indicates the Ring Node’s east port"
			::= { sleRapsRingControl 13 }

		
--   1.3.6.1.4.1.6296.101.4.15.2.14
-- 1.3.6.1.4.1.6296.101.4.15.2.14
		-- 1.3.6.1.4.1.6296.101.4.15.2.14
		sleRapsRingControlWestPort OBJECT-TYPE
			SYNTAX Integer32
			MAX-ACCESS read-write
			STATUS current
			DESCRIPTION
				"Indicates the Ring Node’s west port"
			::= { sleRapsRingControl 14 }

		
--   1.3.6.1.4.1.6296.101.4.15.2.15
-- 1.3.6.1.4.1.6296.101.4.15.2.15
		-- 1.3.6.1.4.1.6296.101.4.15.2.15
		sleRapsRingControlParamPort OBJECT-TYPE
			SYNTAX INTEGER
				{
				east(1),
				west(2)
				}
			MAX-ACCESS read-write
			STATUS current
			DESCRIPTION
				"Indicates the rpl port, interconnection port, forced or manual switch port."
			::= { sleRapsRingControl 15 }

		
--   1.3.6.1.4.1.6296.101.4.15.2.16
-- 1.3.6.1.4.1.6296.101.4.15.2.16
		-- 1.3.6.1.4.1.6296.101.4.15.2.16
		sleRapsRingControlBridgeRole OBJECT-TYPE
			SYNTAX INTEGER
				{
				none(0),
				rplowner(1),
				neighbour(2),
				nextneighbour(3)
				}
			MAX-ACCESS read-write
			STATUS current
			DESCRIPTION
				"Indicates the Ring’s RPL port type"
			::= { sleRapsRingControl 16 }

		
--   1.3.6.1.4.1.6296.101.4.15.2.17
-- 1.3.6.1.4.1.6296.101.4.15.2.17
		-- 1.3.6.1.4.1.6296.101.4.15.2.17
		sleRapsRingControlIcNode OBJECT-TYPE
			SYNTAX INTEGER
				{
				primary(1),
				secondary(2)
				}
			MAX-ACCESS read-write
			STATUS current
			DESCRIPTION
				"Indicates the primary/secondary node for the minimization of the segmentation"
			::= { sleRapsRingControl 17 }

		
--   1.3.6.1.4.1.6296.101.4.15.2.18
-- 1.3.6.1.4.1.6296.101.4.15.2.18
		-- 1.3.6.1.4.1.6296.101.4.15.2.18
		sleRapsRingControlMultipleFailure OBJECT-TYPE
			SYNTAX INTEGER
				{
				none(0),
				primary(1),
				secondary(2)
				}
			MAX-ACCESS read-write
			STATUS current
			DESCRIPTION
				"The multiple failure of Ring Node"
			::= { sleRapsRingControl 18 }

		
--   1.3.6.1.4.1.6296.101.4.15.2.19
-- 1.3.6.1.4.1.6296.101.4.15.2.19
		-- 1.3.6.1.4.1.6296.101.4.15.2.19
		sleRapsRingControlPropagateTc OBJECT-TYPE
			SYNTAX INTEGER
				{
				false(0),
				true(1)
				}
			MAX-ACCESS read-write
			STATUS current
			DESCRIPTION
				"The propagation TC"
			::= { sleRapsRingControl 19 }

		
--   1.3.6.1.4.1.6296.101.4.15.2.20
-- 1.3.6.1.4.1.6296.101.4.15.2.20
		-- 1.3.6.1.4.1.6296.101.4.15.2.20
		sleRapsRingControlNonRevertive OBJECT-TYPE
			SYNTAX INTEGER
				{
				false(0),
				true(1)
				}
			MAX-ACCESS read-write
			STATUS current
			DESCRIPTION
				"The Non-Revertive"
			::= { sleRapsRingControl 20 }

		
--   1.3.6.1.4.1.6296.101.4.15.2.21
-- 1.3.6.1.4.1.6296.101.4.15.2.21
		-- 1.3.6.1.4.1.6296.101.4.15.2.21
		sleRapsRingControlHoldOffTime OBJECT-TYPE
			SYNTAX INTEGER (0..10000)
			MAX-ACCESS read-write
			STATUS current
			DESCRIPTION
				"Indicates the hold-off time.
				The hold-off time's step must be 100
				"
			::= { sleRapsRingControl 21 }

		
--   1.3.6.1.4.1.6296.101.4.15.2.22
-- 1.3.6.1.4.1.6296.101.4.15.2.22
		-- 1.3.6.1.4.1.6296.101.4.15.2.22
		sleRapsRingControlGuardTime OBJECT-TYPE
			SYNTAX INTEGER (10..2000)
			MAX-ACCESS read-write
			STATUS current
			DESCRIPTION
				"Indicates the guard time.
				The guard time's step must be 10.
				"
			::= { sleRapsRingControl 22 }

		
--   1.3.6.1.4.1.6296.101.4.15.2.23
-- 1.3.6.1.4.1.6296.101.4.15.2.23
		-- 1.3.6.1.4.1.6296.101.4.15.2.23
		sleRapsRingControlWaitToRestore OBJECT-TYPE
			SYNTAX INTEGER (1..12)
			MAX-ACCESS read-write
			STATUS current
			DESCRIPTION
				"Indicates the wait-to-restore time
				"
			::= { sleRapsRingControl 23 }

		
--   1.3.6.1.4.1.6296.101.4.15.2.24
-- 1.3.6.1.4.1.6296.101.4.15.2.24
		-- 1.3.6.1.4.1.6296.101.4.15.2.24
		sleRapsRingControlWaitToBlock OBJECT-TYPE
			SYNTAX INTEGER (5..7)
			MAX-ACCESS read-write
			STATUS current
			DESCRIPTION
				"Indicates the wait-to-block time"
			::= { sleRapsRingControl 24 }

		
--   1.3.6.1.4.1.6296.101.4.15.2.25
-- 1.3.6.1.4.1.6296.101.4.15.2.25
		-- 1.3.6.1.4.1.6296.101.4.15.2.25
		sleRapsRingControlInstId OBJECT-TYPE
			SYNTAX Integer32 (1..255)
			MAX-ACCESS read-write
			STATUS current
			DESCRIPTION
				"Indicates the ring instance ID."
			::= { sleRapsRingControl 25 }

		
--   1.3.6.1.4.1.6296.101.4.15.2.26
-- 1.3.6.1.4.1.6296.101.4.15.2.26
		-- 1.3.6.1.4.1.6296.101.4.15.2.26
		sleRapsRingControlPassThrough OBJECT-TYPE
			SYNTAX INTEGER
				{
				false(0),
				true(1)
				}
			MAX-ACCESS read-write
			STATUS current
			DESCRIPTION
				"Indicates the pass-through function."
			::= { sleRapsRingControl 26 }

		
--   1.3.6.1.4.1.6296.101.4.15.2.27
-- 1.3.6.1.4.1.6296.101.4.15.2.27
		-- 1.3.6.1.4.1.6296.101.4.15.2.27
		sleRapsRingControlVerifiedTime OBJECT-TYPE
			SYNTAX INTEGER (0..10000)
			MAX-ACCESS read-write
			STATUS current
			DESCRIPTION
				"Indicates the verified time."
			::= { sleRapsRingControl 27 }

		
--   1.3.6.1.4.1.6296.101.4.15.3
-- 1.3.6.1.4.1.6296.101.4.15.3
		-- 1.3.6.1.4.1.6296.101.4.15.3
		sleRapsRingNotification OBJECT IDENTIFIER ::= { sleRapsRing 3 }

		
--   1.3.6.1.4.1.6296.101.4.15.3.1
-- 1.3.6.1.4.1.6296.101.4.15.3.1
		-- 1.3.6.1.4.1.6296.101.4.15.3.1
		sleRapsRingCreated NOTIFICATION-TYPE
			OBJECTS { sleRapsRingControlRequest, sleRapsRingControlTimeStamp, sleRapsRingControlReqResult, sleRapsRingControlInstId, sleRapsRingControlId, 
				sleRapsRingControlType, sleRapsRingControlLevel, sleRapsRingControlCtrlVlan, sleRapsRingControlTrafficVlans }
			STATUS current
			DESCRIPTION 
				"createRapsRing"
			::= { sleRapsRingNotification 1 }

		
--   1.3.6.1.4.1.6296.101.4.15.3.2
-- 1.3.6.1.4.1.6296.101.4.15.3.2
		-- 1.3.6.1.4.1.6296.101.4.15.3.2
		sleRapsRingDeleted NOTIFICATION-TYPE
			OBJECTS { sleRapsRingControlRequest, sleRapsRingControlTimeStamp, sleRapsRingControlReqResult, sleRapsRingControlInstId }
			STATUS current
			DESCRIPTION 
				"deleteRapsRing"
			::= { sleRapsRingNotification 2 }

		
--   1.3.6.1.4.1.6296.101.4.15.3.3
-- 1.3.6.1.4.1.6296.101.4.15.3.3
		-- 1.3.6.1.4.1.6296.101.4.15.3.3
		sleRapsRingChannelChanged NOTIFICATION-TYPE
			OBJECTS { sleRapsRingControlRequest, sleRapsRingControlTimeStamp, sleRapsRingControlReqResult, sleRapsRingControlInstId, sleRapsRingControlChannel
				 }
			STATUS current
			DESCRIPTION 
				"setRapsRingChannel"
			::= { sleRapsRingNotification 3 }

		
--   1.3.6.1.4.1.6296.101.4.15.3.4
-- 1.3.6.1.4.1.6296.101.4.15.3.4
		-- 1.3.6.1.4.1.6296.101.4.15.3.4
		sleRapsRingEnableChanged NOTIFICATION-TYPE
			OBJECTS { sleRapsRingControlRequest, sleRapsRingControlTimeStamp, sleRapsRingControlReqResult, sleRapsRingControlInstId, sleRapsRingControlEnable
				 }
			STATUS current
			DESCRIPTION 
				"setRapsRingEnable"
			::= { sleRapsRingNotification 4 }

		
--   1.3.6.1.4.1.6296.101.4.15.3.5
-- 1.3.6.1.4.1.6296.101.4.15.3.5
		-- 1.3.6.1.4.1.6296.101.4.15.3.5
		sleRapsRingPortsCreated NOTIFICATION-TYPE
			OBJECTS { sleRapsRingControlRequest, sleRapsRingControlTimeStamp, sleRapsRingControlReqResult, sleRapsRingControlInstId, sleRapsRingControlEastPort, 
				sleRapsRingControlWestPort, sleRapsRingControlParamPort }
			STATUS current
			DESCRIPTION 
				"setRapsRingPorts"
			::= { sleRapsRingNotification 5 }

		
--   1.3.6.1.4.1.6296.101.4.15.3.6
-- 1.3.6.1.4.1.6296.101.4.15.3.6
		-- 1.3.6.1.4.1.6296.101.4.15.3.6
		sleRapsRingPortsDestroyed NOTIFICATION-TYPE
			OBJECTS { sleRapsRingControlRequest, sleRapsRingControlTimeStamp, sleRapsRingControlReqResult, sleRapsRingControlInstId }
			STATUS current
			DESCRIPTION 
				"destroyRapsRingPorts"
			::= { sleRapsRingNotification 6 }

		
--   1.3.6.1.4.1.6296.101.4.15.3.7
-- 1.3.6.1.4.1.6296.101.4.15.3.7
		-- 1.3.6.1.4.1.6296.101.4.15.3.7
		sleRapsRingRplPortChanged NOTIFICATION-TYPE
			OBJECTS { sleRapsRingControlRequest, sleRapsRingControlTimeStamp, sleRapsRingControlReqResult, sleRapsRingControlInstId, sleRapsRingControlBridgeRole, 
				sleRapsRingControlParamPort }
			STATUS current
			DESCRIPTION 
				"setRapsRingRplPort"
			::= { sleRapsRingNotification 7 }

		
--   1.3.6.1.4.1.6296.101.4.15.3.8
-- 1.3.6.1.4.1.6296.101.4.15.3.8
		-- 1.3.6.1.4.1.6296.101.4.15.3.8
		sleRapsRingIcPortCreated NOTIFICATION-TYPE
			OBJECTS { sleRapsRingControlRequest, sleRapsRingControlTimeStamp, sleRapsRingControlReqResult, sleRapsRingControlIcNode, sleRapsRingControlParamPort, 
				sleRapsRingControlInstId }
			STATUS current
			DESCRIPTION 
				"setRapsRingIcPort"
			::= { sleRapsRingNotification 8 }

		
--   1.3.6.1.4.1.6296.101.4.15.3.9
-- 1.3.6.1.4.1.6296.101.4.15.3.9
		-- 1.3.6.1.4.1.6296.101.4.15.3.9
		sleRapsRingIcPortDestroyed NOTIFICATION-TYPE
			OBJECTS { sleRapsRingControlRequest, sleRapsRingControlTimeStamp, sleRapsRingControlReqResult, sleRapsRingControlId }
			STATUS current
			DESCRIPTION 
				"destroyRapsRingIcPort"
			::= { sleRapsRingNotification 9 }

		
--   1.3.6.1.4.1.6296.101.4.15.3.10
-- 1.3.6.1.4.1.6296.101.4.15.3.10
		-- 1.3.6.1.4.1.6296.101.4.15.3.10
		sleRapsRingMultipleFailureChanged NOTIFICATION-TYPE
			OBJECTS { sleRapsRingControlRequest, sleRapsRingControlTimeStamp, sleRapsRingControlReqResult, sleRapsRingControlInstId, sleRapsRingControlMultipleFailure
				 }
			STATUS current
			DESCRIPTION 
				"setRapsRingMultipleFailure"
			::= { sleRapsRingNotification 10 }

		
--   1.3.6.1.4.1.6296.101.4.15.3.11
-- 1.3.6.1.4.1.6296.101.4.15.3.11
		-- 1.3.6.1.4.1.6296.101.4.15.3.11
		sleRapsRingPropagateTcChanged NOTIFICATION-TYPE
			OBJECTS { sleRapsRingControlRequest, sleRapsRingControlTimeStamp, sleRapsRingControlReqResult, sleRapsRingControlInstId, sleRapsRingControlPropagateTc
				 }
			STATUS current
			DESCRIPTION 
				"setRapsRingPropagateTc"
			::= { sleRapsRingNotification 11 }

		
--   1.3.6.1.4.1.6296.101.4.15.3.12
-- 1.3.6.1.4.1.6296.101.4.15.3.12
		-- 1.3.6.1.4.1.6296.101.4.15.3.12
		sleRapsRingNonRevertiveChanged NOTIFICATION-TYPE
			OBJECTS { sleRapsRingControlRequest, sleRapsRingControlTimeStamp, sleRapsRingControlReqResult, sleRapsRingControlInstId, sleRapsRingControlNonRevertive
				 }
			STATUS current
			DESCRIPTION 
				"setRapsRingNonRevertive"
			::= { sleRapsRingNotification 12 }

		
--   1.3.6.1.4.1.6296.101.4.15.3.13
-- 1.3.6.1.4.1.6296.101.4.15.3.13
		-- 1.3.6.1.4.1.6296.101.4.15.3.13
		sleRapsRingForcedSwitchChanged NOTIFICATION-TYPE
			OBJECTS { sleRapsRingControlRequest, sleRapsRingControlTimeStamp, sleRapsRingControlReqResult, sleRapsRingControlInstId, sleRapsRingControlParamPort
				 }
			STATUS current
			DESCRIPTION 
				"setRapsRingForcedSwitch"
			::= { sleRapsRingNotification 13 }

		
--   1.3.6.1.4.1.6296.101.4.15.3.14
-- 1.3.6.1.4.1.6296.101.4.15.3.14
		-- 1.3.6.1.4.1.6296.101.4.15.3.14
		sleRapsRingManualSwitchChanged NOTIFICATION-TYPE
			OBJECTS { sleRapsRingControlRequest, sleRapsRingControlTimeStamp, sleRapsRingControlReqResult, sleRapsRingControlInstId, sleRapsRingControlParamPort
				 }
			STATUS current
			DESCRIPTION 
				"setRapsRingManualSwitch"
			::= { sleRapsRingNotification 14 }

		
--   1.3.6.1.4.1.6296.101.4.15.3.15
-- 1.3.6.1.4.1.6296.101.4.15.3.15
		-- 1.3.6.1.4.1.6296.101.4.15.3.15
		sleRapsRingSwitchCleared NOTIFICATION-TYPE
			OBJECTS { sleRapsRingControlRequest, sleRapsRingControlTimeStamp, sleRapsRingControlReqResult, sleRapsRingControlInstId }
			STATUS current
			DESCRIPTION 
				"setRapsRingClearSwitch"
			::= { sleRapsRingNotification 15 }

		
--   1.3.6.1.4.1.6296.101.4.15.3.16
-- 1.3.6.1.4.1.6296.101.4.15.3.16
		-- 1.3.6.1.4.1.6296.101.4.15.3.16
		sleRapsRingHoldOffTimeChanged NOTIFICATION-TYPE
			OBJECTS { sleRapsRingControlRequest, sleRapsRingControlTimeStamp, sleRapsRingControlReqResult, sleRapsRingControlInstId, sleRapsRingControlHoldOffTime
				 }
			STATUS current
			DESCRIPTION 
				"setRapsRingHoldOffTime"
			::= { sleRapsRingNotification 16 }

		
--   1.3.6.1.4.1.6296.101.4.15.3.17
-- 1.3.6.1.4.1.6296.101.4.15.3.17
		-- 1.3.6.1.4.1.6296.101.4.15.3.17
		sleRapsRingGuardTimeChanged NOTIFICATION-TYPE
			OBJECTS { sleRapsRingControlRequest, sleRapsRingControlTimeStamp, sleRapsRingControlReqResult, sleRapsRingControlInstId, sleRapsRingControlGuardTime
				 }
			STATUS current
			DESCRIPTION 
				"setRapsRingGuardTime"
			::= { sleRapsRingNotification 17 }

		
--   1.3.6.1.4.1.6296.101.4.15.3.18
-- 1.3.6.1.4.1.6296.101.4.15.3.18
		-- 1.3.6.1.4.1.6296.101.4.15.3.18
		sleRapsRingWtrTimeChanged NOTIFICATION-TYPE
			OBJECTS { sleRapsRingControlRequest, sleRapsRingControlTimeStamp, sleRapsRingControlReqResult, sleRapsRingControlInstId, sleRapsRingControlWaitToRestore
				 }
			STATUS current
			DESCRIPTION 
				"setRapsRingWtrTime"
			::= { sleRapsRingNotification 18 }

		
--   1.3.6.1.4.1.6296.101.4.15.3.19
-- 1.3.6.1.4.1.6296.101.4.15.3.19
		-- 1.3.6.1.4.1.6296.101.4.15.3.19
		sleRapsRingWtbTimeChanged NOTIFICATION-TYPE
			OBJECTS { sleRapsRingControlRequest, sleRapsRingControlTimeStamp, sleRapsRingControlReqResult, sleRapsRingControlInstId, sleRapsRingControlWaitToBlock
				 }
			STATUS current
			DESCRIPTION 
				"setRapsRingWtbTime"
			::= { sleRapsRingNotification 19 }

		
--   1.3.6.1.4.1.6296.101.4.15.3.20
-- 1.3.6.1.4.1.6296.101.4.15.3.20
		-- 1.3.6.1.4.1.6296.101.4.15.3.20
		sleRapsRingPassThroughChanged NOTIFICATION-TYPE
			OBJECTS { sleRapsRingControlRequest, sleRapsRingControlTimeStamp, sleRapsRingControlReqResult, sleRapsRingControlInstId, sleRapsRingControlPassThrough
				 }
			STATUS current
			DESCRIPTION 
				"setRapsRingPassThrough"
			::= { sleRapsRingNotification 20 }

		
--   1.3.6.1.4.1.6296.101.4.15.3.21
-- 1.3.6.1.4.1.6296.101.4.15.3.21
		-- 1.3.6.1.4.1.6296.101.4.15.3.21
		sleRapsRingVrfTimeChanged NOTIFICATION-TYPE
			OBJECTS { sleRapsRingControlRequest, sleRapsRingControlTimeStamp, sleRapsRingControlReqResult, sleRapsRingControlInstId, sleRapsRingControlVerifiedTime
				 }
			STATUS current
			DESCRIPTION 
				"setRapsRingVrfTime"
			::= { sleRapsRingNotification 21 }

		
		-- 1.3.6.1.4.1.6296.101.4.16
		sleFaultMonitor OBJECT IDENTIFIER ::= { sleFaultMgmt 16 }

		
		-- 1.3.6.1.4.1.6296.101.4.16.1
		sleFaultMonitorGlobal OBJECT IDENTIFIER ::= { sleFaultMonitor 1 }

		
--   1.3.6.1.4.1.6296.101.4.1.1
-- 1.3.6.1.4.1.6296.101.4.1.1
		-- 1.3.6.1.4.1.6296.101.4.16.1.1
		sleFaultMonitorGlobalBase OBJECT IDENTIFIER ::= { sleFaultMonitorGlobal 1 }

		
		-- 1.3.6.1.4.1.6296.101.4.16.1.1.1
		sleFaultMonitorGlobalInspectInterval OBJECT-TYPE
			SYNTAX INTEGER (3..86400)
			MAX-ACCESS read-only
			STATUS current
			DESCRIPTION
				"daemon Inspection value.
unit : sec, default : 5
				"
			::= { sleFaultMonitorGlobalBase 1 }

		
		-- 1.3.6.1.4.1.6296.101.4.16.1.1.2
		sleFaultMonitorGlobalStartupThreshold OBJECT-TYPE
			SYNTAX INTEGER (100..1000)
			MAX-ACCESS read-only
			STATUS current
			DESCRIPTION
				"daemon startup threshold value.
unit : sec, default : 100
				
				"
			::= { sleFaultMonitorGlobalBase 2 }

		
		-- 1.3.6.1.4.1.6296.101.4.16.1.1.3
		sleFaultMonitorGlobalNoKeepalive OBJECT-TYPE
			SYNTAX INTEGER
				{
				log(1),
				resetMate(2)
				}
			MAX-ACCESS read-only
			STATUS current
			DESCRIPTION
				"Indicate action when don't receive keepalive msg.
				"
			::= { sleFaultMonitorGlobalBase 3 }

		
--   1.3.6.1.4.1.6296.101.4.1.2
-- 1.3.6.1.4.1.6296.101.4.1.2
		-- 1.3.6.1.4.1.6296.101.4.16.1.2
		sleFaultMonitorGlobalControl OBJECT IDENTIFIER ::= { sleFaultMonitorGlobal 2 }

		
		-- 1.3.6.1.4.1.6296.101.4.16.1.2.1
		sleFaultMonitorGlobalControlRequest OBJECT-TYPE
			SYNTAX INTEGER
				{
				setGlobalInspectInterval(1),
				setGlobalStartupThreshold(2),
				setNoKeepaliveAction(3)
				}
			MAX-ACCESS read-write
			STATUS current
			DESCRIPTION			" "
			::= { sleFaultMonitorGlobalControl 1 }

		
		-- 1.3.6.1.4.1.6296.101.4.16.1.2.2
		sleFaultMonitorGlobalControlStatus OBJECT-TYPE
			SYNTAX SleControlStatusType
			MAX-ACCESS read-only
			STATUS current
			DESCRIPTION
				" The status of a control request. "
			::= { sleFaultMonitorGlobalControl 2 }

		
		-- 1.3.6.1.4.1.6296.101.4.16.1.2.3
		sleFaultMonitorGlobalControlTimer OBJECT-TYPE
			SYNTAX Unsigned32
			MAX-ACCESS read-write
			STATUS current
			DESCRIPTION
				" The maximum wait time for the manager for command ending.
				For long running commands.
				The manager reads this value from the DSLAM. "
			::= { sleFaultMonitorGlobalControl 3 }

		
		-- 1.3.6.1.4.1.6296.101.4.16.1.2.4
		sleFaultMonitorGlobalControlTimeStamp OBJECT-TYPE
			SYNTAX TimeTicks
			MAX-ACCESS read-only
			STATUS current
			DESCRIPTION
				" The time stamp of the last command (end of command). "
			::= { sleFaultMonitorGlobalControl 4 }

		
		-- 1.3.6.1.4.1.6296.101.4.16.1.2.5
		sleFaultMonitorGlobalControlReqResult OBJECT-TYPE
			SYNTAX SleControlRequestResultType
			MAX-ACCESS read-only
			STATUS current
			DESCRIPTION
				" The result of the last user command. "
			::= { sleFaultMonitorGlobalControl 5 }

		
		-- 1.3.6.1.4.1.6296.101.4.16.1.2.6
		sleFaultMonitorGlobalControlInspectInterval OBJECT-TYPE
			SYNTAX INTEGER (3..86400)
			MAX-ACCESS read-write
			STATUS current
			DESCRIPTION
				"daemon Inspection value.
unit : sec, default : 5
				"
			::= { sleFaultMonitorGlobalControl 6 }

		
		-- 1.3.6.1.4.1.6296.101.4.16.1.2.7
		sleFaultMonitorGlobalControlStartupThreshold OBJECT-TYPE
			SYNTAX INTEGER (100..1000)
			MAX-ACCESS read-write
			STATUS current
			DESCRIPTION
				"daemon startup threshold value.
unit : sec, default : 100
				"
			::= { sleFaultMonitorGlobalControl 7 }

		
		-- 1.3.6.1.4.1.6296.101.4.16.1.2.8
		sleFaultMonitorGlobalControlNoKeepalive OBJECT-TYPE
			SYNTAX INTEGER
				{
				log(1),
				switchover(2)
				}
			MAX-ACCESS read-write
			STATUS current
			DESCRIPTION
				"Indicate action when don't receive keepalive msg.
				"
			::= { sleFaultMonitorGlobalControl 8 }

		
--   1.3.6.1.4.1.6296.101.4.1.3
-- 1.3.6.1.4.1.6296.101.4.1.3
		-- 1.3.6.1.4.1.6296.101.4.16.1.3
		sleFaultMonitorGlobalNotification OBJECT IDENTIFIER ::= { sleFaultMonitorGlobal 3 }

		
--   1.3.6.1.4.1.6296.101.4.1.3.1
-- 1.3.6.1.4.1.6296.101.4.1.3.1
		-- 1.3.6.1.4.1.6296.101.4.16.1.3.1
		setFaultMonitorGlobalInspectIntervalChanged NOTIFICATION-TYPE
			OBJECTS { sleFaultMonitorGlobalControlRequest, sleFaultMonitorGlobalControlTimeStamp, sleFaultMonitorGlobalControlReqResult, sleFaultMonitorGlobalControlInspectInterval }
			STATUS current
			DESCRIPTION 
				"Description."
			::= { sleFaultMonitorGlobalNotification 1 }

		
--   1.3.6.1.4.1.6296.101.4.1.3.2
-- 1.3.6.1.4.1.6296.101.4.1.3.2
		-- 1.3.6.1.4.1.6296.101.4.16.1.3.2
		setFaultMonitorGlobalStartupThresholdChanged NOTIFICATION-TYPE
			OBJECTS { sleFaultMonitorGlobalControlRequest, sleFaultMonitorGlobalControlTimeStamp, sleFaultMonitorGlobalControlReqResult, sleFaultMonitorGlobalControlStartupThreshold }
			STATUS current
			DESCRIPTION 
				"Description."
			::= { sleFaultMonitorGlobalNotification 2 }

		
--   1.3.6.1.4.1.6296.101.4.1.3.3
-- 1.3.6.1.4.1.6296.101.4.1.3.3
		-- 1.3.6.1.4.1.6296.101.4.16.1.3.3
		setFaultMonitorGlobalNoKeepaliveActionChanged NOTIFICATION-TYPE
			OBJECTS { sleFaultMonitorGlobalControlRequest, sleFaultMonitorGlobalControlTimeStamp, sleFaultMonitorGlobalControlReqResult, sleFaultMonitorGlobalControlNoKeepalive }
			STATUS current
			DESCRIPTION 
				"Description."
			::= { sleFaultMonitorGlobalNotification 3 }

		
		-- 1.3.6.1.4.1.6296.101.4.16.2
		sleFaultMonitorDaemonConfig OBJECT IDENTIFIER ::= { sleFaultMonitor 2 }

		
		-- 1.3.6.1.4.1.6296.101.4.16.2.1
		sleFaultMonitorDaemonTable OBJECT-TYPE
			SYNTAX SEQUENCE OF SleFaultMonitorDaemonEntry
			MAX-ACCESS not-accessible
			STATUS current
			DESCRIPTION
				"Description."
			::= { sleFaultMonitorDaemonConfig 1 }

		
		-- 1.3.6.1.4.1.6296.101.4.16.2.1.1
		sleFaultMonitorDaemonEntry OBJECT-TYPE
			SYNTAX SleFaultMonitorDaemonEntry
			MAX-ACCESS not-accessible
			STATUS current
			DESCRIPTION
				"Description."
			INDEX { sleFaultMonitorDaemonPid }
			::= { sleFaultMonitorDaemonTable 1 }

		
		SleFaultMonitorDaemonEntry ::=
			SEQUENCE { 
				sleFaultMonitorDaemonName
					OCTET STRING,
				sleFaultMonitorDaemonPid
					Integer32,
				sleFaultMonitorDaemonAdminStatus
					INTEGER,
				sleFaultMonitorDaemonCrashAction
					INTEGER,
				sleFaultMonitorDaemonTimeoutAction
					INTEGER,
				sleFaultMonitorDaemonThreshold
					Integer32,
				sleFaultMonitorDaemonThresholded
					Integer32,
				sleFaultMonitorDaemonStartupThresholded
					Integer32,
				sleFaultMonitorDaemonWatchdogAdminStatus
					INTEGER,
				sleFaultMonitorDaemonWatchdogThreshold
					Integer32,
				sleFaultMonitorDaemonWatchdogCount
					Integer32
			 }

		-- 1.3.6.1.4.1.6296.101.4.16.2.1.1.1
		sleFaultMonitorDaemonName OBJECT-TYPE
			SYNTAX OCTET STRING
			MAX-ACCESS read-only
			STATUS current
			DESCRIPTION
				"Daemon name"
			::= { sleFaultMonitorDaemonEntry 1 }

		
		-- 1.3.6.1.4.1.6296.101.4.16.2.1.1.2
		sleFaultMonitorDaemonPid OBJECT-TYPE
			SYNTAX Integer32 (1..65535)
			MAX-ACCESS read-only
			STATUS current
			DESCRIPTION
				"Daemon PID
				"
			::= { sleFaultMonitorDaemonEntry 2 }

		
		-- 1.3.6.1.4.1.6296.101.4.16.2.1.1.3
		sleFaultMonitorDaemonAdminStatus OBJECT-TYPE
			SYNTAX INTEGER
				{
				enable(1),
				disable(2)
				}
			MAX-ACCESS read-only
			STATUS current
			DESCRIPTION
				"Daemon Inspection admin status.
				"
			::= { sleFaultMonitorDaemonEntry 3 }

		
		-- 1.3.6.1.4.1.6296.101.4.16.2.1.1.4
		sleFaultMonitorDaemonCrashAction OBJECT-TYPE
			SYNTAX INTEGER
				{
				log(1),
				restart(2),
				switchover(3)
				}
			MAX-ACCESS read-only
			STATUS current
			DESCRIPTION
				"Indicate action type when daemon is crashed
				"
			::= { sleFaultMonitorDaemonEntry 4 }

		
		-- 1.3.6.1.4.1.6296.101.4.16.2.1.1.5
		sleFaultMonitorDaemonTimeoutAction OBJECT-TYPE
			SYNTAX INTEGER
				{
				log(1),
				restart(2),
				switchover(3)
				}
			MAX-ACCESS read-only
			STATUS current
			DESCRIPTION
				"Indicate action type when daemon is timeout
				"
			::= { sleFaultMonitorDaemonEntry 5 }

		
		-- 1.3.6.1.4.1.6296.101.4.16.2.1.1.6
		sleFaultMonitorDaemonThreshold OBJECT-TYPE
			SYNTAX Integer32 (1..10)
			MAX-ACCESS read-only
			STATUS current
			DESCRIPTION
				"Indicate fault admin threshold.
				"
			::= { sleFaultMonitorDaemonEntry 6 }

		
		-- 1.3.6.1.4.1.6296.101.4.16.2.1.1.7
		sleFaultMonitorDaemonThresholded OBJECT-TYPE
			SYNTAX Integer32
			MAX-ACCESS read-only
			STATUS current
			DESCRIPTION
				"Indicate fault accumulated threshold.
				"
			::= { sleFaultMonitorDaemonEntry 7 }

		
		-- 1.3.6.1.4.1.6296.101.4.16.2.1.1.8
		sleFaultMonitorDaemonStartupThresholded OBJECT-TYPE
			SYNTAX Integer32
			MAX-ACCESS read-only
			STATUS current
			DESCRIPTION
				"Description."
			::= { sleFaultMonitorDaemonEntry 8 }

		
		-- 1.3.6.1.4.1.6296.101.4.16.2.1.1.9
		sleFaultMonitorDaemonWatchdogAdminStatus OBJECT-TYPE
			SYNTAX INTEGER
				{
				enable(1),
				disable(2)
				}
			MAX-ACCESS read-only
			STATUS current
			DESCRIPTION
				"Indicate whether connect watchdog or not
				"
			::= { sleFaultMonitorDaemonEntry 9 }

		
		-- 1.3.6.1.4.1.6296.101.4.16.2.1.1.10
		sleFaultMonitorDaemonWatchdogThreshold OBJECT-TYPE
			SYNTAX Integer32 (5..60)
			MAX-ACCESS read-only
			STATUS current
			DESCRIPTION
				"Indicate watchdog threshold of daemon.
				"
			::= { sleFaultMonitorDaemonEntry 10 }

		
		-- 1.3.6.1.4.1.6296.101.4.16.2.1.1.11
		sleFaultMonitorDaemonWatchdogCount OBJECT-TYPE
			SYNTAX Integer32
			MAX-ACCESS read-only
			STATUS current
			DESCRIPTION
				"Indicate watchdog accumulated count.
				"
			::= { sleFaultMonitorDaemonEntry 11 }

		
		-- 1.3.6.1.4.1.6296.101.4.16.2.2
		sleFaultMonitorDaemonControl OBJECT IDENTIFIER ::= { sleFaultMonitorDaemonConfig 2 }

		
		-- 1.3.6.1.4.1.6296.101.4.16.2.2.1
		sleFaultMonitorDaemonControlRequest OBJECT-TYPE
			SYNTAX INTEGER
				{
				setDaemonAdminStatus(1),
				setDaemonFaultAction(2),
				setDaemonThreshold(3),
				setDaemonWatchdog(4)
				}
			MAX-ACCESS read-write
			STATUS current
			DESCRIPTION			" "
			::= { sleFaultMonitorDaemonControl 1 }

		
		-- 1.3.6.1.4.1.6296.101.4.16.2.2.2
		sleFaultMonitorDaemonControlStatus OBJECT-TYPE
			SYNTAX SleControlStatusType
			MAX-ACCESS read-only
			STATUS current
			DESCRIPTION
				" The status of a control request. "
			::= { sleFaultMonitorDaemonControl 2 }

		
		-- 1.3.6.1.4.1.6296.101.4.16.2.2.3
		sleFaultMonitorDaemonControlTimer OBJECT-TYPE
			SYNTAX Unsigned32
			MAX-ACCESS read-write
			STATUS current
			DESCRIPTION
				" The maximum wait time for the manager for command ending.
				For long running commands.
				The manager reads this value from the DSLAM. "
			::= { sleFaultMonitorDaemonControl 3 }

		
		-- 1.3.6.1.4.1.6296.101.4.16.2.2.4
		sleFaultMonitorDaemonControlTimeStamp OBJECT-TYPE
			SYNTAX TimeTicks
			MAX-ACCESS read-only
			STATUS current
			DESCRIPTION
				" The time stamp of the last command (end of command). "
			::= { sleFaultMonitorDaemonControl 4 }

		
		-- 1.3.6.1.4.1.6296.101.4.16.2.2.5
		sleFaultMonitorDaemonControlReqResult OBJECT-TYPE
			SYNTAX SleControlRequestResultType
			MAX-ACCESS read-only
			STATUS current
			DESCRIPTION
				" The result of the last user command. "
			::= { sleFaultMonitorDaemonControl 5 }

		
		-- 1.3.6.1.4.1.6296.101.4.16.2.2.6
		sleFaultMonitorDaemonControlName OBJECT-TYPE
			SYNTAX OCTET STRING
			MAX-ACCESS read-write
			STATUS current
			DESCRIPTION
				"Description."
			::= { sleFaultMonitorDaemonControl 6 }

		
		-- 1.3.6.1.4.1.6296.101.4.16.2.2.7
		sleFaultMonitorDaemonControlAdminStatus OBJECT-TYPE
			SYNTAX INTEGER
				{
				enable(1),
				disable(2)
				}
			MAX-ACCESS read-write
			STATUS current
			DESCRIPTION
				"daemon Inspection value.
unit : sec, default : 5
				"
			::= { sleFaultMonitorDaemonControl 7 }

		
		-- 1.3.6.1.4.1.6296.101.4.16.2.2.8
		sleFaultMonitorDaemonControlCrashAction OBJECT-TYPE
			SYNTAX INTEGER
				{
				log(1),
				restart(2),
				switchover(3)
				}
			MAX-ACCESS read-write
			STATUS current
			DESCRIPTION
				"daemon startup threshold value.
unit : sec, default : 100
				"
			::= { sleFaultMonitorDaemonControl 8 }

		
		-- 1.3.6.1.4.1.6296.101.4.16.2.2.9
		sleFaultMonitorDaemonControlTimeoutAction OBJECT-TYPE
			SYNTAX INTEGER
				{
				log(1),
				restart(2),
				switchover(3)
				}
			MAX-ACCESS read-write
			STATUS current
			DESCRIPTION
				"Indicate action when don't receive keepalive msg.
				"
			::= { sleFaultMonitorDaemonControl 9 }

		
		-- 1.3.6.1.4.1.6296.101.4.16.2.2.10
		sleFaultMonitorDaemonControlThreshold OBJECT-TYPE
			SYNTAX Integer32 (1..10)
			MAX-ACCESS read-write
			STATUS current
			DESCRIPTION
				"Description."
			::= { sleFaultMonitorDaemonControl 10 }

		
		-- 1.3.6.1.4.1.6296.101.4.16.2.2.11
		sleFaultMonitorDaemonControlThreshed OBJECT-TYPE
			SYNTAX Integer32
			MAX-ACCESS read-write
			STATUS current
			DESCRIPTION
				"Description."
			::= { sleFaultMonitorDaemonControl 11 }

		
		-- 1.3.6.1.4.1.6296.101.4.16.2.2.12
		sleFaultMonitorDaemonControlStartupThresh OBJECT-TYPE
			SYNTAX Integer32
			MAX-ACCESS read-write
			STATUS current
			DESCRIPTION
				"Description."
			::= { sleFaultMonitorDaemonControl 12 }

		
		-- 1.3.6.1.4.1.6296.101.4.16.2.2.13
		sleFaultMonitorDaemonControlWatchdogAdminStatus OBJECT-TYPE
			SYNTAX INTEGER
				{
				enable(1),
				disable(2)
				}
			MAX-ACCESS read-write
			STATUS current
			DESCRIPTION
				"Description."
			::= { sleFaultMonitorDaemonControl 13 }

		
		-- 1.3.6.1.4.1.6296.101.4.16.2.2.14
		sleFaultMonitorDaemonControlWatchdogThreshold OBJECT-TYPE
			SYNTAX Integer32 (5..60)
			MAX-ACCESS read-write
			STATUS current
			DESCRIPTION
				"Description."
			::= { sleFaultMonitorDaemonControl 14 }

		
		-- 1.3.6.1.4.1.6296.101.4.16.2.4
		sleFaultMonitorDaemonNotification OBJECT IDENTIFIER ::= { sleFaultMonitorDaemonConfig 4 }

		
		-- 1.3.6.1.4.1.6296.101.4.16.2.4.1
		setFaultMonitorDaemonAdminStatusChanged NOTIFICATION-TYPE
			OBJECTS { sleFaultMonitorDaemonControlRequest, sleFaultMonitorDaemonControlTimeStamp, sleFaultMonitorDaemonControlReqResult, sleFaultMonitorDaemonControlAdminStatus }
			STATUS current
			DESCRIPTION 
				"Description."
			::= { sleFaultMonitorDaemonNotification 1 }

		
		-- 1.3.6.1.4.1.6296.101.4.16.2.4.2
		setFaultMonitorDaemonFaultActionChanged NOTIFICATION-TYPE
			OBJECTS { sleFaultMonitorDaemonControlRequest, sleFaultMonitorDaemonControlTimeStamp, sleFaultMonitorDaemonControlReqResult, sleFaultMonitorDaemonControlCrashAction, sleFaultMonitorDaemonControlTimeoutAction
				 }
			STATUS current
			DESCRIPTION 
				"Description."
			::= { sleFaultMonitorDaemonNotification 2 }

		
		-- 1.3.6.1.4.1.6296.101.4.16.2.4.3
		setFaultMonitorDaemonThresholdChanged NOTIFICATION-TYPE
			OBJECTS { sleFaultMonitorDaemonControlRequest, sleFaultMonitorDaemonControlTimeStamp, sleFaultMonitorDaemonControlReqResult, sleFaultMonitorDaemonControlThreshold }
			STATUS current
			DESCRIPTION 
				"Description."
			::= { sleFaultMonitorDaemonNotification 3 }

		
		-- 1.3.6.1.4.1.6296.101.4.16.2.4.4
		setFaultMonitorDaemonWatchdogchanged NOTIFICATION-TYPE
			OBJECTS { sleFaultMonitorDaemonControlRequest, sleFaultMonitorDaemonControlTimeStamp, sleFaultMonitorDaemonControlReqResult, sleFaultMonitorDaemonControlWatchdogAdminStatus, sleFaultMonitorDaemonControlWatchdogThreshold
				 }
			STATUS current
			DESCRIPTION 
				"Description."
			::= { sleFaultMonitorDaemonNotification 4 }

		
		-- 1.3.6.1.4.1.6296.101.4.16.3
		sleFaultMonitor2pointsLinear OBJECT IDENTIFIER ::= { sleFaultMonitor 3 }

		
--   1.3.6.1.4.1.6296.101.4.1.1
-- 1.3.6.1.4.1.6296.101.4.1.1
		-- 1.3.6.1.4.1.6296.101.4.16.3.1
		sleFaultMonitor2pointsLinearInfo OBJECT IDENTIFIER ::= { sleFaultMonitor2pointsLinear 1 }

		
		-- 1.3.6.1.4.1.6296.101.4.16.3.1.1
		sleFaultMonitor2pointsLinearAdminStatus OBJECT-TYPE
			SYNTAX INTEGER
				{
				enable(1),
				disable(2)
				}
			MAX-ACCESS read-only
			STATUS current
			DESCRIPTION
				"Indicate whether 2-points-linear monitoring is enabled or not
				"
			::= { sleFaultMonitor2pointsLinearInfo 1 }

		
		-- 1.3.6.1.4.1.6296.101.4.16.3.1.2
		sleFaultMonitor2pointsLinearInterval OBJECT-TYPE
			SYNTAX Integer32 (1..10)
			MAX-ACCESS read-only
			STATUS current
			DESCRIPTION
				"Indicate 2-points-linear monitoring interval
default : 5, unit : sec
				
				
				"
			::= { sleFaultMonitor2pointsLinearInfo 2 }

		
		-- 1.3.6.1.4.1.6296.101.4.16.3.1.3
		sleFaultMonitor2pointsLinearThreshold OBJECT-TYPE
			SYNTAX Integer32 (1..60)
			MAX-ACCESS read-only
			STATUS current
			DESCRIPTION
				"Indicate 2-points-linear monitoring threshold

				default : 8 times
				"
			::= { sleFaultMonitor2pointsLinearInfo 3 }

		
--   1.3.6.1.4.1.6296.101.4.1.2
-- 1.3.6.1.4.1.6296.101.4.1.2
		-- 1.3.6.1.4.1.6296.101.4.16.3.2
		sleFaultMonitor2pointsLinearControl OBJECT IDENTIFIER ::= { sleFaultMonitor2pointsLinear 2 }

		
		-- 1.3.6.1.4.1.6296.101.4.16.3.2.1
		sleFaultMonitor2pointsLinearControlRequest OBJECT-TYPE
			SYNTAX INTEGER
				{
				set2PointsLinearAdminStatus(1),
				set2PointsLinearInterval(2),
				set2PointsLinearThreshold(3)
				}
			MAX-ACCESS read-write
			STATUS current
			DESCRIPTION			" "
			::= { sleFaultMonitor2pointsLinearControl 1 }

		
		-- 1.3.6.1.4.1.6296.101.4.16.3.2.2
		sleFaultMonitor2pointsLinearControlStatus OBJECT-TYPE
			SYNTAX SleControlStatusType
			MAX-ACCESS read-only
			STATUS current
			DESCRIPTION
				" The status of a control request. "
			::= { sleFaultMonitor2pointsLinearControl 2 }

		
		-- 1.3.6.1.4.1.6296.101.4.16.3.2.3
		sleFaultMonitor2pointsLinearControlTimer OBJECT-TYPE
			SYNTAX Unsigned32
			MAX-ACCESS read-write
			STATUS current
			DESCRIPTION
				" The maximum wait time for the manager for command ending.
				For long running commands.
				The manager reads this value from the DSLAM. "
			::= { sleFaultMonitor2pointsLinearControl 3 }

		
		-- 1.3.6.1.4.1.6296.101.4.16.3.2.4
		sleFaultMonitor2pointsLinearControlTimeStamp OBJECT-TYPE
			SYNTAX TimeTicks
			MAX-ACCESS read-only
			STATUS current
			DESCRIPTION
				" The time stamp of the last command (end of command). "
			::= { sleFaultMonitor2pointsLinearControl 4 }

		
		-- 1.3.6.1.4.1.6296.101.4.16.3.2.5
		sleFaultMonitor2pointsLinearControlReqResult OBJECT-TYPE
			SYNTAX SleControlRequestResultType
			MAX-ACCESS read-only
			STATUS current
			DESCRIPTION
				" The result of the last user command. "
			::= { sleFaultMonitor2pointsLinearControl 5 }

		
		-- 1.3.6.1.4.1.6296.101.4.16.3.2.6
		sleFaultMonitor2pointsLinearControlAdminStatus OBJECT-TYPE
			SYNTAX INTEGER
				{
				enable(1),
				disable(2)
				}
			MAX-ACCESS read-write
			STATUS current
			DESCRIPTION			" "
			::= { sleFaultMonitor2pointsLinearControl 6 }

		
		-- 1.3.6.1.4.1.6296.101.4.16.3.2.7
		sleFaultMonitor2PonitsLinearControlInterval OBJECT-TYPE
			SYNTAX Integer32 (1..10)
			MAX-ACCESS read-write
			STATUS current
			DESCRIPTION
				"Indicate 2-points-linear monitoring interval

				default : 5, unit : sec"
			::= { sleFaultMonitor2pointsLinearControl 7 }

		
		-- 1.3.6.1.4.1.6296.101.4.16.3.2.8
		sleFaultMonitor2PointsLinearControlThreshold OBJECT-TYPE
			SYNTAX Integer32 (1..10)
			MAX-ACCESS read-write
			STATUS current
			DESCRIPTION
				"Indicate 2-points-linear monitoring threshold

				default : 8 times
				"
			::= { sleFaultMonitor2pointsLinearControl 8 }

		
		-- 1.3.6.1.4.1.6296.101.4.16.3.3
		sleFaultMonitor2pointsLinearNotification OBJECT IDENTIFIER ::= { sleFaultMonitor2pointsLinear 3 }

		
		-- 1.3.6.1.4.1.6296.101.4.16.3.3.1
		sleFaultMonitor2PointsLinearAdminStatusChanged NOTIFICATION-TYPE
			OBJECTS { sleFaultMonitor2pointsLinearControlRequest, sleFaultMonitor2pointsLinearControlTimeStamp, sleFaultMonitor2pointsLinearControlReqResult, sleFaultMonitor2pointsLinearControlAdminStatus }
			STATUS current
			DESCRIPTION 
				"Description."
			::= { sleFaultMonitor2pointsLinearNotification 1 }

		
		-- 1.3.6.1.4.1.6296.101.4.16.3.3.2
		sleFaultMonitor2PointsLinearIntervalChanged NOTIFICATION-TYPE
			OBJECTS { sleFaultMonitor2pointsLinearControlRequest, sleFaultMonitor2pointsLinearControlTimeStamp, sleFaultMonitor2pointsLinearControlReqResult, sleFaultMonitor2PonitsLinearControlInterval }
			STATUS current
			DESCRIPTION 
				"Description."
			::= { sleFaultMonitor2pointsLinearNotification 2 }

		
		-- 1.3.6.1.4.1.6296.101.4.16.3.3.3
		sleFaultMonitor2PointsLinearThresholdChanged NOTIFICATION-TYPE
			OBJECTS { sleFaultMonitor2pointsLinearControlRequest, sleFaultMonitor2pointsLinearControlTimeStamp, sleFaultMonitor2pointsLinearControlReqResult, sleFaultMonitor2PointsLinearControlThreshold }
			STATUS current
			DESCRIPTION 
				"Description."
			::= { sleFaultMonitor2pointsLinearNotification 3 }

		
		-- 1.3.6.1.4.1.6296.101.4.16.4
		sleFaultMonitorRHM OBJECT IDENTIFIER ::= { sleFaultMonitor 4 }

		
		-- 1.3.6.1.4.1.6296.101.4.16.4.1
		sleFaultMonitorRHMInfo OBJECT IDENTIFIER ::= { sleFaultMonitorRHM 1 }

		
		-- 1.3.6.1.4.1.6296.101.4.16.4.1.1
		sleFaultMonitorRHMAdminStatus OBJECT-TYPE
			SYNTAX INTEGER
				{
				enable(1),
				disable(2)
				}
			MAX-ACCESS read-only
			STATUS current
			DESCRIPTION
				"The RHM admin status"
			::= { sleFaultMonitorRHMInfo 1 }

		
		-- 1.3.6.1.4.1.6296.101.4.16.4.1.2
		sleFaultMonitorRHMActionType OBJECT-TYPE
			SYNTAX INTEGER
				{
				log(1),
				switchover(2)
				}
			MAX-ACCESS read-only
			STATUS current
			DESCRIPTION
				"The RHM action type
				"
			::= { sleFaultMonitorRHMInfo 2 }

		
		-- 1.3.6.1.4.1.6296.101.4.16.4.1.3
		sleFaultMonitorRHMActionThreshold OBJECT-TYPE
			SYNTAX Integer32 (5..1000)
			MAX-ACCESS read-only
			STATUS current
			DESCRIPTION
				"The RHM action threshold
				"
			::= { sleFaultMonitorRHMInfo 3 }

		
		-- 1.3.6.1.4.1.6296.101.4.16.4.1.4
		sleFaultMonitorRHMRebootThreshold OBJECT-TYPE
			SYNTAX Integer32 (1..100)
			MAX-ACCESS read-only
			STATUS current
			DESCRIPTION
				"The RHM reboot threshold"
			::= { sleFaultMonitorRHMInfo 4 }

		
		-- 1.3.6.1.4.1.6296.101.4.16.4.1.5
		sleFaultMonitorRHMRecoveryTime OBJECT-TYPE
			SYNTAX Integer32 (10..14400)
			MAX-ACCESS read-only
			STATUS current
			DESCRIPTION
				"The RHM recovery time"
			::= { sleFaultMonitorRHMInfo 5 }

		
		-- 1.3.6.1.4.1.6296.101.4.16.4.1.6
		sleFaultMonitorRHMFaultCounter OBJECT-TYPE
			SYNTAX Integer32
			MAX-ACCESS read-only
			STATUS current
			DESCRIPTION
				"The RHM fault counter"
			::= { sleFaultMonitorRHMInfo 6 }

		
		-- 1.3.6.1.4.1.6296.101.4.16.4.1.7
		sleFaultMonitorRHMRebootCounter OBJECT-TYPE
			SYNTAX Integer32
			MAX-ACCESS read-only
			STATUS current
			DESCRIPTION
				"The RHM reboot counter"
			::= { sleFaultMonitorRHMInfo 7 }

		
		-- 1.3.6.1.4.1.6296.101.4.16.4.1.8
		sleFaultMonitorRHMInterval OBJECT-TYPE
			SYNTAX Integer32
			MAX-ACCESS read-only
			STATUS current
			DESCRIPTION
				"Description."
			::= { sleFaultMonitorRHMInfo 8 }

		
		-- 1.3.6.1.4.1.6296.101.4.16.4.1.9
		sleFaultMonitorRHMLiveThreshold OBJECT-TYPE
			SYNTAX Integer32
			MAX-ACCESS read-only
			STATUS current
			DESCRIPTION
				"Description."
			::= { sleFaultMonitorRHMInfo 9 }

		
		-- 1.3.6.1.4.1.6296.101.4.16.4.2
		sleFaultMonitorRHMHostTable OBJECT-TYPE
			SYNTAX SEQUENCE OF SleFaultMonitorRHMHostEntry
			MAX-ACCESS not-accessible
			STATUS current
			DESCRIPTION
				"Description."
			::= { sleFaultMonitorRHM 2 }

		
		-- 1.3.6.1.4.1.6296.101.4.16.4.2.1
		sleFaultMonitorRHMHostEntry OBJECT-TYPE
			SYNTAX SleFaultMonitorRHMHostEntry
			MAX-ACCESS not-accessible
			STATUS current
			DESCRIPTION
				"Description."
			INDEX { sleFaultMonitorRHMHostAddr }
			::= { sleFaultMonitorRHMHostTable 1 }

		
		SleFaultMonitorRHMHostEntry ::=
			SEQUENCE { 
				sleFaultMonitorRHMHostAddr
					IpAddress
			 }

		-- 1.3.6.1.4.1.6296.101.4.16.4.2.1.1
		sleFaultMonitorRHMHostAddr OBJECT-TYPE
			SYNTAX IpAddress
			MAX-ACCESS read-only
			STATUS current
			DESCRIPTION
				"The target host or gateway address of RHM
				"
			::= { sleFaultMonitorRHMHostEntry 1 }

		
--   1.3.6.1.4.1.6296.101.4.1.2
-- 1.3.6.1.4.1.6296.101.4.1.2
		-- 1.3.6.1.4.1.6296.101.4.16.4.3
		sleFaultMonitorRHMControl OBJECT IDENTIFIER ::= { sleFaultMonitorRHM 3 }

		
		-- 1.3.6.1.4.1.6296.101.4.16.4.3.1
		sleFaultMonitorRHMControlRequest OBJECT-TYPE
			SYNTAX INTEGER
				{
				setRHMStatus(1),
				setRHMActionThreshold(2),
				setRHMRebootThreshold(3),
				setInterval(4),
				setLiveThreshold(5),
				clearRHMHost(6),
				setRHMHost(7)
				}
			MAX-ACCESS read-write
			STATUS current
			DESCRIPTION			" "
			::= { sleFaultMonitorRHMControl 1 }

		
		-- 1.3.6.1.4.1.6296.101.4.16.4.3.2
		sleFaultMonitorRHMControlStatus OBJECT-TYPE
			SYNTAX SleControlStatusType
			MAX-ACCESS read-only
			STATUS current
			DESCRIPTION
				" The status of a control request. "
			::= { sleFaultMonitorRHMControl 2 }

		
		-- 1.3.6.1.4.1.6296.101.4.16.4.3.3
		sleFaultMonitorRHMControlTimer OBJECT-TYPE
			SYNTAX Unsigned32
			MAX-ACCESS read-write
			STATUS current
			DESCRIPTION
				" The maximum wait time for the manager for command ending.
				For long running commands.
				The manager reads this value from the DSLAM. "
			::= { sleFaultMonitorRHMControl 3 }

		
		-- 1.3.6.1.4.1.6296.101.4.16.4.3.4
		sleFaultMonitorRHMControlTimeStamp OBJECT-TYPE
			SYNTAX TimeTicks
			MAX-ACCESS read-only
			STATUS current
			DESCRIPTION
				" The time stamp of the last command (end of command). "
			::= { sleFaultMonitorRHMControl 4 }

		
		-- 1.3.6.1.4.1.6296.101.4.16.4.3.5
		sleFaultMonitorRHMControlReqResult OBJECT-TYPE
			SYNTAX SleControlRequestResultType
			MAX-ACCESS read-only
			STATUS current
			DESCRIPTION
				" The result of the last user command. "
			::= { sleFaultMonitorRHMControl 5 }

		
		-- 1.3.6.1.4.1.6296.101.4.16.4.3.6
		sleFaultMonitorRHMControlAdminStatus OBJECT-TYPE
			SYNTAX INTEGER
				{
				enable(1),
				disable(2)
				}
			MAX-ACCESS read-write
			STATUS current
			DESCRIPTION			" "
			::= { sleFaultMonitorRHMControl 6 }

		
		-- 1.3.6.1.4.1.6296.101.4.16.4.3.7
		sleFaultMonitorRHMControlActionType OBJECT-TYPE
			SYNTAX INTEGER
				{
				log(1),
				switchover(2)
				}
			MAX-ACCESS read-write
			STATUS current
			DESCRIPTION
				"Indicate 2-points-linear monitoring interval

				default : 5, unit : sec"
			::= { sleFaultMonitorRHMControl 7 }

		
		-- 1.3.6.1.4.1.6296.101.4.16.4.3.8
		sleFaultMonitorRHMControlActionThreshold OBJECT-TYPE
			SYNTAX Integer32 (5..1000)
			MAX-ACCESS read-write
			STATUS current
			DESCRIPTION
				"The RHM reboot threshold"
			::= { sleFaultMonitorRHMControl 8 }

		
		-- 1.3.6.1.4.1.6296.101.4.16.4.3.9
		sleFaultMonitorRHMControlRebootThreshold OBJECT-TYPE
			SYNTAX Integer32 (1..100)
			MAX-ACCESS read-write
			STATUS current
			DESCRIPTION
				"The RHM reboot threshold"
			::= { sleFaultMonitorRHMControl 9 }

		
		-- 1.3.6.1.4.1.6296.101.4.16.4.3.10
		sleFaultMonitorRHMControlRecoveryTime OBJECT-TYPE
			SYNTAX Integer32 (10..14400)
			MAX-ACCESS read-write
			STATUS current
			DESCRIPTION
				"The RHM recovery time"
			::= { sleFaultMonitorRHMControl 10 }

		
		-- 1.3.6.1.4.1.6296.101.4.16.4.3.11
		sleFaultMonitorRHMControlInterval OBJECT-TYPE
			SYNTAX Integer32
			MAX-ACCESS read-write
			STATUS current
			DESCRIPTION
				"Description."
			::= { sleFaultMonitorRHMControl 11 }

		
		-- 1.3.6.1.4.1.6296.101.4.16.4.3.12
		sleFaultMonitorRHMControlLiveThreshold OBJECT-TYPE
			SYNTAX Integer32
			MAX-ACCESS read-write
			STATUS current
			DESCRIPTION
				"Description."
			::= { sleFaultMonitorRHMControl 12 }

		
		-- 1.3.6.1.4.1.6296.101.4.16.4.3.13
		sleFaultMonitorRHMControlHostAddr OBJECT-TYPE
			SYNTAX IpAddress
			MAX-ACCESS read-write
			STATUS current
			DESCRIPTION
				"Description."
			::= { sleFaultMonitorRHMControl 13 }

		
		-- 1.3.6.1.4.1.6296.101.4.16.4.4
		sleFaultMonitorRHMNotification OBJECT IDENTIFIER ::= { sleFaultMonitorRHM 4 }

		
		-- 1.3.6.1.4.1.6296.101.4.16.4.4.1
		setRHMStatusChanged NOTIFICATION-TYPE
			OBJECTS { sleFaultMonitorRHMControlRequest, sleFaultMonitorRHMControlTimeStamp, sleFaultMonitorRHMControlReqResult, sleFaultMonitorRHMControlAdminStatus, sleFaultMonitorRHMControlActionType
				 }
			STATUS current
			DESCRIPTION 
				"Description."
			::= { sleFaultMonitorRHMNotification 1 }

		
		-- 1.3.6.1.4.1.6296.101.4.16.4.4.2
		setRHMActionThresholdChanged NOTIFICATION-TYPE
			OBJECTS { sleFaultMonitorRHMControlRequest, sleFaultMonitorRHMControlTimeStamp, sleFaultMonitorRHMControlReqResult, sleFaultMonitorRHMControlActionThreshold }
			STATUS current
			DESCRIPTION 
				"Description."
			::= { sleFaultMonitorRHMNotification 2 }

		
		-- 1.3.6.1.4.1.6296.101.4.16.4.4.3
		setRHMRebootThresholdChanged NOTIFICATION-TYPE
			OBJECTS { sleFaultMonitorRHMControlRequest, sleFaultMonitorRHMControlTimeStamp, sleFaultMonitorRHMControlReqResult, sleFaultMonitorRHMControlRebootThreshold }
			STATUS current
			DESCRIPTION 
				"Description."
			::= { sleFaultMonitorRHMNotification 3 }

		
		-- 1.3.6.1.4.1.6296.101.4.16.4.4.4
		setRHMHostAdded NOTIFICATION-TYPE
			OBJECTS { sleFaultMonitorRHMControlRequest, sleFaultMonitorRHMControlTimeStamp, sleFaultMonitorRHMControlReqResult, sleFaultMonitorRHMControlRebootThreshold }
			STATUS current
			DESCRIPTION 
				"Description."
			::= { sleFaultMonitorRHMNotification 4 }

		
		-- 1.3.6.1.4.1.6296.101.4.16.4.4.5
		setRHMHostCleared NOTIFICATION-TYPE
			OBJECTS { sleFaultMonitorRHMControlRequest, sleFaultMonitorRHMControlTimeStamp, sleFaultMonitorRHMControlReqResult, sleFaultMonitorRHMControlRebootThreshold }
			STATUS current
			DESCRIPTION 
				"Description."
			::= { sleFaultMonitorRHMNotification 5 }

		
--   1.3.6.1.4.1.6296.101.4.16
-- 1.3.6.1.4.1.6296.101.4.16
		-- 1.3.6.1.4.1.6296.101.4.17
		sleFaultMgmtGroup OBJECT-GROUP
			OBJECTS { sleFaultDefaultSeverity, sleFaultCriteriaSeverity, sleFaultNotifiyActivity, sleFaultControlRequest, sleFaultControlStatus, 
				sleFaultControlTimer, sleFaultControlTimeStamp, sleFaultControlReqResult, sleFaultControlDefaultSeverity, sleFaultControlCriteriaSeverity, 
				sleFaultControlNotifiyActivity, sleAlarmSeverityIndex, sleAlarmSeverityValue, sleAlarmSeverityControlRequest, sleAlarmSeverityControlStatus, 
				sleAlarmSeverityControlTimer, sleAlarmSeverityControlTimeStamp, sleAlarmSeverityControlReqResult, sleAlarmSeverityControlIndex, sleAlarmSeverityControlValue, 
				sleAlarmSpecificCode, sleAlarmReportingSourceType, sleAlarmReportingSource, sleAlarmSpecificSeverity, sleAlarmSpecificProblem, 
				sleAlarmSpecificProblemText, sleAlarmTimeAndDate, sleAlarmHistoryIndex, sleAlarmHistorySpecific, sleAlarmHistorySeverity, 
				sleAlarmHistoryText, sleAlarmHistoryTime, sleAlarmHistoryControlRequest, sleAlarmHistoryControlStatus, sleAlarmHistoryControlTimer, 
				sleAlarmHistoryControlTimeStamp, sleAlarmHistoryControlReqResult, sleOamPortIndex, sleOamMuxAction, sleOamParAction, 
				sleOamAdminState, sleOamMode, sleOamUnidirectionMode, sleOamFunctionsSupported, sleOamPeerStatus, 
				sleOamPeerMacAddress, sleOamPeerMode, sleOamPeerFunctionsSupported, sleOamRemLoopback, sleOamControlRequest, 
				sleOamControlStatus, sleOamControlTimer, sleOamControlTimeStamp, sleOamControlReqResult, sleOamControlIndex, 
				sleOamControlPortAdminState, sleOamControlPortMode, sleOamControlPortUnidirectionMode, sleOamControlPortRemLoopback, sleAdvaFSPOperationMode, 
				sleAdvaActiveNetworkInterface, sleAdvaForceNetworkInterface, sleAdvaReportingInterval, sleAdvaNEMIFitted, sleAdvaForceReset, 
				sleAdvaManagerAddress, sleAdvaMinRailVoltageThreshold, sleAdvaMaxRailVoltageThreshold, sleAdvaTemperatureThreshold, sleAdvaPartNumber, 
				sleAdvaSerialNumber, sleAdvaFirmwareVersion, sleAdvaFPGAVersion, sleAdvaHardwareRevision, sleAdvaCLEICode, 
				sleAdvaTemperature, sleAdvaRailVoltage, sleAdvaPSUStates, sleAdvaPSUType, sleAdvaFansFitted, 
				sleAdvaFanState, sleAdvaTransmitMode, sleAdvaSystemControlRequest, sleAdvaSystemControlStatus, sleAdvaSystemControlTimer, 
				sleAdvaSystemControlTimeStamp, sleAdvaSystemControlReqResult, sleAdvaSystemControlPortIndex, sleAdvaSystemControlFSPOperationMode, sleAdvaSystemControlForceNetworkInterface, 
				sleAdvaSystemControlReportingInterval, sleAdvaSystemControlForceReset, sleAdvaSystemControlMinRailVoltageThreshold, sleAdvaSystemControlMaxRailVoltageThreshold, sleAdvaSystemControlTemperatureThreshold, 
				sleAdvaSystemControlTransmitMode, sleAdvaRemInstance, sleAdvaOperationalStatus, sleAdvaLineSpeed, sleAdvaMACAddress, 
				sleAdvaConnectorType, sleAdvaAutonegiotation, sleAdvaLinkLossForwarding, sleAdvaAdminState, sleAdvaRemoteInterfaceIndex, 
				sleAdvaUserDefinedString, sleAdvaRemoteSignalling, sleAdvaConfiguration, sleAdvaLocalTechnologyAbility, sleAdvaAdvertisedTechnologyAbility, 
				sleAdvaReceivedTechnologyAbility, sleAdvaLocalSectorAbility, sleAdvaAdvertisedSectorAbility, sleAdvaReceivedSectorAbility, sleAdvaDuplexCapabilities, 
				sleAdvaPHYType, sleAdvaPHYTypeList, sleAdvaMIIDetect, sleAdvaPHYState, sleAdvaGoodFramesTransmitted, 
				sleAdvaSingleCollisionFrames, sleAdvaMultipleCollisionFrames, sleAdvaGoodFramesReceived, sleAdvaFCSErrors, sleAdvaAlignmentErrors, 
				sleAdvaFramesTooLong, sleAdvaBytesTransmitted, sleAdvaBytesReceived, sleAdvaSymbolErrors, sleAdvaGeneralControlRequest, 
				sleAdvaGeneralControlStatus, sleAdvaGeneralControlTimer, sleAdvaGeneralControlTimeStamp, sleAdvaGeneralControlReqResult, sleAdvaGeneralControlPortIndex, 
				sleAdvaGeneralControlRemInstance, sleAdvaGeneralControlLineSpeed, sleAdvaGeneralControlAutonegiotation, sleAdvaGeneralControlLinkLossForwarding, sleAdvaGeneralControlUserDefinedString, 
				sleAdvaGeneralControlAdvertisedTechnologyAbility, sleAdvaGeneralControlAdvertisedSectorAbility, sleAdvaModuleType, sleAdvaModulePartNumber, sleAdvaModuleSerialNumber, 
				sleAdvaModuleFirmwareVersion, sleAdvaModuleSoftwareVersion, sleAdvaModuleHardwareRevision, sleAdvaModuleCLEICode, sleAdvaOpticalThresholdLevel, 
				sleAdvaLinkLength1, sleAdvaLinkLength2, sleAdvaLinkLength3, sleAdvaLinkLength4, sleAdvaLinkLengthCu, 
				sleAdvaWaveLength, sleAdvaLaserBias, sleAdvaTransmitPower, sleAdvaReceivePower, sleAdvaLaserTxTemperature, 
				sleAdvaOpticalControlRequest, sleAdvaOpticalControlStatus, sleAdvaOpticalControlTimer, sleAdvaOpticalControlTimeStamp, sleAdvaOpticalControlReqResult, 
				sleAdvaOpticalControlPortIndex, sleAdvaOpticalControlRemInstance, sleAdvaOpticalControlThresholdLevel, sleAdvaAdminStatus, sleAdvaMode, 
				sleAdvaRemMACAddress, sleAdvaRemConfig, sleAdvaRemPduConfig, sleAdvaLocFlags, sleAdvaRemFlags, 
				sleAdvaRemState, sleAdvaRemVendorOUI, sleAdvaRemDeviceNumber, sleAdvaRemVendorVersion, sleAdvaLocErrSymbolPeriodEventConfig, 
				sleAdvaLocErrFrameEventConfig, sleAdvaLocErrFramePeriodEventConfig, sleAdvaLocErrFrameSecsSummaryEventConfig, sleAdvaPDUsTx, sleAdvaPDUsRx, 
				sleAdvaUnsupportedCodesRx, sleAdvaInfoPDUsTx, sleAdvaInfoPDUsRx, sleAdvaEventNotificationPDUsTx, sleAdvaUniqueEventNotificationPDUsTx, 
				sleAdvaDupEventNotificationPDUsTx, sleAdvaLoopbackControlPDUsTx, sleAdvaLoopbackControlPDUsRx, sleAdvaVariableRequestPDUsTx, sleAdvaVariableRequestPDUsRx, 
				sleAdvaVariableResponsePDUsTx, sleAdvaVariableResponsePDUsRx, sleAdvaVendorPDUsTx, sleAdvaVendorPDUsRx, sleAdvaRemFramesLostDuetoOAMErr, 
				sleAdvaLocErrSymbolPeriodEvent, sleAdvaLocErrFrameSecsEvent, sleAdvaLocErrFramePeriodEvent, sleAdvaLocErrFrameSecsSummaryEvent, sleAdvaRemErrSymbolPeriodEvent, 
				sleAdvaRemErrFrameSecsEvent, sleAdvaRemoteErrorFramePeriodEvent, sleAdvaRemoteErrorFrameSecsSummaryEvent, sleAdvaOamControlRequest, sleAdvaOamControlStatus, 
				sleAdvaOamControlTimer, sleAdvaOamControlTimeStamp, sleAdvaOamControlReqResult, sleAdvaOamControlPortIndex, sleAdvaOamControlRemInstance, 
				sleAdvaOamControlAdminStatus, sleAlarmHistorySeqNum, sleAlarmSpecificSeqNum, sleFaultNextSeqNum, sleAlarmLEDType, 
				sleAlarmLEDStatus, sleAlarmLEDLevel, sleAlarmLEDLevelIndex, sleAlarmLEDLevelBlock, sleAlarmLEDControlRequest, 
				sleAlarmLEDControlStatus, sleAlarmLEDControlTimer, sleAlarmLEDControlTimeStamp, sleAlarmLEDControlReqResult, sleAlarmLEDControlType, 
				sleAlarmLEDControlLevel, sleAlarmLEDControlBlock, sleAlarmLEDLevelOperStatus, sleY1731Enable, sleY1731TrunkEnable, 
				sleY1731LtrCacheHoldTime, sleY1731LtrCacheSize, sleY1731SnmpServerTraps, sleY1731XcheckStartDelay, sleY1731DefaultMegLevel, 
				sleY1731DefaultMegMhfCreation, sleY1731PduToCfm, sleY1731DedicatedVlan, sleY1731BaseControlRequest, sleY1731BaseControlStatus, 
				sleY1731BaseControlTimer, sleY1731BaseControlTimeStamp, sleY1731BaseControlReqResult, sleY1731BaseControlEnable, sleY1731BaseControlTrunkEnable, 
				sleY1731BaseControlLtrCacheHoldTime, sleY1731BaseControlLtrCacheSize, sleY1731BaseControlSnmpServerTraps, sleY1731BaseControlXcheckStartDelay, sleY1731BaseControlDefaultMegLevel, 
				sleY1731BaseControlDefaultMegMhfCreation, sleY1731BaseControlPduToCfm, sleY1731BaseControlDedicatedVlan, sleY1731MegIndex, sleY1731MegName, 
				sleY1731MegLevel, sleY1731MegVid, sleY1731MegMepEnable, sleY1731MegCcEnable, sleY1731MegCcInterval, 
				sleY1731MegCcPriority, sleY1731MegCcLossThreshold, sleY1731MegCcHoldTime, sleY1731MegFaultPriority, sleY1731MegFaultKeepTime, 
				sleY1731MegFaultClearTime, sleY1731MegXcheckEnable, sleY1731MegAisEnable, sleY1731MegAisTransmitEnable, sleY1731MegAisInterval, 
				sleY1731MegAisLevel, sleY1731MegAisPriority, sleY1731MegLckEnable, sleY1731MegLckTransmitEnable, sleY1731MegLckInterval, 
				sleY1731MegLckLevel, sleY1731MegLckPriority, sleY1731MegOutOfService, sleY1731MegRapsEnable, sleY1731MegRapsRplOwner, 
				sleY1731MegRapsEastPort, sleY1731MegRapsWestPort, sleY1731MegRapsRplPort, sleY1731MegRapsHoldOffTime, sleY1731MegRapsGuardTime, 
				sleY1731MegRapsWaitToRestore, sleY1731MegRapsState, sleY1731MegControlRequest, sleY1731MegControlStatus, sleY1731MegControlTimer, 
				sleY1731MegControlTimeStamp, sleY1731MegControlReqResult, sleY1731MegControlIndex, sleY1731MegControlName, sleY1731MegControlLevel, 
				sleY1731MegControlVid, sleY1731MegControlMepEnable, sleY1731MegControlCcEnable, sleY1731MegControlCcInterval, sleY1731MegControlCcPriority, 
				sleY1731MegControlCcLossThreshold, sleY1731MegControlCcHoldTime, sleY1731MegControlFaultPriority, sleY1731MegControlFaultKeepTime, sleY1731MegControlFaultClearTime, 
				sleY1731MegControlXcheckEnable, sleY1731MegControlAisEnable, sleY1731MegControlAisTransmitEnable, sleY1731MegControlAisInterval, sleY1731MegControlAisLevel, 
				sleY1731MegControlAisPriority, sleY1731MegControlLckEnable, sleY1731MegControlLckTransmitEnable, sleY1731MegControlLckInterval, sleY1731MegControlLckLevel, 
				sleY1731MegControlLckPriority, sleY1731MegControlOutOfService, sleY1731MegControlRapsEnable, sleY1731MegControlRapsRplOwner, sleY1731MegControlRapsEastPort, 
				sleY1731MegControlRapsWestPort, sleY1731MegControlRapsRplPort, sleY1731MegControlRapsHoldOffTime, sleY1731MegControlRapsGuardTime, sleY1731MegControlRapsWaitToRestore, 
				sleY1731MepIdentifier, sleY1731MepIfIndex, sleY1731MepDirection, sleY1731MepEnable, sleY1731MepFngState, 
				sleY1731MepCcEnable, sleY1731MepMacAddress, sleY1731MepFaultPriority, sleY1731MepFaultKeepTime, sleY1731MepFaultClearTime, 
				sleY1731MepHighestPrDefect, sleY1731MepAisEnable, sleY1731MepAisTransmitEnable, sleY1731MepLckEnable, sleY1731MepLckTransmitEnable, 
				sleY1731MepOutOfService, sleY1731MepDlmEnabledRmep, sleY1731MepDefects, sleY1731MepCcmSequenceErrors, sleY1731MepCciSentCcms, 
				sleY1731MepNextLbmTransId, sleY1731MepLbrIn, sleY1731MepLbrInOutOfOrder, sleY1731MepTstLbrInBitError, sleY1731MepTstLbrInCrcError, 
				sleY1731MepLtmNextSeqNumber, sleY1731MepUnexpLtrIn, sleY1731MepLbrOut, sleY1731MepTmLbrFirstLostId, sleY1731MepTmLbrMaxRate, 
				sleY1731MepCcmFrameLossNearMin, sleY1731MepCcmFrameLossNearMax, sleY1731MepCcmFrameLossNearSum, sleY1731MepCcmFrameLossFarMin, sleY1731MepCcmFrameLossFarMax, 
				sleY1731MepCcmFrameLossFarSum, sleY1731MepControlRequest, sleY1731MepControlStatus, sleY1731MepControlTimer, sleY1731MepControlTimeStamp, 
				sleY1731MepControlReqResult, sleY1731MepControlIdentifier, sleY1731MepControlMegIndex, sleY1731MepControlIfIndex, sleY1731MepControlDirection, 
				sleY1731MepControlEnable, sleY1731MepControlCcEnable, sleY1731MepControlFaultPriority, sleY1731MepControlFaultKeepTime, sleY1731MepControlFaultClearTime, 
				sleY1731MepControlAisEnable, sleY1731MepControlAisTransmitEnable, sleY1731MepControlLckEnable, sleY1731MepControlLckTransmitEnable, sleY1731MepControlOutOfService, 
				sleY1731MepControlDlmEnabledRmep, sleY1731MepControlTransmitLbmIsUnicast, sleY1731MepControlTransmitLbmDestMacAddress, sleY1731MepControlTransmitLbmDestMepId, sleY1731MepControlTransmitLbmDestIsMepId, 
				sleY1731MepControlTransmitLbmCount, sleY1731MepControlTransmitLbmInterval, sleY1731MepControlTransmitLbmTimeout, sleY1731MepControlTransmitLbmPriority, sleY1731MepControlTransmitLbmLength, 
				sleY1731MepControlTransmitLtmTargetMacAddress, sleY1731MepControlTransmitLtmTargetMepId, sleY1731MepControlTransmitLtmTargetIsMepId, sleY1731MepControlTransmitLtmFlags, sleY1731MepControlTransmitLtmTtl, 
				sleY1731MepControlTransmitLtmPriority, sleY1731MepControlTransmitTstLbmDestMepId, sleY1731MepControlTransmitTstLbmDuration, sleY1731MepControlTransmitTstLbmInterval, sleY1731MepControlTransmitTstLbmTimeout, 
				sleY1731MepControlTransmitTstLbmPriority, sleY1731MepControlTransmitTstLbmLength, sleY1731MepControlTransmitTstLbmPattern, sleY1731MepControlTransmitTmLbmDestMepId, sleY1731MepControlTransmitTmLbmDuration, 
				sleY1731MepControlTransmitTmLbmPartDuration, sleY1731MepControlTransmitTmLbmStartRate, sleY1731MepControlTransmitTmLbmIncRate, sleY1731MepControlTransmitTmLbmTimeout, sleY1731MepControlTransmitTmLbmPriority, 
				sleY1731MepControlTransmitTmLbmLength, sleY1731MepControlTransmitTmLbmPattern, sleY1731MepControlTransmitTstIsUnicast, sleY1731MepControlTransmitTstDestMepId, sleY1731MepControlTransmitTstDuration, 
				sleY1731MepControlTransmitTstInterval, sleY1731MepControlTransmitTstPriority, sleY1731MepControlTransmitTstLength, sleY1731MepControlTransmitTstPattern, sleY1731MepControlReceiveTstDuration, 
				sleY1731MepControlTransmitTmTstIsUnicast, sleY1731MepControlTransmitTmTstDestMepId, sleY1731MepControlTransmitTmTstDuration, sleY1731MepControlTransmitTmTstPartDuration, sleY1731MepControlTransmitTmTstStartRate, 
				sleY1731MepControlTransmitTmTstIncRate, sleY1731MepControlTransmitTmTstTimeout, sleY1731MepControlTransmitTmTstPriority, sleY1731MepControlTransmitTmTstLength, sleY1731MepControlTransmitTmTstPattern, 
				sleY1731MepControlReceiveTmTstDuration, sleY1731MepControlTransmitLmmIsUnicast, sleY1731MepControlTransmitLmmDestMepId, sleY1731MepControlTransmitLmmDuration, sleY1731MepControlTransmitLmmInterval, 
				sleY1731MepControlTransmitLmmTimeout, sleY1731MepControlTransmitLmmPriority, sleY1731MepControlTransmit1dmIsUnicast, sleY1731MepControlTransmit1dmDestMepId, sleY1731MepControlTransmit1dmDuration, 
				sleY1731MepControlTransmit1dmInterval, sleY1731MepControlTransmit1dmPriority, sleY1731MepControlReceive1dmDuration, sleY1731MepControlTransmitDmmIsUnicast, sleY1731MepControlTransmitDmmDestMepId, 
				sleY1731MepControlTransmitDmmDuration, sleY1731MepControlTransmitDmmInterval, sleY1731MepControlTransmitDmmTimeout, sleY1731MepControlTransmitDmmPriority, sleY1731MipPort, 
				sleY1731MipLevel, sleY1731MipType, sleY1731MipControlRequest, sleY1731MipControlStatus, sleY1731MipControlTimer, 
				sleY1731MipControlTimeStamp, sleY1731MipControlReqResult, sleY1731MipControlPort, sleY1731MipControlLevel, sleY1731XcheckMepIdentifier, 
				sleY1731XcheckMepState, sleY1731XcheckControlRequest, sleY1731XcheckControlStatus, sleY1731XcheckControlTimer, sleY1731XcheckControlTimeStamp, 
				sleY1731XcheckControlReqResult, sleY1731XcheckControlMepIdentifier, sleY1731XcheckControlMegIndex, sleY1731CcMacAddress, sleY1731CcMacControlRequest, 
				sleY1731CcMacControlStatus, sleY1731CcMacControlTimer, sleY1731CcMacControlTimeStamp, sleY1731CcMacControlReqResult, sleY1731CcMacControlMegIndex, 
				sleY1731CcMacControlMepIdentifier, sleY1731CcMacControlAddress, sleY1731AisMacAddress, sleY1731AisMacControlRequest, sleY1731AisMacControlStatus, 
				sleY1731AisMacControlTimer, sleY1731AisMacControlTimeStamp, sleY1731AisMacControlReqResult, sleY1731AisMacControlMegIndex, sleY1731AisMacControlMepIdentifier, 
				sleY1731AisMacControlAddress, sleY1731LckMacAddress, sleY1731LckMacControlRequest, sleY1731LckMacControlStatus, sleY1731LckMacControlTimer, 
				sleY1731LckMacControlTimeStamp, sleY1731LckMacControlReqResult, sleY1731LckMacControlMegIndex, sleY1731LckMacControlMepIdentifier, sleY1731LckMacControlAddress, 
				sleY1731RmepIdentifier, sleY1731RmepState, sleY1731RmepFailedOkTime, sleY1731RmepMacAddress, sleY1731RmepIfIndex, 
				sleY1731RmepRdi, sleY1731RmepLoc, sleY1731RmepReceiveTstCount, sleY1731RmepReceiveTstOutOfOrder, sleY1731RmepReceiveTstBitError, 
				sleY1731RmepReceiveTstCrcError, sleY1731RmepReceiveTmTstCount, sleY1731RmepReceiveTmTstLostId, sleY1731RmepLmrFrameLossNearMin, sleY1731RmepLmrFrameLossNearMax, 
				sleY1731RmepLmrFrameLossNearSum, sleY1731RmepLmrFrameLossFarMin, sleY1731RmepLmrFrameLossFarMax, sleY1731RmepLmrFrameLossFarSum, sleY1731RmepReceive1dmCount, 
				sleY1731Rmep1dmFrameDelayMin, sleY1731Rmep1dmFrameDelayMax, sleY1731Rmep1dmFrameDelayAvg, sleY1731Rmep1dmFrameDelayVar, sleY1731RmepReceiveDmrCount, 
				sleY1731RmepDmrFrameDelayMin, sleY1731RmepDmrFrameDelayMax, sleY1731RmepDmrFrameDelayAvg, sleY1731RmepDmrFrameDelayVar, sleY1731LbrReceiveOrder, 
				sleY1731LbrRemoteMacAddress, sleY1731LtrSeqNumber, sleY1731LtrReceiveOrder, sleY1731LtrForwarded, sleY1731LtrTerminalMep, 
				sleY1731LtrLastEgressIdentifier, sleY1731LtrNextEgressIdentifier, sleY1731LtrRelay, sleY1731LtrIngress, sleY1731LtrIngressMac, 
				sleY1731LtrIngressPort, sleY1731LtrEgress, sleY1731LtrEgressMac, sleY1731LtrEgressPort, sleY1731ConfigErrorVid, 
				sleY1731ConfigErrorIfIndex, sleY1731ConfigErrorType, sleY1731MipCcdbIndex, sleY1731MipCcdbVlanId, sleY1731MipCcdbMacAddr, 
				sleY1731MipCcdbPort, sleY1731MipCcdbKeepTime, sleY1731RmepCreation, sleY1731BaseControlRmepCreation, sleY1731BaseControlTrunkIndex, 
				sleY1731BaseControlTrunkOamStatus, sleY1731TrunkIndex, sleY1731TrunkOamStatus, sleY1731BaseControlTrunkMeg, sleY1731TrunkMeg, 
				sleY1731MepLbSuccessRate, sleY1731MepTmLbmCount, sleY1731MepTmLbrCount, sleY1731MepTmTstCount, sleY1731RmepControlRequest, 
				sleY1731RMepControlStatus, sleY1731RmepControlTimer, sleY1731RmepControlTimeStamp, sleY1731RmepControlReqResult, sleY1731RmepControlIdentifier, 
				sleY1731RmepControlMegIndex, sleY1731RmepControlIfIndex, sleY1731MegRapsEastPortStatus, sleY1731MegRapsWestPortStatus, sleY1731MegRapsNonRevertive, 
				sleY1731MegRapsForcedSwitchEast, sleY1731MegRapsForcedSwitchWest, sleY1731MegControlRapsNonRevertive, sleY1731MegControlRapsForcedSwitchEast, sleY1731MegControlRapsForcedSwitchWest, 
				sleY1731URMegName, sleY1731URDedicatedVlan, sleY1731UREnableStatus, sleY1731URConnectivityCheckMeg, sleY1731URPrimaryMepId, 
				sleY1731URSecondaryMepId, sleY1731URControlVlan, sleY1731URNodeConf, sleY1731URNodeConfPortNum, sleY1731URNonRevertive, 
				sleY1731URTrustMemberCount, sleY1731URWaitToRestore, sleY1731URControlRequest, sleY1731URControlStatus, sleY1731URControlTimer, 
				sleY1731URControlTimeStamp, sleY1731URControlReqResult, sleY1731URControlMegName, sleY1731URControlDedicatedVlan, sleY1731URControlEnableStatus, 
				sleY1731URControlConnectivityCheckMeg, sleY1731URControlPrimaryMepId, sleY1731URControlSecondaryMepId, sleY1731URControlControlVlan, sleY1731URControlNodeConf, 
				sleY1731URControlNodeConfPortNum, sleY1731URControlNonRevertive, sleY1731URControlTrustMemberCount, sleY1731URControlWaitToRestore, sleY1731URMegIndex, 
				sleY1731URControlMegIndex, sleY1731URNodeConfPortStatus, sleY1731CCIgnoreDefect, sleY1731RapsFloodingBlock, sleY1731BaseControlCCIgnoreDefect, 
				sleY1731BaseControlRapsFloodingBlock, sleEMLogDisableStatus, sleEMLogAction, sleEMLogInterval, sleEMLogControlRequest, 
				sleEMLogControlStatus, sleEMLogControlTimer, sleEMLogControlTimeStamp, sleEMLogControlReqResult, sleEMLogControlDisableStatus, 
				sleEMLogControlAction, sleEMLogControlInterval, sleY1731MepLbRoundtripMin, sleY1731MepLbRoundtripMax, sleY1731MepLbRoundtripAvg, 
				sleCfmEnable, sleCfmLtrCacheHoldTime, sleCfmLtrCacheSize, sleCfmSnmpServerTraps, sleCfmXcheckStartDelay, 
				sleCfmBaseControlRequest, sleCfmBaseControlStatus, sleCfmBaseControlTimer, sleCfmBaseControlTimeStamp, sleCfmBaseControlReqResult, 
				sleCfmBaseControlEnable, sleCfmBaseControlLtrCacheHoldTime, sleCfmBaseControlLtrCacheSize, sleCfmBaseControlSnmpServerTraps, sleCfmBaseControlXcheckStartDelay, 
				sleCfmBaseControlTrunkIndex, sleCfmBaseControlTrunkMdName, sleCfmBaseControlTrunkMaVid, sleCfmTrunkIndex, sleCfmTrunkMdName, 
				sleCfmTrunkMaVid, sleCfmMdIndex, sleCfmMdName, sleCfmMdLevel, sleCfmMdMepEnable, 
				sleCfmMdCcEnable, sleCfmMdCcInterval, sleCfmMdCcPriority, sleCfmMdCcLossThreshold, sleCfmMdCcHoldTime, 
				sleCfmMdFaultPriority, sleCfmMdFaultKeepTime, sleCfmMdFaultClearTime, sleCfmMdXcheckEnable, sleCfmMdControlRequest, 
				sleCfmMdControlStatus, sleCfmMdControlTimer, sleCfmMdControlTimeStamp, sleCfmMdControlReqResult, sleCfmMdControlIndex, 
				sleCfmMdControlName, sleCfmMdControlLevel, sleCfmMdControlMepEnable, sleCfmMdControlCcEnable, sleCfmMdControlCcInterval, 
				sleCfmMdControlCcPriority, sleCfmMdControlCcLossThreshold, sleCfmMdControlCcHoldTime, sleCfmMdControlFaultPriority, sleCfmMdControlFaultKeepTime, 
				sleCfmMdControlFaultClearTime, sleCfmMdControlXcheckEnable, sleCfmMaIndex, sleCfmMaName, sleCfmMaVid, 
				sleCfmMaMepEnable, sleCfmMaCcEnable, sleCfmMaCcInterval, sleCfmMaCcPriority, sleCfmMaCcLossThreshold, 
				sleCfmMaCcFaultPriority, sleCfmMaCcFaultKeepTime, sleCfmMaCcFaultClearTime, sleCfmMaXcheckEnable, sleCfmMaControlRequest, 
				sleCfmMaControlStatus, sleCfmMaControlTimer, sleCfmMaControlTimeStamp, sleCfmMaControlReqResult, sleCfmMaControlIndex, 
				sleCfmMaControlName, sleCfmMaControlVid, sleCfmMaControlMdIndex, sleCfmMaControlMepEnable, sleCfmMaControlCcEnable, 
				sleCfmMaControlCcInterval, sleCfmMaControlCcPriority, sleCfmMaControlCcLossThreshold, sleCfmMaControlFaultPriority, sleCfmMaControlFaultKeepTime, 
				sleCfmMaControlFaultClearTime, sleCfmMaControlXcheckEnable, sleCfmMepIdentifier, sleCfmMepIfIndex, sleCfmMepDirection, 
				sleCfmMepEnable, sleCfmMepFngState, sleCfmMepCcEnable, sleCfmMepMacAddress, sleCfmMepCcPriority, 
				sleCfmMepFaultPriority, sleCfmMepFaultKeepTime, sleCfmMepFaultClearTime, sleCfmMepHighestPrDefect, sleCfmMepDefects, 
				sleCfmMepCciSentCcms, sleCfmMepNextLbmTransId, sleCfmMepLbrIn, sleCfmMepLbrInOutOfOrder, sleCfmMepLtmNextSeqNumber, 
				sleCfmMepUnexpLtrIn, sleCfmMepControlRequest, sleCfmMepControlStatus, sleCfmMepControlTimer, sleCfmMepControlTimeStamp, 
				sleCfmMepControlReqResult, sleCfmMepControlIdentifier, sleCfmMepControlMdIndex, sleCfmMepControlMaIndex, sleCfmMepControlIfIndex, 
				sleCfmMepControlDirection, sleCfmMepControlEnable, sleCfmMepControlCcEnable, sleCfmMepControlCcPriority, sleCfmMepControlFaultPriority, 
				sleCfmMepControlFaultKeepTime, sleCfmMepControlFaultClearTime, sleCfmMepControlTransmitLbmDestMacAddress, sleCfmMepControlTransmitLbmDestMepId, sleCfmMepControlTransmitLbmDestIsMepId, 
				sleCfmMepControlTransmitLbmCount, sleCfmMepControlTransmitLbmInterval, sleCfmMepControlTransmitLbmTimeout, sleCfmMepControlTransmitLbmPriority, sleCfmMepControlTransmitLtmTargetMacAddress, 
				sleCfmMepControlTransmitLtmTargetMepId, sleCfmMepControlTransmitLtmTargetIsMepId, sleCfmMepControlTransmitLtmFlags, sleCfmMepControlTransmitLtmTtl, sleCfmMipPort, 
				sleCfmMipLevel, sleCfmMipType, sleCfmMipControlRequest, sleCfmMipControlStatus, sleCfmMipControlTimer, 
				sleCfmMipControlTimeStamp, sleCfmMipControlReqResult, sleCfmMipControlPort, sleCfmMipControlLevel, sleCfmXcheckMepIdentifier, 
				sleCfmXcheckMepState, sleCfmXcheckControlRequest, sleCfmXcheckControlStatus, sleCfmXcheckControlTimer, sleCfmXcheckControlTimeStamp, 
				sleCfmXcheckControlReqResult, sleCfmXcheckControlMepIdentifier, sleCfmXcheckControlMdIndex, sleCfmXcheckControlMaIndex, sleCfmRmepIdentifier, 
				sleCfmRmepState, sleCfmRmepMacAddress, sleCfmRmepIfIndex, sleCfmRmepRdi, sleCfmRmepPortStatus, 
				sleCfmRmepInterfaceStatus, sleCfmLtrSeqNumber, sleCfmLtrReceiveOrder, sleCfmLtrTtl, sleCfmLtrForwarded, 
				sleCfmLtrTerminalMep, sleCfmLtrLastEgressIdentifier, sleCfmLtrNextEgressIdentifier, sleCfmLtrRelay, sleCfmLtrIngress, 
				sleCfmLtrIngressMac, sleCfmLtrIngressPort, sleCfmLtrEgress, sleCfmLtrEgressMac, sleCfmLtrEgressPort, 
				sleCfmConfigErrorVid, sleCfmConfigErrorIfIndex, sleCfmConfigErrorType, sleCfmMipCcdbIndex, sleCfmMipCcdbVlanId, 
				sleCfmMipCcdbMacAddr, sleCfmMipCcdbPort, sleCfmMipCcdbKeepTime, sleRapsRingId, sleRapsRingType, 
				sleRapsRingLevel, sleRapsRingCtrlVlan, sleRapsRingTrafficVlans, sleRapsRingNodeId, sleRapsRingEnable, 
				sleRapsRingBridgeRole, sleRapsRingState, sleRapsRingEastPort, sleRapsRingEastPortStatus, sleRapsRingWestPort, 
				sleRapsRingWestPortStatus, sleRapsRingRplPort, sleRapsRingIcPort, sleRapsRingMultipleFailure, sleRapsRingPropagateTc, 
				sleRapsRingNonRevertive, sleRapsRingForcedSwitch, sleRapsRingHoldOffTime, sleRapsRingGuardTime, sleRapsRingWaitToRestore, 
				sleRapsRingWaitToBlock, sleRapsRingControlRequest, sleRapsRingControlStatus, sleRapsRingControlTimer, sleRapsRingControlTimeStamp, 
				sleRapsRingControlReqResult, sleRapsRingControlId, sleRapsRingControlType, sleRapsRingControlLevel, sleRapsRingControlCtrlVlan, 
				sleRapsRingControlTrafficVlans, sleRapsRingControlEnable, sleRapsRingControlEastPort, sleRapsRingControlWestPort, sleRapsRingControlBridgeRole, 
				sleRapsRingControlMultipleFailure, sleRapsRingControlPropagateTc, sleRapsRingControlNonRevertive, sleRapsRingControlHoldOffTime, sleRapsRingControlGuardTime, 
				sleRapsRingControlWaitToRestore, sleRapsRingControlWaitToBlock, sleY1731LbrTransId, sleY1731LbrRoundTripTime, sleY1731TlvPermission, 
				sleY1731BaseControlTlvPermission, sleY1731MepPmEnable, sleY1731MepCcmFrameLossNearRatio, sleY1731MepCcmFrameLossNearAvgRatio, sleY1731MepCcmFrameLossFarRatio, 
				sleY1731MepCcmFrameLossFarAvgRatio, sleY1731MepControlPmEnable, sleY1731RmepLmrFrameLossNearRatio, sleY1731RmepLmrFrameLossNearAvgRatio, sleY1731RmepLmrFrameLossFarRatio, 
				sleY1731RmepLmrFrameLossFarAvgRatio, sleY1731URSFCondition, sleY1731URControlSFCondition, sleAdvaOamControlMode, sleAlarmReportControlRequest, 
				sleAlarmReportControlStatus, sleAlarmReportControlTimer, sleAlarmReportControlTimeStamp, sleAlarmReportControlReqResult, sleY1731URForceSwitch, 
				sleY1731URControlForceSwitch, sleEMLogDefectCPUHigh, sleEMLogTemperHigh, sleEMLogTemperLow, sleEMLogMemLow, 
				sleEMLogFanFail, sleEMLogPhyCRCFail, sleEMLogPhyDetectFail, sleEMLogSFUMateInitFail, sleEMLogDaemonHealthBad, 
				sleY1731LtrTtl, sleY1731LRMepIndex, sleY1731LRMepDMegIndex, sleY1731LRMepDMepIdentifier, sleY1731LRMepDRmepIdentifier, 
				sleY1731LRMepControlRequest, sleY1731LRMepControlStatus, sleY1731LRMepControlTimer, sleY1731LRMepControlTimeStamp, sleY1731LRMepControlReqResult, 
				sleY1731LRMepControlMegIndex, sleY1731LRMepControlMepIdentifier, sleY1731LRMepControlRmepIdentifier, sleY1731LRMepControlDMegIndex, sleY1731LRMepControlDMepIdentifier, 
				sleY1731LRMepControlDRmepIdentifier, sleEMLogGPIURavenLinkDown, sleY1731MepRllcfGuardTime, sleY1731MepControlRllcfGuardTime, sleOamRemLoopbackCnt, 
				sleOamLm, sleOamLmAction, sleOamLmFrameWindow, sleOamLmFrameThresh, sleOamLmFrameTotal, 
				sleOamLmFramePeriodWindow, sleOamLmFramePeriodThresh, sleOamLmFramePeriodTotal, sleOamLmFrameSecondSummaryWindow, sleOamLmFrameSecondSummaryThresh, 
				sleOamLmFrameSecondSummaryTotal, sleOamLmSymbolPeriodWindow, sleOamLmSymbolPeriodThresh, sleOamLmSymbolPeriodTotal, sleOamLmRemSeqNum, 
				sleOamLmRemFrameLength, sleOamLmRemFrameTimeStamp, sleOamLmRemFrameWindow, sleOamLmRemFrameThresh, sleOamLmRemFrameErrors, 
				sleOamLmRemFrameErrorRunTotal, sleOamLmRemFrameEventRunTotal, sleOamLmRemFramePeriodLength, sleOamLmRemFramePeriodTimeStamp, sleOamLmRemFramePeriodWindow, 
				sleOamLmRemFramePeriodThresh, sleOamLmRemFramePeriodErrors, sleOamLmRemFramePeriodErrorRunTotal, sleOamLmRemFramePeriodEventRunTotal, sleOamLmRemFrameSecondSummaryLength, 
				sleOamLmRemFrameSecondSummaryTimeStamp, sleOamLmRemFrameSecondSummaryWindow, sleOamLmRemFrameSecondSummaryThresh, sleOamLmRemFrameSecondSummaryErrors, sleOamLmRemFrameSecondSummaryErrorRunTotal, 
				sleOamLmRemFrameSecondSummaryEventRunTotal, sleOamLmRemSymbolPeriodLength, sleOamLmRemSymbolPeriodTimeStamp, sleOamLmRemSymbolPeriodWindow, sleOamLmRemSymbolPeriodThresh, 
				sleOamLmRemSymbolPeriodErrors, sleOamLmRemSymbolPeriodErrorRunTotal, sleOamLmRemSymbolPeriodEventRunTotal, sleOamControlRemLoopbackPkCnt, sleOamControlLm, 
				sleOamControlLmAction, sleOamControlLmFrameWindow, sleOamControlLmFrameThresh, sleOamControlLmFramePeriodWindow, sleOamControlLmFramePeriodThresh, 
				sleOamControlLmFrameSecondSummaryWindow, sleOamControlLmFrameSecondSummaryThresh, sleOamControlLmSymbolPeriodWindow, sleOamControlLmSymbolPeriodThresh, sleY1731LtrRoundTripTime, 
				sleY1731MepRllcf, sleY1731MepRllcfHoldOff, sleY1731MepControlRllcf, sleY1731MepControlRllcfHoldOff, sleRapsRingInstId, 
				sleRapsRingChannel, sleRapsRingPassThrough, sleRapsRingManualSwitch, sleRapsRingVerifiedTime, sleRapsRingControlInstId, 
				sleRapsRingVirtualVlan, sleRapsRingIcNode, sleY1731URTrafficVlan, sleY1731URState, sleY1731URControlTrafficVlan, 
				sleAlarmReportPairType, sleAlarmHistoryPairType, sleY1731URManualSwitch, sleY1731URControlManualSwitch, sleEMLogNAKLockStatus, 
				sleEMLogNakCompensate, sleEMLogRecoverActionMemLow, sleEMLogRecoverActionNak, sleEMLogControlNAKLockStatus, sleEMLogControlNAKCompensate, 
				sleEMLogControlRecoverActionMemLow, sleEMLogControlRecoverActionNAK, sleEMLogNAK, sleFaultMonitorGlobalInspectInterval, sleFaultMonitorGlobalStartupThreshold, 
				sleFaultMonitorGlobalNoKeepalive, sleFaultMonitorGlobalControlRequest, sleFaultMonitorGlobalControlStatus, sleFaultMonitorGlobalControlTimer, sleFaultMonitorGlobalControlTimeStamp, 
				sleFaultMonitorGlobalControlReqResult, sleFaultMonitorGlobalControlInspectInterval, sleFaultMonitorGlobalControlStartupThreshold, sleFaultMonitorGlobalControlNoKeepalive, sleFaultMonitorDaemonName, 
				sleFaultMonitorDaemonPid, sleFaultMonitorDaemonAdminStatus, sleFaultMonitorDaemonCrashAction, sleFaultMonitorDaemonTimeoutAction, sleFaultMonitorDaemonThreshold, 
				sleFaultMonitorDaemonThresholded, sleFaultMonitorDaemonStartupThresholded, sleFaultMonitorDaemonWatchdogAdminStatus, sleFaultMonitorDaemonWatchdogThreshold, sleFaultMonitorDaemonWatchdogCount, 
				sleFaultMonitorDaemonControlRequest, sleFaultMonitorDaemonControlStatus, sleFaultMonitorDaemonControlTimer, sleFaultMonitorDaemonControlTimeStamp, sleFaultMonitorDaemonControlReqResult, 
				sleFaultMonitorDaemonControlAdminStatus, sleFaultMonitorDaemonControlCrashAction, sleFaultMonitorDaemonControlTimeoutAction, sleFaultMonitorDaemonControlThreshold, sleFaultMonitorDaemonControlWatchdogAdminStatus, 
				sleFaultMonitorDaemonControlWatchdogThreshold, sleFaultMonitor2pointsLinearAdminStatus, sleFaultMonitor2pointsLinearInterval, sleFaultMonitor2pointsLinearThreshold, sleFaultMonitor2pointsLinearControlRequest, 
				sleFaultMonitor2pointsLinearControlStatus, sleFaultMonitor2pointsLinearControlTimer, sleFaultMonitor2pointsLinearControlTimeStamp, sleFaultMonitor2pointsLinearControlReqResult, sleFaultMonitor2pointsLinearControlAdminStatus, 
				sleFaultMonitor2PonitsLinearControlInterval, sleFaultMonitor2PointsLinearControlThreshold, sleFaultMonitorRHMAdminStatus, sleFaultMonitorRHMActionType, sleFaultMonitorRHMActionThreshold, 
				sleFaultMonitorRHMRebootThreshold, sleFaultMonitorRHMRecoveryTime, sleFaultMonitorRHMFaultCounter, sleFaultMonitorRHMRebootCounter, sleFaultMonitorRHMHostAddr, 
				sleFaultMonitorRHMControlRequest, sleFaultMonitorRHMControlStatus, sleFaultMonitorRHMControlTimer, sleFaultMonitorRHMControlTimeStamp, sleFaultMonitorRHMControlReqResult, 
				sleFaultMonitorRHMControlAdminStatus, sleFaultMonitorRHMControlActionType, sleFaultMonitorRHMControlActionThreshold, sleFaultMonitorRHMControlRebootThreshold, sleFaultMonitorRHMControlRecoveryTime, 
				sleFaultMonitorRHMControlHostAddr, sleEMLogFANRPMLow, sleFaultMonitorRHMInterval, sleFaultMonitorRHMLiveThreshold, sleFaultMonitorRHMControlInterval, 
				sleFaultMonitorRHMControlLiveThreshold, sleRapsRingControlIcNode, sleRapsRingControlChannel, sleRapsRingControlParamPort, sleRapsRingControlPassThrough, 
				sleRapsRingControlVerifiedTime }
			STATUS current
			DESCRIPTION 
				"Description."
			::= { sleFaultMgmt 17 }

		
--   1.3.6.1.4.1.6296.101.4.17
-- 1.3.6.1.4.1.6296.101.4.17
		-- 1.3.6.1.4.1.6296.101.4.18
		sleFaultMgmtNotificationGroup NOTIFICATION-GROUP
			NOTIFICATIONS { sleAlarmDefaultSeverityChanged, sleAlarmDefaultCriteriaChanged, sleNotificationActivityChanged, sleAlarmSeveriityCreated, sleAlarmSeveriityDestroyed, 
				sleAlarmSeverityChanged, sleAlarmReportNotified, sleAlarmHistoryCleared, sleEfmOamPortProfileChanged, sleEfmOamPortRemLoopback, 
				sleAdvaSystemProfileChanged, sleAdvaAlarmProfileChanged, sleAdvaElectricalInterfaceChanged, sleAdvaGeneralProfileChanged, sleAdvaAutonegProfileChanged, 
				sleAdvaOpticalAlarmChanged, sleAlarmLEDOffChanged, sleAlarmLEDLevelChanged, sleAlarmLEDCleared, sleAlarmLEDBlockChanged, 
				sleY1731EnableChanged, sleY1731TrunkEnableChanged, sleY1731LtrCacheProfileChanged, sleY1731SnmpProfileChanged, sleY1731XcheckProfileChanged, 
				sleY1731DefaultMegProfileChanged, sleY1731PduToCfmChanged, sleY1731DedicatedVlanChanged, sleY1731MipCcdbDestroyed, sleY1731LtrCacheDestroyed, 
				sleY1731MegCreated, sleY1731MegDeleted, sleY1731MegMepEnableChanged, sleY1731MegCcEnableChanged, sleY1731MegCcProfileChanged, 
				sleY1731MegFaultProfileChanged, sleY1731MegXcheckEnableChanged, sleY1731MegAisEnableChanged, sleY1731MegAisTransmitEnableChanged, sleY1731MegAisProfileChanged, 
				sleY1731MegLckEnableChanged, sleY1731MegLckTransmitEnableChanged, sleY1731MegLckProfileChanged, sleY1731MegOutOfServiceChanged, sleY1731MegRapsEnableChanged, 
				sleY1731MegRapsRingportsChanged, sleY1731MegRapsRplPortChanged, sleY1731MegRapsRplOwnerChanged, sleY1731MegRapsTimerChanged, sleY1731MegRemoteMepDestroyed, 
				sleY1731MegErrorDestroyed, sleY1731MepCreated, sleY1731MepDeleted, sleY1731MepEnableChanged, sleY1731MepCcEnableChanged, 
				sleY1731MepFaultProfileChanged, sleY1731MepAisEnableChanged, sleY1731MepAisTransmitEnableChanged, sleY1731MepLckEnableChanged, sleY1731MepLckTransmitEnableChanged, 
				sleY1731MepOutOfServiceChanged, sleY1731MepDlmEnableChanged, sleY1731MepTransmitLbmFinished, sleY1731MepTransmitLtmFinished, sleY1731MepTransmitTstLbmFinished, 
				sleY1731MepTransmitTmLbmFinished, sleY1731MepTransmitTstFinished, sleY1731MepReceiveTstFinished, sleY1731MepTransmitTmTstFinished, sleY1731MepReceiveTmTstFinished, 
				sleY1731MepTransmitLmmFinished, sleY1731MepTransmit1dmFinished, sleY1731MepReceive1dmFinished, sleY1731MepTransmitDmmFinished, sleY1731MipCreated, 
				sleY1731MipDeleted, sleY1731XcheckMepCreated, sleY1731XcheckMepDeleted, sleY1731CcMacCreated, sleY1731CcMacDeleted, 
				sleY1731AisMacCreated, sleY1731AisMacDeleted, sleY1731LckMacCreated, sleY1731LckMacDeleted, sleY1731RmepCreationChanged, 
				sleY1731TrunkOamStatusChanged, sleY1731RmepCreated, sleY1731RmepDeleted, sleY1731MegRapsNonRevertiveChanged, sleY1731MegRapsForcedSwitchEastChanged, 
				sleY1731MegRapsForcedSwitchWestChanged, sleY1731URDedicatedVlanChanged, sleY1731UREnableStatusChanged, sleY1731URCCPrimaryMepIdChanged, sleY1731URCCPrimaryMepIdCleared, 
				sleY1731URCCSecondaryMepIdChanged, sleY1731URCCSecondaryMepIdCleared, sleY1731URControlVlanChanged, sleY1731URNodeConfChanged, sleY1731URNodeConfCleared, 
				sleY1731URNonRevertiveChanged, sleY1731URTrustMemberCountChanged, sleY1731URTrustMemberCountCleared, sleY1731URWaitToRestoreChanged, sleY1731URWaitToRestoreCleared, 
				sleY1731URControlVlanCleared, sleY1731URForceSwitchChanged, sleY1731URManualSwitchChanged, sleY1731CCIgnoreDefectChanged, sleY1731RapsFloodinBlockChanged, 
				sleEMLogDisableStatusChanged, sleEMLogActionChanged, sleEMLogIntervalChanged, sleCfmEnableChanged, sleCfmLtrCacheProfileChanged, 
				sleCfmSnmpServerTrapsChanged, sleCfmXcheckStartDelayChanged, sleCfmMipCcdbDestroyed, sleCfmLtrCacheDestroyed, sleCfmTrunkPortCreated, 
				sleCfmTrunkPortDeleted, sleCfmMdCreated, sleCfmMdDeleted, sleCfmMdMepEnableChanged, sleCfmMdCcEnableChanged, 
				sleCfmMdCcProfileChanged, sleCfmMdFaultProfileChanged, sleCfmMdXcheckEnableChanged, sleCfmMdErrorDestoryed, sleCfmMdRmepDestoryed, 
				sleCfmMaCreated, sleCfmMaDeleted, sleCfmMaMepEnableChanged, sleCfmMaCcEnableChanged, sleCfmMaCcProfileChanged, 
				sleCfmMaFaultProfileChanged, sleCfmMaXcheckEnableChanged, sleCfmMepCreated, sleCfmMepDeleted, sleCfmMepEnableChanged, 
				sleCfmMepCcEnableChanged, sleCfmMepCcProfileChanged, sleCfmMepFaultProfileChanged, sleCfmMipCreated, sleCfmMipDeleted, 
				sleCfmXcheckMepCreated, sleCfmXcheckMepDeleted, sleRapsRingCreated, sleRapsRingDeleted, sleRapsRingEnableChanged, 
				sleRapsRingPortsCreated, sleRapsRingPortsDestroyed, sleRapsRingRplPortChanged, sleRapsRingMultipleFailureChanged, sleRapsRingPropagateTcChanged, 
				sleRapsRingNonRevertiveChanged, sleRapsRingForcedSwitchChanged, sleRapsRingManualSwitchChanged, sleRapsRingSwitchCleared, sleRapsRingHoldOffTimeChanged, 
				sleRapsRingGuardTimeChanged, sleRapsRingWtrTimeChanged, sleRapsRingWtbTimeChanged, sleY1731TlvPermissionChanged, sleY1731MepPmEnableChanged, 
				sleY1731LRMepCreated, sleY1731LRMEPDeleted, setAdvaOamProfileChanged, sleAlarmReportCleared, sleEfmOamPortLinkMonitorChanged, 
				sleRapsRingIcPortCreated, sleRapsRingIcPortDestroyed, sleY1731URTrafficVlanChanged, sleY1731URTrafficVlanCleared, sleEMLogNAKLockChanged, 
				sleEMLogNAKCompensateChanged, sleEMLogRecoverActionMemLowChanged, sleEMLogRecoverActionNAKChanged, setFaultMonitorGlobalInspectIntervalChanged, setFaultMonitorGlobalStartupThresholdChanged, 
				setFaultMonitorGlobalNoKeepaliveActionChanged, setFaultMonitorDaemonAdminStatusChanged, setFaultMonitorDaemonFaultActionChanged, setFaultMonitorDaemonThresholdChanged, setFaultMonitorDaemonWatchdogchanged, 
				sleFaultMonitor2PointsLinearAdminStatusChanged, sleFaultMonitor2PointsLinearIntervalChanged, sleFaultMonitor2PointsLinearThresholdChanged, setRHMStatusChanged, setRHMActionThresholdChanged, 
				setRHMRebootThresholdChanged, setRHMHostAdded, setRHMHostCleared, sleY1731URSFConditionChanged, sleY1731MepRllcfChanged, 
				sleRapsRingChannelChanged, sleRapsRingPassThroughChanged, sleRapsRingVrfTimeChanged }
			STATUS current
			DESCRIPTION 
				"Description."
			::= { sleFaultMgmt 18 }

		
	
	END

--
-- SLE-FAULTMGMT-MIB.my
--
