--
-- SLE-OSPF-MIB.my
-- MIB generated by MG-SOFT Visual MIB Builder Version 6.0  Build 88
-- Saturday, May 15, 2010 at 12:03:04
--

	SLE-OSPF-MIB DEFINITIONS ::= BEGIN
 
		IMPORTS
			sleMgmt			
				FROM DASAN-SMI			
			SleControlStatusType, SleControlRequestResultType			
				FROM SLE-TC-MIB			
			OBJECT-GROUP, NOTIFICATION-GROUP			
				FROM SNMPv2-CONF			
			TimeTicks, IpAddress, Integer32, Gauge32, OBJECT-TYPE, 
			MODULE-IDENTITY, NOTIFICATION-TYPE			
				FROM SNMPv2-SMI;
	
	
		-- 1.3.6.1.4.1.6296.101.51
		sleOspf MODULE-IDENTITY 
			LAST-UPDATED "200412291441Z"		-- December 29, 2004 at 14:41 GMT
			ORGANIZATION 
				"HANASOFT"
			CONTACT-INFO 
				" "
			DESCRIPTION 
				"This MIB contains information about OSPF version 2."
			REVISION "201003211954Z"		-- March 21, 2010 at 19:54 GMT
			DESCRIPTION 
				"OSFPv2"
			::= { sleMgmt 51 }

		
	
	
	
--
-- Node definitions
--
	
		-- 1.3.6.1.4.1.6296.101.51.1
		sleOSPFBase OBJECT IDENTIFIER ::= { sleOspf 1 }

		
		-- 1.3.6.1.4.1.6296.101.51.1.1
		sleOSPFBaseInfo OBJECT IDENTIFIER ::= { sleOSPFBase 1 }

		
		-- 1.3.6.1.4.1.6296.101.51.1.1.1
		sleOSPFRestartPeriod OBJECT-TYPE
			SYNTAX INTEGER (0..1800)
			MAX-ACCESS read-only
			STATUS current
			DESCRIPTION
				"Description."
			::= { sleOSPFBaseInfo 1 }

		
		-- 1.3.6.1.4.1.6296.101.51.1.1.2
		sleOSPFRestartHelperPolicy OBJECT-TYPE
			SYNTAX INTEGER
				{
				unspec(0),
				never(1),
				onlyreload(2),
				onlyugrade(3)
				}
			MAX-ACCESS read-only
			STATUS current
			DESCRIPTION
				"Description."
			::= { sleOSPFBaseInfo 2 }

		
		-- 1.3.6.1.4.1.6296.101.51.1.1.3
		sleOSPFRestartHelperPeriod OBJECT-TYPE
			SYNTAX INTEGER (0..1800)
			MAX-ACCESS read-only
			STATUS current
			DESCRIPTION
				"Description."
			::= { sleOSPFBaseInfo 3 }

		
		-- 1.3.6.1.4.1.6296.101.51.1.2
		sleOSPFBaseControl OBJECT IDENTIFIER ::= { sleOSPFBase 2 }

		
		-- 1.3.6.1.4.1.6296.101.51.1.2.1
		sleOSPFControlRequest OBJECT-TYPE
			SYNTAX INTEGER
				{
				setOSPFRestartPeriod(1),
				setOSPFRestartHelperProfile(2),
				restartOSPFGraceful(3)
				}
			MAX-ACCESS read-write
			STATUS current
			DESCRIPTION
				"Description."
			::= { sleOSPFBaseControl 1 }

		
		-- 1.3.6.1.4.1.6296.101.51.1.2.2
		sleOSPFControlStatus OBJECT-TYPE
			SYNTAX SleControlStatusType
			MAX-ACCESS read-only
			STATUS current
			DESCRIPTION
				"Description."
			::= { sleOSPFBaseControl 2 }

		
		-- 1.3.6.1.4.1.6296.101.51.1.2.3
		sleOSPFControlTimer OBJECT-TYPE
			SYNTAX Gauge32
			MAX-ACCESS read-write
			STATUS current
			DESCRIPTION
				"Description."
			::= { sleOSPFBaseControl 3 }

		
		-- 1.3.6.1.4.1.6296.101.51.1.2.4
		sleOSPFControlTimeStamp OBJECT-TYPE
			SYNTAX TimeTicks
			MAX-ACCESS read-only
			STATUS current
			DESCRIPTION
				"Description."
			::= { sleOSPFBaseControl 4 }

		
		-- 1.3.6.1.4.1.6296.101.51.1.2.5
		sleOSPFControlReqResult OBJECT-TYPE
			SYNTAX SleControlRequestResultType
			MAX-ACCESS read-only
			STATUS current
			DESCRIPTION
				"Description."
			::= { sleOSPFBaseControl 5 }

		
		-- 1.3.6.1.4.1.6296.101.51.1.2.6
		sleOSPFControlRestartPeriod OBJECT-TYPE
			SYNTAX INTEGER (0..1800)
			MAX-ACCESS read-write
			STATUS current
			DESCRIPTION
				"Description."
			::= { sleOSPFBaseControl 6 }

		
		-- 1.3.6.1.4.1.6296.101.51.1.2.7
		sleOSPFControlRestartHelperPolicy OBJECT-TYPE
			SYNTAX INTEGER
				{
				unspec(0),
				never(1),
				onlyreload(2),
				onlyugrade(3)
				}
			MAX-ACCESS read-write
			STATUS current
			DESCRIPTION
				"Description."
			::= { sleOSPFBaseControl 7 }

		
		-- 1.3.6.1.4.1.6296.101.51.1.2.8
		sleOSPFControlRestartHelperPeriod OBJECT-TYPE
			SYNTAX INTEGER (0..1800)
			MAX-ACCESS read-write
			STATUS current
			DESCRIPTION
				"Description."
			::= { sleOSPFBaseControl 8 }

		
		-- 1.3.6.1.4.1.6296.101.51.1.3
		sleOSPFBaseNotification OBJECT IDENTIFIER ::= { sleOSPFBase 3 }

		
		-- 1.3.6.1.4.1.6296.101.51.1.3.1
		sleOSPFRestartPeriodChanged NOTIFICATION-TYPE
			OBJECTS { sleOSPFControlRequest, sleOSPFControlTimeStamp, sleOSPFControlReqResult, sleOSPFRestartPeriod }
			STATUS current
			DESCRIPTION 
				"Description."
			::= { sleOSPFBaseNotification 1 }

		
		-- 1.3.6.1.4.1.6296.101.51.1.3.2
		sleOSPFRestartHelperProfileChanged NOTIFICATION-TYPE
			OBJECTS { sleOSPFControlRequest, sleOSPFControlTimeStamp, sleOSPFControlReqResult, sleOSPFRestartHelperPolicy, sleOSPFRestartHelperPeriod
				 }
			STATUS current
			DESCRIPTION 
				"Description."
			::= { sleOSPFBaseNotification 2 }

		
		-- 1.3.6.1.4.1.6296.101.51.1.3.3
		sleOSPFGracefulRestarted NOTIFICATION-TYPE
			OBJECTS { sleOSPFControlRequest, sleOSPFControlTimeStamp, sleOSPFControlReqResult, sleOSPFControlRestartPeriod }
			STATUS current
			DESCRIPTION 
				"Description."
			::= { sleOSPFBaseNotification 3 }

		
		-- 1.3.6.1.4.1.6296.101.51.2
		sleOSPFProc OBJECT IDENTIFIER ::= { sleOspf 2 }

		
		-- 1.3.6.1.4.1.6296.101.51.2.1
		sleOSPFProcInfo OBJECT IDENTIFIER ::= { sleOSPFProc 1 }

		
		-- 1.3.6.1.4.1.6296.101.51.2.1.1
		sleOSPFProcInfoTable OBJECT-TYPE
			SYNTAX SEQUENCE OF SleOSPFProcInfoEntry
			MAX-ACCESS not-accessible
			STATUS current
			DESCRIPTION
				"Description."
			::= { sleOSPFProcInfo 1 }

		
		-- 1.3.6.1.4.1.6296.101.51.2.1.1.1
		sleOSPFProcInfoEntry OBJECT-TYPE
			SYNTAX SleOSPFProcInfoEntry
			MAX-ACCESS not-accessible
			STATUS current
			DESCRIPTION
				"Description."
			INDEX { sleOSPFProcID }
			::= { sleOSPFProcInfoTable 1 }

		
		SleOSPFProcInfoEntry ::=
			SEQUENCE { 
				sleOSPFProcID
					Integer32,
				sleOSPFProcRouterID
					IpAddress,
				sleOSPFProcSPFDelayTime
					INTEGER,
				sleOSPFProcSPFHoldTime
					INTEGER,
				sleOSPFProcAutoCost
					INTEGER,
				sleOSPFProcAbrType
					INTEGER,
				sleOSPFProcSnmpNotification
					INTEGER,
				sleOSPFProcDefaultMetricConfig
					INTEGER,
				sleOSPFProcDefaultMetricValue
					INTEGER,
				sleOSPFProcMaxArea
					Gauge32,
				sleOSPFProcMaxConcurrentDD
					INTEGER,
				sleOSPFProcCompatiblerfc1583
					INTEGER,
				sleOSPFProcCapabilityOpaque
					INTEGER,
				sleOSPFProcLSDBOverflowType
					INTEGER,
				sleOSPFProcLSDBOverflowLimit
					Gauge32,
				sleOSPFProcExtLSDBLimit
					INTEGER,
				sleOSPFProcExitOverFlowInterval
					INTEGER,
				sleOSPFProcAdminDistance
					INTEGER,
				sleOSPFProcExternalDistance
					INTEGER,
				sleOSPFProcIntraAreaDistance
					INTEGER,
				sleOSPFProcInterAreaDistance
					INTEGER,
				sleOSPFProcDefaultOriginType
					INTEGER,
				sleOSPFProcDefaultOriginMetricType
					INTEGER,
				sleOSPFProcDefaultOriginMetric
					INTEGER,
				sleOSPFProcDefaultOriginRouteMap
					OCTET STRING,
				sleOSPFProcLogNeighborChange
					INTEGER,
				sleOSPFProcPassiveIfAll
					INTEGER,
				sleOSPFProcBfdIFAll
					INTEGER,
				sleOSPFProcEfmIFAll
					INTEGER,
				sleOSPFProcCapabilityRestart
					INTEGER
			 }

		-- 1.3.6.1.4.1.6296.101.51.2.1.1.1.1
		sleOSPFProcID OBJECT-TYPE
			SYNTAX Integer32 (1..65535)
			MAX-ACCESS read-only
			STATUS current
			DESCRIPTION
				"Description."
			::= { sleOSPFProcInfoEntry 1 }

		
		-- 1.3.6.1.4.1.6296.101.51.2.1.1.1.2
		sleOSPFProcRouterID OBJECT-TYPE
			SYNTAX IpAddress
			MAX-ACCESS read-only
			STATUS current
			DESCRIPTION
				"Description."
			::= { sleOSPFProcInfoEntry 2 }

		
		-- 1.3.6.1.4.1.6296.101.51.2.1.1.1.3
		sleOSPFProcSPFDelayTime OBJECT-TYPE
			SYNTAX INTEGER (0..2147483647)
			MAX-ACCESS read-only
			STATUS current
			DESCRIPTION
				"Description."
			::= { sleOSPFProcInfoEntry 3 }

		
		-- 1.3.6.1.4.1.6296.101.51.2.1.1.1.4
		sleOSPFProcSPFHoldTime OBJECT-TYPE
			SYNTAX INTEGER (0..2147483647)
			MAX-ACCESS read-only
			STATUS current
			DESCRIPTION
				"Description."
			::= { sleOSPFProcInfoEntry 4 }

		
		-- 1.3.6.1.4.1.6296.101.51.2.1.1.1.5
		sleOSPFProcAutoCost OBJECT-TYPE
			SYNTAX INTEGER (1..4294967)
			MAX-ACCESS read-only
			STATUS current
			DESCRIPTION
				"Description."
			::= { sleOSPFProcInfoEntry 5 }

		
		-- 1.3.6.1.4.1.6296.101.51.2.1.1.1.6
		sleOSPFProcAbrType OBJECT-TYPE
			SYNTAX INTEGER
				{
				standard(1),
				cisco(2),
				ibm(3),
				shortcut(4)
				}
			MAX-ACCESS read-only
			STATUS current
			DESCRIPTION
				"Description."
			::= { sleOSPFProcInfoEntry 6 }

		
		-- 1.3.6.1.4.1.6296.101.51.2.1.1.1.7
		sleOSPFProcSnmpNotification OBJECT-TYPE
			SYNTAX INTEGER
				{
				disable(0),
				enable(1)
				}
			MAX-ACCESS read-only
			STATUS current
			DESCRIPTION
				"Description."
			::= { sleOSPFProcInfoEntry 7 }

		
		-- 1.3.6.1.4.1.6296.101.51.2.1.1.1.8
		sleOSPFProcDefaultMetricConfig OBJECT-TYPE
			SYNTAX INTEGER
				{
				disable(0),
				enable(1)
				}
			MAX-ACCESS read-only
			STATUS current
			DESCRIPTION
				"Description."
			::= { sleOSPFProcInfoEntry 8 }

		
		-- 1.3.6.1.4.1.6296.101.51.2.1.1.1.9
		sleOSPFProcDefaultMetricValue OBJECT-TYPE
			SYNTAX INTEGER (0..16777214)
			MAX-ACCESS read-only
			STATUS current
			DESCRIPTION
				"Description."
			::= { sleOSPFProcInfoEntry 9 }

		
		-- 1.3.6.1.4.1.6296.101.51.2.1.1.1.10
		sleOSPFProcMaxArea OBJECT-TYPE
			SYNTAX Gauge32 (1..4294967294)
			MAX-ACCESS read-only
			STATUS current
			DESCRIPTION
				"Description."
			::= { sleOSPFProcInfoEntry 10 }

		
		-- 1.3.6.1.4.1.6296.101.51.2.1.1.1.11
		sleOSPFProcMaxConcurrentDD OBJECT-TYPE
			SYNTAX INTEGER (0..65535)
			MAX-ACCESS read-only
			STATUS current
			DESCRIPTION
				"Description."
			::= { sleOSPFProcInfoEntry 11 }

		
		-- 1.3.6.1.4.1.6296.101.51.2.1.1.1.12
		sleOSPFProcCompatiblerfc1583 OBJECT-TYPE
			SYNTAX INTEGER
				{
				uncompatible(0),
				compatible(1)
				}
			MAX-ACCESS read-only
			STATUS current
			DESCRIPTION
				"Description."
			::= { sleOSPFProcInfoEntry 12 }

		
		-- 1.3.6.1.4.1.6296.101.51.2.1.1.1.13
		sleOSPFProcCapabilityOpaque OBJECT-TYPE
			SYNTAX INTEGER
				{
				uncapability(0),
				capability(1)
				}
			MAX-ACCESS read-only
			STATUS current
			DESCRIPTION
				"Description."
			::= { sleOSPFProcInfoEntry 13 }

		
		-- 1.3.6.1.4.1.6296.101.51.2.1.1.1.14
		sleOSPFProcLSDBOverflowType OBJECT-TYPE
			SYNTAX INTEGER
				{
				unspec(0),
				soft(1),
				hard(2)
				}
			MAX-ACCESS read-only
			STATUS current
			DESCRIPTION
				"Description."
			::= { sleOSPFProcInfoEntry 14 }

		
		-- 1.3.6.1.4.1.6296.101.51.2.1.1.1.15
		sleOSPFProcLSDBOverflowLimit OBJECT-TYPE
			SYNTAX Gauge32 (0..4294967294)
			MAX-ACCESS read-only
			STATUS current
			DESCRIPTION
				"Description."
			::= { sleOSPFProcInfoEntry 15 }

		
		-- 1.3.6.1.4.1.6296.101.51.2.1.1.1.16
		sleOSPFProcExtLSDBLimit OBJECT-TYPE
			SYNTAX INTEGER (-1..2147483647)
			MAX-ACCESS read-only
			STATUS current
			DESCRIPTION
				"Description."
			::= { sleOSPFProcInfoEntry 16 }

		
		-- 1.3.6.1.4.1.6296.101.51.2.1.1.1.17
		sleOSPFProcExitOverFlowInterval OBJECT-TYPE
			SYNTAX INTEGER (0..65535)
			MAX-ACCESS read-only
			STATUS current
			DESCRIPTION
				"Description."
			::= { sleOSPFProcInfoEntry 17 }

		
		-- 1.3.6.1.4.1.6296.101.51.2.1.1.1.18
		sleOSPFProcAdminDistance OBJECT-TYPE
			SYNTAX INTEGER (0..255)
			MAX-ACCESS read-only
			STATUS current
			DESCRIPTION
				"Description."
			::= { sleOSPFProcInfoEntry 18 }

		
		-- 1.3.6.1.4.1.6296.101.51.2.1.1.1.19
		sleOSPFProcExternalDistance OBJECT-TYPE
			SYNTAX INTEGER (0..255)
			MAX-ACCESS read-only
			STATUS current
			DESCRIPTION
				"Description."
			::= { sleOSPFProcInfoEntry 19 }

		
		-- 1.3.6.1.4.1.6296.101.51.2.1.1.1.20
		sleOSPFProcIntraAreaDistance OBJECT-TYPE
			SYNTAX INTEGER (0..255)
			MAX-ACCESS read-only
			STATUS current
			DESCRIPTION
				"Description."
			::= { sleOSPFProcInfoEntry 20 }

		
		-- 1.3.6.1.4.1.6296.101.51.2.1.1.1.21
		sleOSPFProcInterAreaDistance OBJECT-TYPE
			SYNTAX INTEGER (0..255)
			MAX-ACCESS read-only
			STATUS current
			DESCRIPTION
				"Description."
			::= { sleOSPFProcInfoEntry 21 }

		
		-- 1.3.6.1.4.1.6296.101.51.2.1.1.1.22
		sleOSPFProcDefaultOriginType OBJECT-TYPE
			SYNTAX INTEGER
				{
				unspec(0),
				normal(1),
				always(2)
				}
			MAX-ACCESS read-only
			STATUS current
			DESCRIPTION
				"Description."
			::= { sleOSPFProcInfoEntry 22 }

		
		-- 1.3.6.1.4.1.6296.101.51.2.1.1.1.23
		sleOSPFProcDefaultOriginMetricType OBJECT-TYPE
			SYNTAX INTEGER
				{
				unspec(0),
				external1(1),
				external2(2)
				}
			MAX-ACCESS read-only
			STATUS current
			DESCRIPTION
				"Description."
			::= { sleOSPFProcInfoEntry 23 }

		
		-- 1.3.6.1.4.1.6296.101.51.2.1.1.1.24
		sleOSPFProcDefaultOriginMetric OBJECT-TYPE
			SYNTAX INTEGER (0..16777215)
			MAX-ACCESS read-only
			STATUS current
			DESCRIPTION
				"Description."
			::= { sleOSPFProcInfoEntry 24 }

		
		-- 1.3.6.1.4.1.6296.101.51.2.1.1.1.25
		sleOSPFProcDefaultOriginRouteMap OBJECT-TYPE
			SYNTAX OCTET STRING (SIZE (0..255))
			MAX-ACCESS read-only
			STATUS current
			DESCRIPTION
				"Description."
			::= { sleOSPFProcInfoEntry 25 }

		
		-- 1.3.6.1.4.1.6296.101.51.2.1.1.1.26
		sleOSPFProcLogNeighborChange OBJECT-TYPE
			SYNTAX INTEGER
				{
				disable(0),
				enable(1)
				}
			MAX-ACCESS read-only
			STATUS current
			DESCRIPTION
				"Description."
			::= { sleOSPFProcInfoEntry 26 }

		
		-- 1.3.6.1.4.1.6296.101.51.2.1.1.1.27
		sleOSPFProcPassiveIfAll OBJECT-TYPE
			SYNTAX INTEGER
				{
				disable(0),
				enable(1)
				}
			MAX-ACCESS read-only
			STATUS current
			DESCRIPTION
				"Description."
			::= { sleOSPFProcInfoEntry 27 }

		
		-- 1.3.6.1.4.1.6296.101.51.2.1.1.1.28
		sleOSPFProcBfdIFAll OBJECT-TYPE
			SYNTAX INTEGER
				{
				disable(0),
				enable(1)
				}
			MAX-ACCESS read-only
			STATUS current
			DESCRIPTION
				"Description."
			::= { sleOSPFProcInfoEntry 28 }

		
		-- 1.3.6.1.4.1.6296.101.51.2.1.1.1.29
		sleOSPFProcEfmIFAll OBJECT-TYPE
			SYNTAX INTEGER
				{
				disable(0),
				enable(1)
				}
			MAX-ACCESS read-only
			STATUS current
			DESCRIPTION
				"Description."
			::= { sleOSPFProcInfoEntry 29 }

		
		-- 1.3.6.1.4.1.6296.101.51.2.1.1.1.30
		sleOSPFProcCapabilityRestart OBJECT-TYPE
			SYNTAX INTEGER
				{
				none(0),
				graceful(1),
				signaling(2),
				gracefulAck(3)
				}
			MAX-ACCESS read-only
			STATUS current
			DESCRIPTION
				"The Restart-Capability that this OSPF Process has. "
			::= { sleOSPFProcInfoEntry 30 }

		
		-- 1.3.6.1.4.1.6296.101.51.2.1.2
		sleOSPFProcInfoControl OBJECT IDENTIFIER ::= { sleOSPFProcInfo 2 }

		
		-- 1.3.6.1.4.1.6296.101.51.2.1.2.1
		sleOSPFProcControlRequest OBJECT-TYPE
			SYNTAX INTEGER
				{
				createOSPFProcess(1),
				deleteOSPFProcess(2),
				createOSPFProcRouterID(3),
				deleteOSPFProcRouterID(4),
				setOSPFProcSPFTimer(5),
				setOSPFProcAutoCost(6),
				setOSPFProcAbrType(7),
				setOSPFProcSnmpNotification(8),
				setOSPFProcDefaultMetricProfile(9),
				setOSPFProcMaximumArea(10),
				setOSPFProcMaxConcurDD(11),
				setOSPFProcComprfc1583(12),
				setOSPFProcCapOpaque(13),
				setOSPFProcLSDBOverflowProfile(14),
				setOSPFProcExtOverflowProfile(15),
				setOSPFProcAdminDistance(16),
				setOSPFProcExtDistance(17),
				setOSPFProcIntraDistance(18),
				setOSPFProcInterDistance(19),
				setOSPFProcDefaultOriginType(20),
				setOSPFProcDefaultOriginMetricType(21),
				setOSPFProcDefaultOriginMetric(22),
				setOSPFProcDefaultOriginRouteMap(23),
				setOSPFProcLogNeighborChange(24),
				setOSPFProcPassiveIfAll(25),
				setOSPFProcBfdIFAll(26),
				setOSPFProcEfmIFAll(27),
				setOSPFProcCapRestart(28),
				clearOSPFProcess(29)
				}
			MAX-ACCESS read-write
			STATUS current
			DESCRIPTION
				"Description."
			::= { sleOSPFProcInfoControl 1 }

		
		-- 1.3.6.1.4.1.6296.101.51.2.1.2.2
		sleOSPFProcControlStatus OBJECT-TYPE
			SYNTAX SleControlStatusType
			MAX-ACCESS read-only
			STATUS current
			DESCRIPTION
				"Description."
			::= { sleOSPFProcInfoControl 2 }

		
		-- 1.3.6.1.4.1.6296.101.51.2.1.2.3
		sleOSPFProcControlTimer OBJECT-TYPE
			SYNTAX Gauge32
			MAX-ACCESS read-write
			STATUS current
			DESCRIPTION
				"Description."
			::= { sleOSPFProcInfoControl 3 }

		
		-- 1.3.6.1.4.1.6296.101.51.2.1.2.4
		sleOSPFProcControlTimeStamp OBJECT-TYPE
			SYNTAX TimeTicks
			MAX-ACCESS read-only
			STATUS current
			DESCRIPTION
				"Description."
			::= { sleOSPFProcInfoControl 4 }

		
		-- 1.3.6.1.4.1.6296.101.51.2.1.2.5
		sleOSPFProcControlReqResult OBJECT-TYPE
			SYNTAX SleControlRequestResultType
			MAX-ACCESS read-only
			STATUS current
			DESCRIPTION
				"Description."
			::= { sleOSPFProcInfoControl 5 }

		
		-- 1.3.6.1.4.1.6296.101.51.2.1.2.6
		sleOSPFProcControlID OBJECT-TYPE
			SYNTAX INTEGER (0..65535)
			MAX-ACCESS read-write
			STATUS current
			DESCRIPTION
				"Description."
			::= { sleOSPFProcInfoControl 6 }

		
		-- 1.3.6.1.4.1.6296.101.51.2.1.2.7
		sleOSPFProcControlRouterID OBJECT-TYPE
			SYNTAX IpAddress
			MAX-ACCESS read-write
			STATUS current
			DESCRIPTION
				"Description."
			::= { sleOSPFProcInfoControl 7 }

		
		-- 1.3.6.1.4.1.6296.101.51.2.1.2.8
		sleOSPFProcControlSPFDelayTime OBJECT-TYPE
			SYNTAX INTEGER (0..2147483647)
			MAX-ACCESS read-write
			STATUS current
			DESCRIPTION
				"Description."
			::= { sleOSPFProcInfoControl 8 }

		
		-- 1.3.6.1.4.1.6296.101.51.2.1.2.9
		sleOSPFProcControlSPFHoldTime OBJECT-TYPE
			SYNTAX INTEGER (0..2147483647)
			MAX-ACCESS read-write
			STATUS current
			DESCRIPTION
				"Description."
			::= { sleOSPFProcInfoControl 9 }

		
		-- 1.3.6.1.4.1.6296.101.51.2.1.2.10
		sleOSPFProcControlAutoCost OBJECT-TYPE
			SYNTAX INTEGER (0..4294967)
			MAX-ACCESS read-write
			STATUS current
			DESCRIPTION
				"Description."
			::= { sleOSPFProcInfoControl 10 }

		
		-- 1.3.6.1.4.1.6296.101.51.2.1.2.11
		sleOSPFProcControlAbrType OBJECT-TYPE
			SYNTAX INTEGER
				{
				standard(1),
				cisco(2),
				ibm(3),
				shortcut(4)
				}
			MAX-ACCESS read-write
			STATUS current
			DESCRIPTION
				"Description."
			::= { sleOSPFProcInfoControl 11 }

		
		-- 1.3.6.1.4.1.6296.101.51.2.1.2.12
		sleOSPFProcControlSnmpNotification OBJECT-TYPE
			SYNTAX INTEGER
				{
				disable(0),
				enable(1)
				}
			MAX-ACCESS read-write
			STATUS current
			DESCRIPTION
				"Description."
			::= { sleOSPFProcInfoControl 12 }

		
		-- 1.3.6.1.4.1.6296.101.51.2.1.2.13
		sleOSPFProcControlDefaultMetricConfig OBJECT-TYPE
			SYNTAX INTEGER
				{
				disable(0),
				enable(1)
				}
			MAX-ACCESS read-write
			STATUS current
			DESCRIPTION
				"Description."
			::= { sleOSPFProcInfoControl 13 }

		
		-- 1.3.6.1.4.1.6296.101.51.2.1.2.14
		sleOSPFProcControlDefaultMetricValue OBJECT-TYPE
			SYNTAX INTEGER (0..16777214)
			MAX-ACCESS read-write
			STATUS current
			DESCRIPTION
				"Description."
			::= { sleOSPFProcInfoControl 14 }

		
		-- 1.3.6.1.4.1.6296.101.51.2.1.2.15
		sleOSPFProcControlMaxArea OBJECT-TYPE
			SYNTAX Gauge32 (1..4294967294)
			MAX-ACCESS read-write
			STATUS current
			DESCRIPTION
				"Description."
			::= { sleOSPFProcInfoControl 15 }

		
		-- 1.3.6.1.4.1.6296.101.51.2.1.2.16
		sleOSPFProcControlMaxConcurDD OBJECT-TYPE
			SYNTAX INTEGER (0..65535)
			MAX-ACCESS read-write
			STATUS current
			DESCRIPTION
				"Description."
			::= { sleOSPFProcInfoControl 16 }

		
		-- 1.3.6.1.4.1.6296.101.51.2.1.2.17
		sleOSPFProcControlComprfc1583 OBJECT-TYPE
			SYNTAX INTEGER
				{
				uncompatible(0),
				compatible(1)
				}
			MAX-ACCESS read-write
			STATUS current
			DESCRIPTION
				"Description."
			::= { sleOSPFProcInfoControl 17 }

		
		-- 1.3.6.1.4.1.6296.101.51.2.1.2.18
		sleOSPFProcControlCapabilityOpaque OBJECT-TYPE
			SYNTAX INTEGER
				{
				uncapability(0),
				capability(1)
				}
			MAX-ACCESS read-write
			STATUS current
			DESCRIPTION
				"Description."
			::= { sleOSPFProcInfoControl 18 }

		
		-- 1.3.6.1.4.1.6296.101.51.2.1.2.19
		sleOSPFProcControlLSDBOverflowType OBJECT-TYPE
			SYNTAX INTEGER
				{
				unspec(0),
				soft(1),
				hard(2)
				}
			MAX-ACCESS read-write
			STATUS current
			DESCRIPTION
				"Description."
			::= { sleOSPFProcInfoControl 19 }

		
		-- 1.3.6.1.4.1.6296.101.51.2.1.2.20
		sleOSPFProcControlLSDBOverflowLimit OBJECT-TYPE
			SYNTAX Gauge32 (0..4294967294)
			MAX-ACCESS read-write
			STATUS current
			DESCRIPTION
				"Description."
			::= { sleOSPFProcInfoControl 20 }

		
		-- 1.3.6.1.4.1.6296.101.51.2.1.2.21
		sleOSPFProcControlExtLSDBLimit OBJECT-TYPE
			SYNTAX INTEGER (-1..2147483647)
			MAX-ACCESS read-write
			STATUS current
			DESCRIPTION
				"Description."
			::= { sleOSPFProcInfoControl 21 }

		
		-- 1.3.6.1.4.1.6296.101.51.2.1.2.22
		sleOSPFProcControlExitOverFlowInterval OBJECT-TYPE
			SYNTAX INTEGER (0..65535)
			MAX-ACCESS read-write
			STATUS current
			DESCRIPTION
				"Description."
			::= { sleOSPFProcInfoControl 22 }

		
		-- 1.3.6.1.4.1.6296.101.51.2.1.2.23
		sleOSPFProcControlAdminDistance OBJECT-TYPE
			SYNTAX INTEGER (0..255)
			MAX-ACCESS read-write
			STATUS current
			DESCRIPTION
				"Description."
			::= { sleOSPFProcInfoControl 23 }

		
		-- 1.3.6.1.4.1.6296.101.51.2.1.2.24
		sleOSPFProcControlExtDistance OBJECT-TYPE
			SYNTAX INTEGER (0..255)
			MAX-ACCESS read-write
			STATUS current
			DESCRIPTION
				"Description."
			::= { sleOSPFProcInfoControl 24 }

		
		-- 1.3.6.1.4.1.6296.101.51.2.1.2.25
		sleOSPFProcControlIntraAreaDistance OBJECT-TYPE
			SYNTAX INTEGER (0..255)
			MAX-ACCESS read-write
			STATUS current
			DESCRIPTION
				"Description."
			::= { sleOSPFProcInfoControl 25 }

		
		-- 1.3.6.1.4.1.6296.101.51.2.1.2.26
		sleOSPFProcControlInterAreaDistance OBJECT-TYPE
			SYNTAX INTEGER (0..255)
			MAX-ACCESS read-write
			STATUS current
			DESCRIPTION
				"Description."
			::= { sleOSPFProcInfoControl 26 }

		
		-- 1.3.6.1.4.1.6296.101.51.2.1.2.27
		sleOSPFProcControlDefOriginType OBJECT-TYPE
			SYNTAX INTEGER
				{
				unspec(0),
				normal(1),
				always(2)
				}
			MAX-ACCESS read-write
			STATUS current
			DESCRIPTION
				"Description."
			::= { sleOSPFProcInfoControl 27 }

		
		-- 1.3.6.1.4.1.6296.101.51.2.1.2.28
		sleOSPFProcControlDefOriginMetricType OBJECT-TYPE
			SYNTAX INTEGER
				{
				unspec(0),
				external1(1),
				external2(2)
				}
			MAX-ACCESS read-write
			STATUS current
			DESCRIPTION
				"Description."
			::= { sleOSPFProcInfoControl 28 }

		
		-- 1.3.6.1.4.1.6296.101.51.2.1.2.29
		sleOSPFProcControlDefOriginMetric OBJECT-TYPE
			SYNTAX INTEGER (0..16777215)
			MAX-ACCESS read-write
			STATUS current
			DESCRIPTION
				"Description."
			::= { sleOSPFProcInfoControl 29 }

		
		-- 1.3.6.1.4.1.6296.101.51.2.1.2.30
		sleOSPFProcControlDefOriginRouteMap OBJECT-TYPE
			SYNTAX OCTET STRING (SIZE (0..255))
			MAX-ACCESS read-write
			STATUS current
			DESCRIPTION
				"Description."
			::= { sleOSPFProcInfoControl 30 }

		
		-- 1.3.6.1.4.1.6296.101.51.2.1.2.31
		sleOSPFProcControlLogNeighborChange OBJECT-TYPE
			SYNTAX INTEGER
				{
				disable(0),
				enable(1)
				}
			MAX-ACCESS read-write
			STATUS current
			DESCRIPTION
				"Description."
			::= { sleOSPFProcInfoControl 31 }

		
		-- 1.3.6.1.4.1.6296.101.51.2.1.2.32
		sleOSPFProcControlPassiveIFAll OBJECT-TYPE
			SYNTAX INTEGER
				{
				disable(0),
				enable(1)
				}
			MAX-ACCESS read-write
			STATUS current
			DESCRIPTION
				"Description."
			::= { sleOSPFProcInfoControl 32 }

		
		-- 1.3.6.1.4.1.6296.101.51.2.1.2.33
		sleOSPFProcControlBfdIFAll OBJECT-TYPE
			SYNTAX INTEGER
				{
				disable(0),
				enable(1)
				}
			MAX-ACCESS read-write
			STATUS current
			DESCRIPTION
				"Description."
			::= { sleOSPFProcInfoControl 33 }

		
		-- 1.3.6.1.4.1.6296.101.51.2.1.2.34
		sleOSPFProcControlEfmIFAll OBJECT-TYPE
			SYNTAX INTEGER
				{
				disable(0),
				enable(1)
				}
			MAX-ACCESS read-write
			STATUS current
			DESCRIPTION
				"Description."
			::= { sleOSPFProcInfoControl 34 }

		
		-- 1.3.6.1.4.1.6296.101.51.2.1.2.35
		sleOSPFProcControlCapabilityRestart OBJECT-TYPE
			SYNTAX INTEGER
				{
				none(0),
				graceful(1),
				signaling(2),
				gracefulAck(3)
				}
			MAX-ACCESS read-write
			STATUS current
			DESCRIPTION
				"The Restart-Capability that this OSPF Process has. "
			::= { sleOSPFProcInfoControl 35 }

		
		-- 1.3.6.1.4.1.6296.101.51.2.1.3
		sleOSPFProcInfoNotification OBJECT IDENTIFIER ::= { sleOSPFProcInfo 3 }

		
		-- 1.3.6.1.4.1.6296.101.51.2.1.3.1
		sleOSPFProcCreated NOTIFICATION-TYPE
			OBJECTS { sleOSPFProcControlRequest, sleOSPFProcControlTimeStamp, sleOSPFProcControlReqResult, sleOSPFProcID }
			STATUS current
			DESCRIPTION 
				"Description."
			::= { sleOSPFProcInfoNotification 1 }

		
		-- 1.3.6.1.4.1.6296.101.51.2.1.3.2
		sleOSPFProcDeleted NOTIFICATION-TYPE
			OBJECTS { sleOSPFProcControlRequest, sleOSPFProcControlTimeStamp, sleOSPFProcControlReqResult, sleOSPFProcControlID }
			STATUS current
			DESCRIPTION 
				"Description."
			::= { sleOSPFProcInfoNotification 2 }

		
		-- 1.3.6.1.4.1.6296.101.51.2.1.3.3
		sleOSPFRouterIDCreated NOTIFICATION-TYPE
			OBJECTS { sleOSPFProcControlRequest, sleOSPFProcControlTimeStamp, sleOSPFProcControlReqResult, sleOSPFProcID, sleOSPFProcRouterID
				 }
			STATUS current
			DESCRIPTION 
				"Description."
			::= { sleOSPFProcInfoNotification 3 }

		
		-- 1.3.6.1.4.1.6296.101.51.2.1.3.4
		sleOSPFRouterIDDeleted NOTIFICATION-TYPE
			OBJECTS { sleOSPFProcControlRequest, sleOSPFProcControlTimeStamp, sleOSPFProcControlReqResult, sleOSPFProcID, sleOSPFProcControlRouterID
				 }
			STATUS current
			DESCRIPTION 
				"Description."
			::= { sleOSPFProcInfoNotification 4 }

		
		-- 1.3.6.1.4.1.6296.101.51.2.1.3.5
		sleOSPFProcSPFTimerChanged NOTIFICATION-TYPE
			OBJECTS { sleOSPFProcControlRequest, sleOSPFProcControlTimeStamp, sleOSPFProcControlReqResult, sleOSPFProcID, sleOSPFProcSPFDelayTime, 
				sleOSPFProcSPFHoldTime }
			STATUS current
			DESCRIPTION 
				"Description."
			::= { sleOSPFProcInfoNotification 5 }

		
		-- 1.3.6.1.4.1.6296.101.51.2.1.3.6
		sleOSPFProcAutoCostChanged NOTIFICATION-TYPE
			OBJECTS { sleOSPFProcControlRequest, sleOSPFProcControlTimeStamp, sleOSPFProcControlReqResult, sleOSPFProcID, sleOSPFProcAutoCost
				 }
			STATUS current
			DESCRIPTION 
				"Description."
			::= { sleOSPFProcInfoNotification 6 }

		
		-- 1.3.6.1.4.1.6296.101.51.2.1.3.7
		sleOSPFProcAbrTypeChanged NOTIFICATION-TYPE
			OBJECTS { sleOSPFProcControlRequest, sleOSPFProcControlTimeStamp, sleOSPFProcControlReqResult, sleOSPFProcID, sleOSPFProcAbrType
				 }
			STATUS current
			DESCRIPTION 
				"Description."
			::= { sleOSPFProcInfoNotification 7 }

		
		-- 1.3.6.1.4.1.6296.101.51.2.1.3.8
		sleOSPFProcSnmpNotificationChanged NOTIFICATION-TYPE
			OBJECTS { sleOSPFProcControlRequest, sleOSPFProcControlTimeStamp, sleOSPFProcControlReqResult, sleOSPFProcID, sleOSPFProcSnmpNotification
				 }
			STATUS current
			DESCRIPTION 
				"Description."
			::= { sleOSPFProcInfoNotification 8 }

		
		-- 1.3.6.1.4.1.6296.101.51.2.1.3.9
		sleOSPFProcDefaultMetricProfileChanged NOTIFICATION-TYPE
			OBJECTS { sleOSPFProcControlRequest, sleOSPFProcControlTimeStamp, sleOSPFProcControlReqResult, sleOSPFProcID, sleOSPFProcDefaultMetricConfig, 
				sleOSPFProcDefaultMetricValue }
			STATUS current
			DESCRIPTION 
				"Description."
			::= { sleOSPFProcInfoNotification 9 }

		
		-- 1.3.6.1.4.1.6296.101.51.2.1.3.10
		sleOSPFProcMaxAreaChanged NOTIFICATION-TYPE
			OBJECTS { sleOSPFProcControlRequest, sleOSPFProcControlTimeStamp, sleOSPFProcControlReqResult, sleOSPFProcID, sleOSPFProcMaxArea
				 }
			STATUS current
			DESCRIPTION 
				"Description."
			::= { sleOSPFProcInfoNotification 10 }

		
		-- 1.3.6.1.4.1.6296.101.51.2.1.3.11
		sleOSPFProcMaxConcurDDChanged NOTIFICATION-TYPE
			OBJECTS { sleOSPFProcControlRequest, sleOSPFProcControlTimeStamp, sleOSPFProcControlReqResult, sleOSPFProcID, sleOSPFProcMaxConcurrentDD
				 }
			STATUS current
			DESCRIPTION 
				"Description."
			::= { sleOSPFProcInfoNotification 11 }

		
		-- 1.3.6.1.4.1.6296.101.51.2.1.3.12
		sleOSPFProcComrfc1853Changed NOTIFICATION-TYPE
			OBJECTS { sleOSPFProcControlRequest, sleOSPFProcControlTimeStamp, sleOSPFProcControlReqResult, sleOSPFProcID, sleOSPFProcCompatiblerfc1583
				 }
			STATUS current
			DESCRIPTION 
				"Description."
			::= { sleOSPFProcInfoNotification 12 }

		
		-- 1.3.6.1.4.1.6296.101.51.2.1.3.13
		sleOSPFProcCapOpaqueChanged NOTIFICATION-TYPE
			OBJECTS { sleOSPFProcControlRequest, sleOSPFProcControlTimeStamp, sleOSPFProcControlReqResult, sleOSPFProcID, sleOSPFProcCapabilityOpaque
				 }
			STATUS current
			DESCRIPTION 
				"Description."
			::= { sleOSPFProcInfoNotification 13 }

		
		-- 1.3.6.1.4.1.6296.101.51.2.1.3.14
		sleOSPFProcLSDBOverflowProfileChanged NOTIFICATION-TYPE
			OBJECTS { sleOSPFProcControlRequest, sleOSPFProcControlTimeStamp, sleOSPFProcControlReqResult, sleOSPFProcID, sleOSPFProcLSDBOverflowType, 
				sleOSPFProcLSDBOverflowLimit }
			STATUS current
			DESCRIPTION 
				"Description."
			::= { sleOSPFProcInfoNotification 14 }

		
		-- 1.3.6.1.4.1.6296.101.51.2.1.3.15
		sleOSPFProcExtOverflowProfileChanged NOTIFICATION-TYPE
			OBJECTS { sleOSPFProcControlRequest, sleOSPFProcControlTimeStamp, sleOSPFProcControlReqResult, sleOSPFProcID, sleOSPFProcExtLSDBLimit, 
				sleOSPFProcExitOverFlowInterval }
			STATUS current
			DESCRIPTION 
				"Description."
			::= { sleOSPFProcInfoNotification 15 }

		
		-- 1.3.6.1.4.1.6296.101.51.2.1.3.16
		sleOSPFProcAdminDistanceChanged NOTIFICATION-TYPE
			OBJECTS { sleOSPFProcControlRequest, sleOSPFProcControlTimeStamp, sleOSPFProcControlReqResult, sleOSPFProcID, sleOSPFProcAdminDistance
				 }
			STATUS current
			DESCRIPTION 
				"Description."
			::= { sleOSPFProcInfoNotification 16 }

		
		-- 1.3.6.1.4.1.6296.101.51.2.1.3.17
		sleOSPFProcExtDistanceChanged NOTIFICATION-TYPE
			OBJECTS { sleOSPFProcControlRequest, sleOSPFProcControlTimeStamp, sleOSPFProcControlReqResult, sleOSPFProcID, sleOSPFProcExternalDistance
				 }
			STATUS current
			DESCRIPTION 
				"Description."
			::= { sleOSPFProcInfoNotification 17 }

		
		-- 1.3.6.1.4.1.6296.101.51.2.1.3.18
		sleOSPFProcIntraDistanceChanged NOTIFICATION-TYPE
			OBJECTS { sleOSPFProcControlRequest, sleOSPFProcControlTimeStamp, sleOSPFProcControlReqResult, sleOSPFProcID, sleOSPFProcIntraAreaDistance
				 }
			STATUS current
			DESCRIPTION 
				"Description."
			::= { sleOSPFProcInfoNotification 18 }

		
		-- 1.3.6.1.4.1.6296.101.51.2.1.3.19
		sleOSPFProcInterDistanceChanged NOTIFICATION-TYPE
			OBJECTS { sleOSPFProcControlRequest, sleOSPFProcControlTimeStamp, sleOSPFProcControlReqResult, sleOSPFProcID, sleOSPFProcInterAreaDistance
				 }
			STATUS current
			DESCRIPTION 
				"Description."
			::= { sleOSPFProcInfoNotification 19 }

		
		-- 1.3.6.1.4.1.6296.101.51.2.1.3.20
		sleOSPFProcDefaultOriginTypeChanged NOTIFICATION-TYPE
			OBJECTS { sleOSPFProcControlRequest, sleOSPFProcControlTimeStamp, sleOSPFProcControlReqResult, sleOSPFProcID, sleOSPFProcDefaultOriginType
				 }
			STATUS current
			DESCRIPTION 
				"Description."
			::= { sleOSPFProcInfoNotification 20 }

		
		-- 1.3.6.1.4.1.6296.101.51.2.1.3.21
		sleOSPFProcDefaultOriginMetricTypeChanged NOTIFICATION-TYPE
			OBJECTS { sleOSPFProcControlRequest, sleOSPFProcControlTimeStamp, sleOSPFProcControlReqResult, sleOSPFProcID, sleOSPFProcDefaultOriginMetricType
				 }
			STATUS current
			DESCRIPTION 
				"Description."
			::= { sleOSPFProcInfoNotification 21 }

		
		-- 1.3.6.1.4.1.6296.101.51.2.1.3.22
		sleOSPFProcDefaultOriginMetricChanged NOTIFICATION-TYPE
			OBJECTS { sleOSPFProcControlRequest, sleOSPFProcControlTimeStamp, sleOSPFProcControlReqResult, sleOSPFProcID, sleOSPFProcDefaultOriginMetric
				 }
			STATUS current
			DESCRIPTION 
				"Description."
			::= { sleOSPFProcInfoNotification 22 }

		
		-- 1.3.6.1.4.1.6296.101.51.2.1.3.23
		sleOSPFProcDefaultOriginRouteMapChanged NOTIFICATION-TYPE
			OBJECTS { sleOSPFProcControlRequest, sleOSPFProcControlTimeStamp, sleOSPFProcControlReqResult, sleOSPFProcID, sleOSPFProcDefaultOriginRouteMap
				 }
			STATUS current
			DESCRIPTION 
				"Description."
			::= { sleOSPFProcInfoNotification 23 }

		
		-- 1.3.6.1.4.1.6296.101.51.2.1.3.24
		sleOSPFProcLogNeighborChanged NOTIFICATION-TYPE
			OBJECTS { sleOSPFProcControlRequest, sleOSPFProcControlTimeStamp, sleOSPFProcControlReqResult, sleOSPFProcID, sleOSPFProcLogNeighborChange
				 }
			STATUS current
			DESCRIPTION 
				"Description."
			::= { sleOSPFProcInfoNotification 24 }

		
		-- 1.3.6.1.4.1.6296.101.51.2.1.3.25
		sleOSPFProcPassiveIFAllChanged NOTIFICATION-TYPE
			OBJECTS { sleOSPFProcControlRequest, sleOSPFProcControlTimeStamp, sleOSPFProcControlReqResult, sleOSPFProcID, sleOSPFProcPassiveIfAll
				 }
			STATUS current
			DESCRIPTION 
				"Description."
			::= { sleOSPFProcInfoNotification 25 }

		
		-- 1.3.6.1.4.1.6296.101.51.2.1.3.26
		sleOSPFProcBfdIFAllChanged NOTIFICATION-TYPE
			OBJECTS { sleOSPFProcControlRequest, sleOSPFProcControlTimeStamp, sleOSPFProcControlReqResult, sleOSPFProcID, sleOSPFProcBfdIFAll
				 }
			STATUS current
			DESCRIPTION 
				"Description."
			::= { sleOSPFProcInfoNotification 26 }

		
		-- 1.3.6.1.4.1.6296.101.51.2.1.3.27
		sleOSPFProcEfmIFAllChanged NOTIFICATION-TYPE
			OBJECTS { sleOSPFProcControlRequest, sleOSPFProcControlTimeStamp, sleOSPFProcControlReqResult, sleOSPFProcID, sleOSPFProcEfmIFAll
				 }
			STATUS current
			DESCRIPTION 
				"Description."
			::= { sleOSPFProcInfoNotification 27 }

		
		-- 1.3.6.1.4.1.6296.101.51.2.1.3.28
		sleOSPFProcCapRestartChanged NOTIFICATION-TYPE
			OBJECTS { sleOSPFProcControlRequest, sleOSPFProcControlTimeStamp, sleOSPFProcCapabilityRestart, sleOSPFProcControlReqResult, sleOSPFProcID
				 }
			STATUS current
			DESCRIPTION 
				"Description."
			::= { sleOSPFProcInfoNotification 28 }

		
		-- 1.3.6.1.4.1.6296.101.51.2.1.3.29
		sleOSPFProcCleared NOTIFICATION-TYPE
			OBJECTS { sleOSPFProcControlRequest, sleOSPFProcControlTimeStamp, sleOSPFProcControlReqResult, sleOSPFProcID }
			STATUS current
			DESCRIPTION 
				"Description."
			::= { sleOSPFProcInfoNotification 29 }

		
		-- 1.3.6.1.4.1.6296.101.51.2.2
		sleOSPFProcNetwork OBJECT IDENTIFIER ::= { sleOSPFProc 2 }

		
		-- 1.3.6.1.4.1.6296.101.51.2.2.1
		sleOSPFProcNetworkTable OBJECT-TYPE
			SYNTAX SEQUENCE OF SleOSPFProcNetworkEntry
			MAX-ACCESS not-accessible
			STATUS current
			DESCRIPTION
				"Description."
			::= { sleOSPFProcNetwork 1 }

		
		-- 1.3.6.1.4.1.6296.101.51.2.2.1.1
		sleOSPFProcNetworkEntry OBJECT-TYPE
			SYNTAX SleOSPFProcNetworkEntry
			MAX-ACCESS not-accessible
			STATUS current
			DESCRIPTION
				"Description."
			INDEX { sleOSPFProcID, sleOSPFProcNetworkIP, sleOSPFProcNetworkIPMask }
			::= { sleOSPFProcNetworkTable 1 }

		
		SleOSPFProcNetworkEntry ::=
			SEQUENCE { 
				sleOSPFProcNetworkIP
					IpAddress,
				sleOSPFProcNetworkIPMask
					Integer32,
				sleOSPFProcNetworkAreaID
					IpAddress
			 }

		-- 1.3.6.1.4.1.6296.101.51.2.2.1.1.1
		sleOSPFProcNetworkIP OBJECT-TYPE
			SYNTAX IpAddress
			MAX-ACCESS read-only
			STATUS current
			DESCRIPTION
				"Description."
			::= { sleOSPFProcNetworkEntry 1 }

		
		-- 1.3.6.1.4.1.6296.101.51.2.2.1.1.2
		sleOSPFProcNetworkIPMask OBJECT-TYPE
			SYNTAX Integer32 (0..32)
			MAX-ACCESS read-only
			STATUS current
			DESCRIPTION
				"Description."
			::= { sleOSPFProcNetworkEntry 2 }

		
		-- 1.3.6.1.4.1.6296.101.51.2.2.1.1.3
		sleOSPFProcNetworkAreaID OBJECT-TYPE
			SYNTAX IpAddress
			MAX-ACCESS read-only
			STATUS current
			DESCRIPTION
				"Description."
			::= { sleOSPFProcNetworkEntry 3 }

		
		-- 1.3.6.1.4.1.6296.101.51.2.2.2
		sleOSPFProcNetworkControl OBJECT IDENTIFIER ::= { sleOSPFProcNetwork 2 }

		
		-- 1.3.6.1.4.1.6296.101.51.2.2.2.1
		sleOSPFProcNetworkControlRequest OBJECT-TYPE
			SYNTAX INTEGER
				{
				createOSPFProcNetwork(1),
				deleteOSPFProcNetwork(2)
				}
			MAX-ACCESS read-write
			STATUS current
			DESCRIPTION
				"Description."
			::= { sleOSPFProcNetworkControl 1 }

		
		-- 1.3.6.1.4.1.6296.101.51.2.2.2.2
		sleOSPFProcNetworkControlStatus OBJECT-TYPE
			SYNTAX SleControlStatusType
			MAX-ACCESS read-only
			STATUS current
			DESCRIPTION
				"Description."
			::= { sleOSPFProcNetworkControl 2 }

		
		-- 1.3.6.1.4.1.6296.101.51.2.2.2.3
		sleOSPFProcNetworkControlTimer OBJECT-TYPE
			SYNTAX Gauge32
			MAX-ACCESS read-only
			STATUS current
			DESCRIPTION
				"Description."
			::= { sleOSPFProcNetworkControl 3 }

		
		-- 1.3.6.1.4.1.6296.101.51.2.2.2.4
		sleOSPFProcNetworkControlTimeStamp OBJECT-TYPE
			SYNTAX TimeTicks
			MAX-ACCESS read-only
			STATUS current
			DESCRIPTION
				"Description."
			::= { sleOSPFProcNetworkControl 4 }

		
		-- 1.3.6.1.4.1.6296.101.51.2.2.2.5
		sleOSPFProcNetworkControlReqResult OBJECT-TYPE
			SYNTAX SleControlRequestResultType
			MAX-ACCESS read-write
			STATUS current
			DESCRIPTION
				"Description."
			::= { sleOSPFProcNetworkControl 5 }

		
		-- 1.3.6.1.4.1.6296.101.51.2.2.2.6
		sleOSPFProcNetworkControlProcID OBJECT-TYPE
			SYNTAX INTEGER (0..65535)
			MAX-ACCESS read-write
			STATUS current
			DESCRIPTION
				"Description."
			::= { sleOSPFProcNetworkControl 6 }

		
		-- 1.3.6.1.4.1.6296.101.51.2.2.2.7
		sleOSPFProcNetworkControlIP OBJECT-TYPE
			SYNTAX IpAddress
			MAX-ACCESS read-write
			STATUS current
			DESCRIPTION
				"Description."
			::= { sleOSPFProcNetworkControl 7 }

		
		-- 1.3.6.1.4.1.6296.101.51.2.2.2.8
		sleOSPFProcNetworkControlIPMask OBJECT-TYPE
			SYNTAX INTEGER (0..32)
			MAX-ACCESS read-write
			STATUS current
			DESCRIPTION
				"Description."
			::= { sleOSPFProcNetworkControl 8 }

		
		-- 1.3.6.1.4.1.6296.101.51.2.2.2.9
		sleOSPFProcNetworkControlAreaID OBJECT-TYPE
			SYNTAX IpAddress
			MAX-ACCESS read-write
			STATUS current
			DESCRIPTION
				"Description."
			::= { sleOSPFProcNetworkControl 9 }

		
		-- 1.3.6.1.4.1.6296.101.51.2.2.3
		sleOSPFProcNetworkNotification OBJECT IDENTIFIER ::= { sleOSPFProcNetwork 3 }

		
		-- 1.3.6.1.4.1.6296.101.51.2.2.3.1
		sleOSPFProcNetworkCreated NOTIFICATION-TYPE
			OBJECTS { sleOSPFProcNetworkControlRequest, sleOSPFProcNetworkControlTimeStamp, sleOSPFProcNetworkControlReqResult, sleOSPFProcID, sleOSPFProcNetworkIP, 
				sleOSPFProcNetworkIPMask, sleOSPFProcNetworkAreaID }
			STATUS current
			DESCRIPTION 
				"Description."
			::= { sleOSPFProcNetworkNotification 1 }

		
		-- 1.3.6.1.4.1.6296.101.51.2.2.3.2
		sleOSPFProcNetworkDeleted NOTIFICATION-TYPE
			OBJECTS { sleOSPFProcNetworkControlRequest, sleOSPFProcNetworkControlTimeStamp, sleOSPFProcNetworkControlReqResult, sleOSPFProcID, sleOSPFProcNetworkControlIP, 
				sleOSPFProcNetworkControlIPMask, sleOSPFProcNetworkControlAreaID }
			STATUS current
			DESCRIPTION 
				"Description."
			::= { sleOSPFProcNetworkNotification 2 }

		
		-- 1.3.6.1.4.1.6296.101.51.2.3
		sleOSPFProcSummary OBJECT IDENTIFIER ::= { sleOSPFProc 3 }

		
		-- 1.3.6.1.4.1.6296.101.51.2.3.1
		sleOSPFProcSummaryTable OBJECT-TYPE
			SYNTAX SEQUENCE OF SleOSPFProcSummaryEntry
			MAX-ACCESS not-accessible
			STATUS current
			DESCRIPTION
				"Description."
			::= { sleOSPFProcSummary 1 }

		
		-- 1.3.6.1.4.1.6296.101.51.2.3.1.1
		sleOSPFProcSummaryEntry OBJECT-TYPE
			SYNTAX SleOSPFProcSummaryEntry
			MAX-ACCESS not-accessible
			STATUS current
			DESCRIPTION
				"Description."
			INDEX { sleOSPFProcID, sleOSPFProcSummaryIPAddress, sleOSPFProcSummaryIPMask }
			::= { sleOSPFProcSummaryTable 1 }

		
		SleOSPFProcSummaryEntry ::=
			SEQUENCE { 
				sleOSPFProcSummaryIPAddress
					IpAddress,
				sleOSPFProcSummaryIPMask
					Integer32,
				sleOSPFProcSummaryTag
					Gauge32,
				sleOSPFProcSummaryAdvertiseFlag
					INTEGER
			 }

		-- 1.3.6.1.4.1.6296.101.51.2.3.1.1.1
		sleOSPFProcSummaryIPAddress OBJECT-TYPE
			SYNTAX IpAddress
			MAX-ACCESS read-only
			STATUS current
			DESCRIPTION
				"Description."
			::= { sleOSPFProcSummaryEntry 1 }

		
		-- 1.3.6.1.4.1.6296.101.51.2.3.1.1.2
		sleOSPFProcSummaryIPMask OBJECT-TYPE
			SYNTAX Integer32 (0..32)
			MAX-ACCESS read-only
			STATUS current
			DESCRIPTION
				"Description."
			::= { sleOSPFProcSummaryEntry 2 }

		
		-- 1.3.6.1.4.1.6296.101.51.2.3.1.1.3
		sleOSPFProcSummaryTag OBJECT-TYPE
			SYNTAX Gauge32 (0..4294967295)
			MAX-ACCESS read-only
			STATUS current
			DESCRIPTION
				"Description."
			::= { sleOSPFProcSummaryEntry 3 }

		
		-- 1.3.6.1.4.1.6296.101.51.2.3.1.1.4
		sleOSPFProcSummaryAdvertiseFlag OBJECT-TYPE
			SYNTAX INTEGER
				{
				disable(0),
				enable(1)
				}
			MAX-ACCESS read-only
			STATUS current
			DESCRIPTION
				"Description."
			::= { sleOSPFProcSummaryEntry 4 }

		
		-- 1.3.6.1.4.1.6296.101.51.2.3.2
		sleOSPFProcSummaryControl OBJECT IDENTIFIER ::= { sleOSPFProcSummary 2 }

		
		-- 1.3.6.1.4.1.6296.101.51.2.3.2.1
		sleOSPFProcSummaryControlRequest OBJECT-TYPE
			SYNTAX INTEGER
				{
				createOSPFProcSummary(1),
				deleteOSPFProcSummary(2),
				setOSPFProcSummary(3)
				}
			MAX-ACCESS read-write
			STATUS current
			DESCRIPTION
				"Description."
			::= { sleOSPFProcSummaryControl 1 }

		
		-- 1.3.6.1.4.1.6296.101.51.2.3.2.2
		sleOSPFProcSummaryControlStatus OBJECT-TYPE
			SYNTAX SleControlStatusType
			MAX-ACCESS read-only
			STATUS current
			DESCRIPTION
				"Description."
			::= { sleOSPFProcSummaryControl 2 }

		
		-- 1.3.6.1.4.1.6296.101.51.2.3.2.3
		sleOSPFProcSummaryControlTimer OBJECT-TYPE
			SYNTAX Gauge32
			MAX-ACCESS read-write
			STATUS current
			DESCRIPTION
				"Description."
			::= { sleOSPFProcSummaryControl 3 }

		
		-- 1.3.6.1.4.1.6296.101.51.2.3.2.4
		sleOSPFProcSummaryControlTimeStamp OBJECT-TYPE
			SYNTAX TimeTicks
			MAX-ACCESS read-only
			STATUS current
			DESCRIPTION
				"Description."
			::= { sleOSPFProcSummaryControl 4 }

		
		-- 1.3.6.1.4.1.6296.101.51.2.3.2.5
		sleOSPFProcSummaryControlReqResult OBJECT-TYPE
			SYNTAX SleControlRequestResultType
			MAX-ACCESS read-only
			STATUS current
			DESCRIPTION
				"Description."
			::= { sleOSPFProcSummaryControl 5 }

		
		-- 1.3.6.1.4.1.6296.101.51.2.3.2.6
		sleOSPFProcSummaryControlProcID OBJECT-TYPE
			SYNTAX INTEGER (0..65535)
			MAX-ACCESS read-write
			STATUS current
			DESCRIPTION
				"Description."
			::= { sleOSPFProcSummaryControl 6 }

		
		-- 1.3.6.1.4.1.6296.101.51.2.3.2.7
		sleOSPFProcSummaryControlIPAddress OBJECT-TYPE
			SYNTAX IpAddress
			MAX-ACCESS read-write
			STATUS current
			DESCRIPTION
				"Description."
			::= { sleOSPFProcSummaryControl 7 }

		
		-- 1.3.6.1.4.1.6296.101.51.2.3.2.8
		sleOSPFProcSummaryControlIPMask OBJECT-TYPE
			SYNTAX INTEGER (0..32)
			MAX-ACCESS read-write
			STATUS current
			DESCRIPTION
				"Description."
			::= { sleOSPFProcSummaryControl 8 }

		
		-- 1.3.6.1.4.1.6296.101.51.2.3.2.9
		sleOSPFProcSummaryControlTag OBJECT-TYPE
			SYNTAX Gauge32 (0..4294967295)
			MAX-ACCESS read-write
			STATUS current
			DESCRIPTION
				"Description."
			::= { sleOSPFProcSummaryControl 9 }

		
		-- 1.3.6.1.4.1.6296.101.51.2.3.2.10
		sleOSPFProcSummaryControlAdvertiseFlag OBJECT-TYPE
			SYNTAX INTEGER
				{
				disable(0),
				enable(1)
				}
			MAX-ACCESS read-write
			STATUS current
			DESCRIPTION
				"Description."
			::= { sleOSPFProcSummaryControl 10 }

		
		-- 1.3.6.1.4.1.6296.101.51.2.3.3
		sleOSPFProcSummaryNotification OBJECT IDENTIFIER ::= { sleOSPFProcSummary 3 }

		
		-- 1.3.6.1.4.1.6296.101.51.2.3.3.1
		sleOSPFSummaryCreated NOTIFICATION-TYPE
			OBJECTS { sleOSPFProcSummaryControlRequest, sleOSPFProcSummaryControlTimeStamp, sleOSPFProcSummaryControlReqResult, sleOSPFProcID, sleOSPFProcSummaryIPAddress, 
				sleOSPFProcSummaryIPMask, sleOSPFProcSummaryTag, sleOSPFProcSummaryAdvertiseFlag }
			STATUS current
			DESCRIPTION 
				"Description."
			::= { sleOSPFProcSummaryNotification 1 }

		
		-- 1.3.6.1.4.1.6296.101.51.2.3.3.2
		sleOSPFSummaryDeleted NOTIFICATION-TYPE
			OBJECTS { sleOSPFProcSummaryControlRequest, sleOSPFProcSummaryControlTimeStamp, sleOSPFProcSummaryControlReqResult, sleOSPFProcID, sleOSPFProcSummaryControlIPAddress, 
				sleOSPFProcSummaryControlIPMask, sleOSPFProcSummaryControlTag, sleOSPFProcSummaryControlAdvertiseFlag }
			STATUS current
			DESCRIPTION 
				"Description."
			::= { sleOSPFProcSummaryNotification 2 }

		
		-- 1.3.6.1.4.1.6296.101.51.2.3.3.3
		sleOSPFSummaryChanged NOTIFICATION-TYPE
			OBJECTS { sleOSPFProcSummaryControlRequest, sleOSPFProcSummaryControlTimeStamp, sleOSPFProcSummaryControlReqResult, sleOSPFProcID, sleOSPFProcSummaryIPAddress, 
				sleOSPFProcSummaryIPMask, sleOSPFProcSummaryTag, sleOSPFProcSummaryAdvertiseFlag }
			STATUS current
			DESCRIPTION 
				"Description."
			::= { sleOSPFProcSummaryNotification 3 }

		
		-- 1.3.6.1.4.1.6296.101.51.2.4
		sleOSPFProcDistributeList OBJECT IDENTIFIER ::= { sleOSPFProc 4 }

		
		-- 1.3.6.1.4.1.6296.101.51.2.4.1
		sleOSPFProcDistributeListTable OBJECT-TYPE
			SYNTAX SEQUENCE OF SleOSPFProcDistributeListEntry
			MAX-ACCESS not-accessible
			STATUS current
			DESCRIPTION
				"Description."
			::= { sleOSPFProcDistributeList 1 }

		
		-- 1.3.6.1.4.1.6296.101.51.2.4.1.1
		sleOSPFProcDistributeListEntry OBJECT-TYPE
			SYNTAX SleOSPFProcDistributeListEntry
			MAX-ACCESS not-accessible
			STATUS current
			DESCRIPTION
				"Description."
			INDEX { sleOSPFProcID, sleOSPFProcDistributeListOutFilterType }
			::= { sleOSPFProcDistributeListTable 1 }

		
		SleOSPFProcDistributeListEntry ::=
			SEQUENCE { 
				sleOSPFProcDistributeListOutFilterType
					INTEGER,
				sleOSPFProcDistributeListAccessName
					OCTET STRING
			 }

		-- 1.3.6.1.4.1.6296.101.51.2.4.1.1.1
		sleOSPFProcDistributeListOutFilterType OBJECT-TYPE
			SYNTAX INTEGER
				{
				kernel(1),
				connected(2),
				static(3),
				rip(4),
				bgp(8)
				}
			MAX-ACCESS read-only
			STATUS current
			DESCRIPTION
				"Description."
			::= { sleOSPFProcDistributeListEntry 1 }

		
		-- 1.3.6.1.4.1.6296.101.51.2.4.1.1.2
		sleOSPFProcDistributeListAccessName OBJECT-TYPE
			SYNTAX OCTET STRING
			MAX-ACCESS read-only
			STATUS current
			DESCRIPTION
				"Description."
			::= { sleOSPFProcDistributeListEntry 2 }

		
		-- 1.3.6.1.4.1.6296.101.51.2.4.2
		sleOSPFProcDistributeListControl OBJECT IDENTIFIER ::= { sleOSPFProcDistributeList 2 }

		
		-- 1.3.6.1.4.1.6296.101.51.2.4.2.1
		sleOSPFProcDistributeListControlRequest OBJECT-TYPE
			SYNTAX INTEGER
				{
				createOSPFProcDistributeList(1),
				deleteOSPFProcDistributeList(2)
				}
			MAX-ACCESS read-write
			STATUS current
			DESCRIPTION
				"Description."
			::= { sleOSPFProcDistributeListControl 1 }

		
		-- 1.3.6.1.4.1.6296.101.51.2.4.2.2
		sleOSPFProcDistributeListControlStatus OBJECT-TYPE
			SYNTAX SleControlStatusType
			MAX-ACCESS read-only
			STATUS current
			DESCRIPTION
				"Description."
			::= { sleOSPFProcDistributeListControl 2 }

		
		-- 1.3.6.1.4.1.6296.101.51.2.4.2.3
		sleOSPFProcDistributeListControlTimer OBJECT-TYPE
			SYNTAX Gauge32
			MAX-ACCESS read-write
			STATUS current
			DESCRIPTION
				"Description."
			::= { sleOSPFProcDistributeListControl 3 }

		
		-- 1.3.6.1.4.1.6296.101.51.2.4.2.4
		sleOSPFProcDistributeListControlTimeStamp OBJECT-TYPE
			SYNTAX TimeTicks
			MAX-ACCESS read-only
			STATUS current
			DESCRIPTION
				"Description."
			::= { sleOSPFProcDistributeListControl 4 }

		
		-- 1.3.6.1.4.1.6296.101.51.2.4.2.5
		sleOSPFProcDistributeListControlReqResult OBJECT-TYPE
			SYNTAX SleControlRequestResultType
			MAX-ACCESS read-only
			STATUS current
			DESCRIPTION
				"Description."
			::= { sleOSPFProcDistributeListControl 5 }

		
		-- 1.3.6.1.4.1.6296.101.51.2.4.2.6
		sleOSPFProcDistributeListControlProcID OBJECT-TYPE
			SYNTAX INTEGER (0..65535)
			MAX-ACCESS read-write
			STATUS current
			DESCRIPTION
				"Description."
			::= { sleOSPFProcDistributeListControl 6 }

		
		-- 1.3.6.1.4.1.6296.101.51.2.4.2.7
		sleOSPFProcDistributeListControlOutFilterType OBJECT-TYPE
			SYNTAX INTEGER
				{
				kernel(1),
				connected(2),
				static(3),
				rip(4),
				bgp(8)
				}
			MAX-ACCESS read-write
			STATUS current
			DESCRIPTION
				"Description."
			::= { sleOSPFProcDistributeListControl 7 }

		
		-- 1.3.6.1.4.1.6296.101.51.2.4.2.8
		sleOSPFProcDistributeListControlAccessName OBJECT-TYPE
			SYNTAX OCTET STRING
			MAX-ACCESS read-write
			STATUS current
			DESCRIPTION
				"Description."
			::= { sleOSPFProcDistributeListControl 8 }

		
		-- 1.3.6.1.4.1.6296.101.51.2.4.3
		sleOSPFProcDistributeListNotification OBJECT IDENTIFIER ::= { sleOSPFProcDistributeList 3 }

		
		-- 1.3.6.1.4.1.6296.101.51.2.4.3.1
		sleOSPFDistributeListCreated NOTIFICATION-TYPE
			OBJECTS { sleOSPFProcDistributeListControlRequest, sleOSPFProcDistributeListControlTimeStamp, sleOSPFProcDistributeListControlReqResult, sleOSPFProcID, sleOSPFProcDistributeListOutFilterType, 
				sleOSPFProcDistributeListAccessName }
			STATUS current
			DESCRIPTION 
				"Description."
			::= { sleOSPFProcDistributeListNotification 1 }

		
		-- 1.3.6.1.4.1.6296.101.51.2.4.3.2
		sleOSPFDistributeListDeleted NOTIFICATION-TYPE
			OBJECTS { sleOSPFProcDistributeListControlRequest, sleOSPFProcDistributeListControlTimeStamp, sleOSPFProcDistributeListControlReqResult, sleOSPFProcID, sleOSPFProcDistributeListControlOutFilterType, 
				sleOSPFProcDistributeListControlAccessName }
			STATUS current
			DESCRIPTION 
				"Description."
			::= { sleOSPFProcDistributeListNotification 2 }

		
		-- 1.3.6.1.4.1.6296.101.51.2.5
		sleOSPFProcNeighbor OBJECT IDENTIFIER ::= { sleOSPFProc 5 }

		
		-- 1.3.6.1.4.1.6296.101.51.2.5.1
		sleOSPFProcNeighborTable OBJECT-TYPE
			SYNTAX SEQUENCE OF SleOSPFProcNeighborEntry
			MAX-ACCESS not-accessible
			STATUS current
			DESCRIPTION
				"Description."
			::= { sleOSPFProcNeighbor 1 }

		
		-- 1.3.6.1.4.1.6296.101.51.2.5.1.1
		sleOSPFProcNeighborEntry OBJECT-TYPE
			SYNTAX SleOSPFProcNeighborEntry
			MAX-ACCESS not-accessible
			STATUS current
			DESCRIPTION
				"Description."
			INDEX { sleOSPFProcID, sleOSPFProcNeighborIPAddr }
			::= { sleOSPFProcNeighborTable 1 }

		
		SleOSPFProcNeighborEntry ::=
			SEQUENCE { 
				sleOSPFProcNeighborIPAddr
					IpAddress,
				sleOSPFProcNeighborPriority
					INTEGER,
				sleOSPFProcNeighborPollInterval
					INTEGER,
				sleOSPFProcNeighborCost
					INTEGER
			 }

		-- 1.3.6.1.4.1.6296.101.51.2.5.1.1.1
		sleOSPFProcNeighborIPAddr OBJECT-TYPE
			SYNTAX IpAddress
			MAX-ACCESS read-only
			STATUS current
			DESCRIPTION
				"Description."
			::= { sleOSPFProcNeighborEntry 1 }

		
		-- 1.3.6.1.4.1.6296.101.51.2.5.1.1.2
		sleOSPFProcNeighborPriority OBJECT-TYPE
			SYNTAX INTEGER (1..255)
			MAX-ACCESS read-only
			STATUS current
			DESCRIPTION
				"Description."
			::= { sleOSPFProcNeighborEntry 2 }

		
		-- 1.3.6.1.4.1.6296.101.51.2.5.1.1.3
		sleOSPFProcNeighborPollInterval OBJECT-TYPE
			SYNTAX INTEGER (1..65535)
			MAX-ACCESS read-only
			STATUS current
			DESCRIPTION
				"Description."
			::= { sleOSPFProcNeighborEntry 3 }

		
		-- 1.3.6.1.4.1.6296.101.51.2.5.1.1.4
		sleOSPFProcNeighborCost OBJECT-TYPE
			SYNTAX INTEGER (1..65535)
			MAX-ACCESS read-only
			STATUS current
			DESCRIPTION
				"Description."
			::= { sleOSPFProcNeighborEntry 4 }

		
		-- 1.3.6.1.4.1.6296.101.51.2.5.2
		sleOSPFProcNeighborControl OBJECT IDENTIFIER ::= { sleOSPFProcNeighbor 2 }

		
		-- 1.3.6.1.4.1.6296.101.51.2.5.2.1
		sleOSPFProcNeighborControlRequest OBJECT-TYPE
			SYNTAX INTEGER
				{
				createOSPFProcNeighbor(1),
				deleteOSPFProcNeighbor(2),
				setOSPFProcNeighbor(3)
				}
			MAX-ACCESS read-write
			STATUS current
			DESCRIPTION
				"Description."
			::= { sleOSPFProcNeighborControl 1 }

		
		-- 1.3.6.1.4.1.6296.101.51.2.5.2.2
		sleOSPFProcNeighborControlStatus OBJECT-TYPE
			SYNTAX SleControlStatusType
			MAX-ACCESS read-only
			STATUS current
			DESCRIPTION
				"Description."
			::= { sleOSPFProcNeighborControl 2 }

		
		-- 1.3.6.1.4.1.6296.101.51.2.5.2.3
		sleOSPFProcNeighborControlTimer OBJECT-TYPE
			SYNTAX Gauge32
			MAX-ACCESS read-write
			STATUS current
			DESCRIPTION
				"Description."
			::= { sleOSPFProcNeighborControl 3 }

		
		-- 1.3.6.1.4.1.6296.101.51.2.5.2.4
		sleOSPFProcNeighborControlTimeStamp OBJECT-TYPE
			SYNTAX TimeTicks
			MAX-ACCESS read-only
			STATUS current
			DESCRIPTION
				"Description."
			::= { sleOSPFProcNeighborControl 4 }

		
		-- 1.3.6.1.4.1.6296.101.51.2.5.2.5
		sleOSPFProcNeighborControlReqResult OBJECT-TYPE
			SYNTAX SleControlRequestResultType
			MAX-ACCESS read-only
			STATUS current
			DESCRIPTION
				"Description."
			::= { sleOSPFProcNeighborControl 5 }

		
		-- 1.3.6.1.4.1.6296.101.51.2.5.2.6
		sleOSPFProcNeighborControlProcID OBJECT-TYPE
			SYNTAX INTEGER (0..65535)
			MAX-ACCESS read-write
			STATUS current
			DESCRIPTION
				"Description."
			::= { sleOSPFProcNeighborControl 6 }

		
		-- 1.3.6.1.4.1.6296.101.51.2.5.2.7
		sleOSPFProcNeighborControlIPAddr OBJECT-TYPE
			SYNTAX IpAddress
			MAX-ACCESS read-write
			STATUS current
			DESCRIPTION
				"Description."
			::= { sleOSPFProcNeighborControl 7 }

		
		-- 1.3.6.1.4.1.6296.101.51.2.5.2.8
		sleOSPFProcNeighborControlPriority OBJECT-TYPE
			SYNTAX INTEGER (1..255)
			MAX-ACCESS read-write
			STATUS current
			DESCRIPTION
				"Description."
			::= { sleOSPFProcNeighborControl 8 }

		
		-- 1.3.6.1.4.1.6296.101.51.2.5.2.9
		sleOSPFProcNeighborControlPollInterval OBJECT-TYPE
			SYNTAX INTEGER (1..65535)
			MAX-ACCESS read-write
			STATUS current
			DESCRIPTION
				"Description."
			::= { sleOSPFProcNeighborControl 9 }

		
		-- 1.3.6.1.4.1.6296.101.51.2.5.2.10
		sleOSPFProcNeighborControlCost OBJECT-TYPE
			SYNTAX INTEGER (1..65535)
			MAX-ACCESS read-write
			STATUS current
			DESCRIPTION
				"Description."
			::= { sleOSPFProcNeighborControl 10 }

		
		-- 1.3.6.1.4.1.6296.101.51.2.5.3
		sleOSPFProcNeighborNotification OBJECT IDENTIFIER ::= { sleOSPFProcNeighbor 3 }

		
		-- 1.3.6.1.4.1.6296.101.51.2.5.3.1
		sleOSPFProcNeighborCreated NOTIFICATION-TYPE
			OBJECTS { sleOSPFProcNeighborControlRequest, sleOSPFProcNeighborControlTimeStamp, sleOSPFProcNeighborControlReqResult, sleOSPFProcID, sleOSPFProcNeighborIPAddr, 
				sleOSPFProcNeighborCost, sleOSPFProcNeighborPollInterval, sleOSPFProcNeighborPriority }
			STATUS current
			DESCRIPTION 
				"Description."
			::= { sleOSPFProcNeighborNotification 1 }

		
		-- 1.3.6.1.4.1.6296.101.51.2.5.3.2
		sleOSPFProcNeighborDeleted NOTIFICATION-TYPE
			OBJECTS { sleOSPFProcNeighborControlRequest, sleOSPFProcNeighborControlTimeStamp, sleOSPFProcNeighborControlReqResult, sleOSPFProcID, sleOSPFProcNeighborControlIPAddr
				 }
			STATUS current
			DESCRIPTION 
				"Description."
			::= { sleOSPFProcNeighborNotification 2 }

		
		-- 1.3.6.1.4.1.6296.101.51.2.5.3.3
		sleOSPFProcNeighborChanged NOTIFICATION-TYPE
			OBJECTS { sleOSPFProcNeighborControlRequest, sleOSPFProcNeighborControlTimeStamp, sleOSPFProcNeighborControlReqResult, sleOSPFProcNeighborIPAddr, sleOSPFProcID, 
				sleOSPFProcNeighborCost, sleOSPFProcNeighborPollInterval, sleOSPFProcNeighborPriority }
			STATUS current
			DESCRIPTION 
				"Description."
			::= { sleOSPFProcNeighborNotification 3 }

		
		-- 1.3.6.1.4.1.6296.101.51.2.6
		sleOSPFProcPassIf OBJECT IDENTIFIER ::= { sleOSPFProc 6 }

		
		-- 1.3.6.1.4.1.6296.101.51.2.6.1
		sleOSPFProcPassIfTable OBJECT-TYPE
			SYNTAX SEQUENCE OF SleOSPFProcPassIfEntry
			MAX-ACCESS not-accessible
			STATUS current
			DESCRIPTION
				"Description."
			::= { sleOSPFProcPassIf 1 }

		
		-- 1.3.6.1.4.1.6296.101.51.2.6.1.1
		sleOSPFProcPassIfEntry OBJECT-TYPE
			SYNTAX SleOSPFProcPassIfEntry
			MAX-ACCESS not-accessible
			STATUS current
			DESCRIPTION
				"Description."
			INDEX { sleOSPFProcID, sleOSPFProcPassIfAddr, sleOSPFProcPassIfName }
			::= { sleOSPFProcPassIfTable 1 }

		
		SleOSPFProcPassIfEntry ::=
			SEQUENCE { 
				sleOSPFProcPassIfAddr
					IpAddress,
				sleOSPFProcPassIfName
					OCTET STRING
			 }

		-- 1.3.6.1.4.1.6296.101.51.2.6.1.1.1
		sleOSPFProcPassIfAddr OBJECT-TYPE
			SYNTAX IpAddress
			MAX-ACCESS read-only
			STATUS current
			DESCRIPTION
				"Description."
			::= { sleOSPFProcPassIfEntry 1 }

		
		-- 1.3.6.1.4.1.6296.101.51.2.6.1.1.2
		sleOSPFProcPassIfName OBJECT-TYPE
			SYNTAX OCTET STRING
			MAX-ACCESS read-only
			STATUS current
			DESCRIPTION
				"Description."
			::= { sleOSPFProcPassIfEntry 2 }

		
		-- 1.3.6.1.4.1.6296.101.51.2.6.2
		sleOSPFProcPassIfControl OBJECT IDENTIFIER ::= { sleOSPFProcPassIf 2 }

		
		-- 1.3.6.1.4.1.6296.101.51.2.6.2.1
		sleOSPFProcPassIfControlRequest OBJECT-TYPE
			SYNTAX INTEGER
				{
				createOSPFProcPassInterface(1),
				deleteOSPFProcPassInterface(2)
				}
			MAX-ACCESS read-write
			STATUS current
			DESCRIPTION
				"Description."
			::= { sleOSPFProcPassIfControl 1 }

		
		-- 1.3.6.1.4.1.6296.101.51.2.6.2.2
		sleOSPFProcPassIfControlStatus OBJECT-TYPE
			SYNTAX SleControlStatusType
			MAX-ACCESS read-only
			STATUS current
			DESCRIPTION
				"Description."
			::= { sleOSPFProcPassIfControl 2 }

		
		-- 1.3.6.1.4.1.6296.101.51.2.6.2.3
		sleOSPFProcPassIfControlTimer OBJECT-TYPE
			SYNTAX Gauge32
			MAX-ACCESS read-write
			STATUS current
			DESCRIPTION
				"Description."
			::= { sleOSPFProcPassIfControl 3 }

		
		-- 1.3.6.1.4.1.6296.101.51.2.6.2.4
		sleOSPFProcPassIfControlTimeStamp OBJECT-TYPE
			SYNTAX TimeTicks
			MAX-ACCESS read-only
			STATUS current
			DESCRIPTION
				"Description."
			::= { sleOSPFProcPassIfControl 4 }

		
		-- 1.3.6.1.4.1.6296.101.51.2.6.2.5
		sleOSPFProcPassIfControlReqResult OBJECT-TYPE
			SYNTAX SleControlRequestResultType
			MAX-ACCESS read-only
			STATUS current
			DESCRIPTION
				"Description."
			::= { sleOSPFProcPassIfControl 5 }

		
		-- 1.3.6.1.4.1.6296.101.51.2.6.2.6
		sleOSPFProcPassIfControlProcID OBJECT-TYPE
			SYNTAX INTEGER (0..65535)
			MAX-ACCESS read-write
			STATUS current
			DESCRIPTION
				"Description."
			::= { sleOSPFProcPassIfControl 6 }

		
		-- 1.3.6.1.4.1.6296.101.51.2.6.2.7
		sleOSPFProcPassIfControlIPAddr OBJECT-TYPE
			SYNTAX IpAddress
			MAX-ACCESS read-write
			STATUS current
			DESCRIPTION
				"Description."
			::= { sleOSPFProcPassIfControl 7 }

		
		-- 1.3.6.1.4.1.6296.101.51.2.6.2.8
		sleOSPFProcPassIfControlName OBJECT-TYPE
			SYNTAX OCTET STRING
			MAX-ACCESS read-write
			STATUS current
			DESCRIPTION
				"Description."
			::= { sleOSPFProcPassIfControl 8 }

		
		-- 1.3.6.1.4.1.6296.101.51.2.6.3
		sleOSPFProcPassIfNotification OBJECT IDENTIFIER ::= { sleOSPFProcPassIf 3 }

		
		-- 1.3.6.1.4.1.6296.101.51.2.6.3.1
		sleOSPFPassInterfaceCreated NOTIFICATION-TYPE
			OBJECTS { sleOSPFProcPassIfControlRequest, sleOSPFProcPassIfControlTimeStamp, sleOSPFProcPassIfControlReqResult, sleOSPFProcPassIfName, sleOSPFProcPassIfAddr
				 }
			STATUS current
			DESCRIPTION 
				"Description."
			::= { sleOSPFProcPassIfNotification 1 }

		
		-- 1.3.6.1.4.1.6296.101.51.2.6.3.2
		sleOSPFPassInterfaceDeleted NOTIFICATION-TYPE
			OBJECTS { sleOSPFProcPassIfControlRequest, sleOSPFProcPassIfControlTimeStamp, sleOSPFProcPassIfControlReqResult, sleOSPFProcID, sleOSPFProcPassIfControlName, 
				sleOSPFProcPassIfControlIPAddr }
			STATUS current
			DESCRIPTION 
				"Description."
			::= { sleOSPFProcPassIfNotification 2 }

		
		-- 1.3.6.1.4.1.6296.101.51.2.7
		sleOSPFProcHost OBJECT IDENTIFIER ::= { sleOSPFProc 7 }

		
		-- 1.3.6.1.4.1.6296.101.51.2.7.1
		sleOSPFProcHostTable OBJECT-TYPE
			SYNTAX SEQUENCE OF SleOSPFProcHostEntry
			MAX-ACCESS not-accessible
			STATUS current
			DESCRIPTION
				"Description."
			::= { sleOSPFProcHost 1 }

		
		-- 1.3.6.1.4.1.6296.101.51.2.7.1.1
		sleOSPFProcHostEntry OBJECT-TYPE
			SYNTAX SleOSPFProcHostEntry
			MAX-ACCESS not-accessible
			STATUS current
			DESCRIPTION
				"Description."
			INDEX { sleOSPFProcID, sleOSPFProcHostIPAddr }
			::= { sleOSPFProcHostTable 1 }

		
		SleOSPFProcHostEntry ::=
			SEQUENCE { 
				sleOSPFProcHostIPAddr
					IpAddress,
				sleOSPFProcHostAreaID
					Gauge32,
				sleOSPFProcHostAreaCost
					INTEGER
			 }

		-- 1.3.6.1.4.1.6296.101.51.2.7.1.1.1
		sleOSPFProcHostIPAddr OBJECT-TYPE
			SYNTAX IpAddress
			MAX-ACCESS read-only
			STATUS current
			DESCRIPTION
				"Description."
			::= { sleOSPFProcHostEntry 1 }

		
		-- 1.3.6.1.4.1.6296.101.51.2.7.1.1.2
		sleOSPFProcHostAreaID OBJECT-TYPE
			SYNTAX Gauge32 (1..4294967295)
			MAX-ACCESS read-only
			STATUS current
			DESCRIPTION
				"Description."
			::= { sleOSPFProcHostEntry 2 }

		
		-- 1.3.6.1.4.1.6296.101.51.2.7.1.1.3
		sleOSPFProcHostAreaCost OBJECT-TYPE
			SYNTAX INTEGER (1..65535)
			MAX-ACCESS read-only
			STATUS current
			DESCRIPTION
				"Description."
			::= { sleOSPFProcHostEntry 3 }

		
		-- 1.3.6.1.4.1.6296.101.51.2.7.2
		sleOSPFProcHostControl OBJECT IDENTIFIER ::= { sleOSPFProcHost 2 }

		
		-- 1.3.6.1.4.1.6296.101.51.2.7.2.1
		sleOSPFProcHostControlRequest OBJECT-TYPE
			SYNTAX INTEGER
				{
				createOSPFProcHost(1),
				deleteOSPFProcHost(2),
				setOSPFProcHostCost(3)
				}
			MAX-ACCESS read-write
			STATUS current
			DESCRIPTION
				"Description."
			::= { sleOSPFProcHostControl 1 }

		
		-- 1.3.6.1.4.1.6296.101.51.2.7.2.2
		sleOSPFProcHostControlStatus OBJECT-TYPE
			SYNTAX SleControlStatusType
			MAX-ACCESS read-only
			STATUS current
			DESCRIPTION
				"Description."
			::= { sleOSPFProcHostControl 2 }

		
		-- 1.3.6.1.4.1.6296.101.51.2.7.2.3
		sleOSPFProcHostControlTimer OBJECT-TYPE
			SYNTAX Gauge32
			MAX-ACCESS read-write
			STATUS current
			DESCRIPTION
				"Description."
			::= { sleOSPFProcHostControl 3 }

		
		-- 1.3.6.1.4.1.6296.101.51.2.7.2.4
		sleOSPFProcHostControlTimeStamp OBJECT-TYPE
			SYNTAX TimeTicks
			MAX-ACCESS read-only
			STATUS current
			DESCRIPTION
				"Description."
			::= { sleOSPFProcHostControl 4 }

		
		-- 1.3.6.1.4.1.6296.101.51.2.7.2.5
		sleOSPFProcHostControlReqResult OBJECT-TYPE
			SYNTAX SleControlRequestResultType
			MAX-ACCESS read-only
			STATUS current
			DESCRIPTION
				"Description."
			::= { sleOSPFProcHostControl 5 }

		
		-- 1.3.6.1.4.1.6296.101.51.2.7.2.6
		sleOSPFProcHostControlProcID OBJECT-TYPE
			SYNTAX INTEGER (0..65535)
			MAX-ACCESS read-write
			STATUS current
			DESCRIPTION
				"Description."
			::= { sleOSPFProcHostControl 6 }

		
		-- 1.3.6.1.4.1.6296.101.51.2.7.2.7
		sleOSPFProcHostControlIPAddr OBJECT-TYPE
			SYNTAX IpAddress
			MAX-ACCESS read-write
			STATUS current
			DESCRIPTION
				"Description."
			::= { sleOSPFProcHostControl 7 }

		
		-- 1.3.6.1.4.1.6296.101.51.2.7.2.8
		sleOSPFProcHostControlAreaID OBJECT-TYPE
			SYNTAX Gauge32 (1..4294967295)
			MAX-ACCESS read-write
			STATUS current
			DESCRIPTION
				"Description."
			::= { sleOSPFProcHostControl 8 }

		
		-- 1.3.6.1.4.1.6296.101.51.2.7.2.9
		sleOSPFProcHostControlAreaCost OBJECT-TYPE
			SYNTAX INTEGER (1..65535)
			MAX-ACCESS read-write
			STATUS current
			DESCRIPTION
				"Description."
			::= { sleOSPFProcHostControl 9 }

		
		-- 1.3.6.1.4.1.6296.101.51.2.7.3
		sleOSPFProcHostNotification OBJECT IDENTIFIER ::= { sleOSPFProcHost 3 }

		
		-- 1.3.6.1.4.1.6296.101.51.2.7.3.1
		sleOSPFProcHostCreated NOTIFICATION-TYPE
			OBJECTS { sleOSPFProcHostControlRequest, sleOSPFProcHostControlTimeStamp, sleOSPFProcHostControlReqResult, sleOSPFProcHostIPAddr, sleOSPFProcHostAreaID, 
				sleOSPFProcHostAreaCost }
			STATUS current
			DESCRIPTION 
				"Description."
			::= { sleOSPFProcHostNotification 1 }

		
		-- 1.3.6.1.4.1.6296.101.51.2.7.3.2
		sleOSPFProcHostDeleted NOTIFICATION-TYPE
			OBJECTS { sleOSPFProcHostControlRequest, sleOSPFProcHostControlTimeStamp, sleOSPFProcHostControlReqResult, sleOSPFProcID, sleOSPFProcHostControlIPAddr, 
				sleOSPFProcHostControlAreaID }
			STATUS current
			DESCRIPTION 
				"Description."
			::= { sleOSPFProcHostNotification 2 }

		
		-- 1.3.6.1.4.1.6296.101.51.2.7.3.3
		sleOSPFProcHostCostChanged NOTIFICATION-TYPE
			OBJECTS { sleOSPFProcHostControlRequest, sleOSPFProcHostControlTimeStamp, sleOSPFProcHostControlReqResult, sleOSPFProcHostIPAddr, sleOSPFProcHostAreaID, 
				sleOSPFProcHostAreaCost }
			STATUS current
			DESCRIPTION 
				"Description."
			::= { sleOSPFProcHostNotification 3 }

		
		-- 1.3.6.1.4.1.6296.101.51.2.8
		sleOSPFProcRedistribute OBJECT IDENTIFIER ::= { sleOSPFProc 8 }

		
		-- 1.3.6.1.4.1.6296.101.51.2.8.1
		sleOSPFProcRedistTable OBJECT-TYPE
			SYNTAX SEQUENCE OF SleOSPFProcRedistEntry
			MAX-ACCESS not-accessible
			STATUS current
			DESCRIPTION
				"Description."
			::= { sleOSPFProcRedistribute 1 }

		
		-- 1.3.6.1.4.1.6296.101.51.2.8.1.1
		sleOSPFProcRedistEntry OBJECT-TYPE
			SYNTAX SleOSPFProcRedistEntry
			MAX-ACCESS not-accessible
			STATUS current
			DESCRIPTION
				"Description."
			INDEX { sleOSPFProcID, sleOSPFProcRedistType }
			::= { sleOSPFProcRedistTable 1 }

		
		SleOSPFProcRedistEntry ::=
			SEQUENCE { 
				sleOSPFProcRedistType
					INTEGER,
				sleOSPFProcRedistMetricType
					INTEGER,
				sleOSPFProcRedistMetric
					INTEGER,
				sleOSPFProcRedistRouteMapName
					OCTET STRING,
				sleOSPFProcRedistTag
					Gauge32,
				sleOSPFProcRedistSubnets
					INTEGER
			 }

		-- 1.3.6.1.4.1.6296.101.51.2.8.1.1.1
		sleOSPFProcRedistType OBJECT-TYPE
			SYNTAX INTEGER
				{
				kernel(1),
				connected(2),
				static(3),
				rip(4),
				bgp(5)
				}
			MAX-ACCESS read-only
			STATUS current
			DESCRIPTION
				"Description."
			::= { sleOSPFProcRedistEntry 1 }

		
		-- 1.3.6.1.4.1.6296.101.51.2.8.1.1.2
		sleOSPFProcRedistMetricType OBJECT-TYPE
			SYNTAX INTEGER
				{
				external1(1),
				external2(2)
				}
			MAX-ACCESS read-only
			STATUS current
			DESCRIPTION
				"Description."
			::= { sleOSPFProcRedistEntry 2 }

		
		-- 1.3.6.1.4.1.6296.101.51.2.8.1.1.3
		sleOSPFProcRedistMetric OBJECT-TYPE
			SYNTAX INTEGER (1..16777214)
			MAX-ACCESS read-only
			STATUS current
			DESCRIPTION
				"Description."
			::= { sleOSPFProcRedistEntry 3 }

		
		-- 1.3.6.1.4.1.6296.101.51.2.8.1.1.4
		sleOSPFProcRedistRouteMapName OBJECT-TYPE
			SYNTAX OCTET STRING
			MAX-ACCESS read-only
			STATUS current
			DESCRIPTION
				"Description."
			::= { sleOSPFProcRedistEntry 4 }

		
		-- 1.3.6.1.4.1.6296.101.51.2.8.1.1.5
		sleOSPFProcRedistTag OBJECT-TYPE
			SYNTAX Gauge32 (1..4294967295)
			MAX-ACCESS read-only
			STATUS current
			DESCRIPTION
				"Description."
			::= { sleOSPFProcRedistEntry 5 }

		
		-- 1.3.6.1.4.1.6296.101.51.2.8.1.1.6
		sleOSPFProcRedistSubnets OBJECT-TYPE
			SYNTAX INTEGER
				{
				disable(0),
				enable(1)
				}
			MAX-ACCESS read-only
			STATUS current
			DESCRIPTION
				"Description."
			::= { sleOSPFProcRedistEntry 6 }

		
		-- 1.3.6.1.4.1.6296.101.51.2.8.2
		sleOSPFProcRedistControl OBJECT IDENTIFIER ::= { sleOSPFProcRedistribute 2 }

		
		-- 1.3.6.1.4.1.6296.101.51.2.8.2.1
		sleOSPFProcRedistControlRequest OBJECT-TYPE
			SYNTAX INTEGER
				{
				createOSPFProcRedist(1),
				deleteOSPFProcRedist(2),
				setOSPFProcRedist(3)
				}
			MAX-ACCESS read-write
			STATUS current
			DESCRIPTION
				"Description."
			::= { sleOSPFProcRedistControl 1 }

		
		-- 1.3.6.1.4.1.6296.101.51.2.8.2.2
		sleOSPFProcRedistControlStatus OBJECT-TYPE
			SYNTAX SleControlStatusType
			MAX-ACCESS read-only
			STATUS current
			DESCRIPTION
				"Description."
			::= { sleOSPFProcRedistControl 2 }

		
		-- 1.3.6.1.4.1.6296.101.51.2.8.2.3
		sleOSPFProcRedistControlTimer OBJECT-TYPE
			SYNTAX Gauge32
			MAX-ACCESS read-write
			STATUS current
			DESCRIPTION
				"Description."
			::= { sleOSPFProcRedistControl 3 }

		
		-- 1.3.6.1.4.1.6296.101.51.2.8.2.4
		sleOSPFProcRedistControlTimeStamp OBJECT-TYPE
			SYNTAX TimeTicks
			MAX-ACCESS read-only
			STATUS current
			DESCRIPTION
				"Description."
			::= { sleOSPFProcRedistControl 4 }

		
		-- 1.3.6.1.4.1.6296.101.51.2.8.2.5
		sleOSPFProcRedistControlReqResult OBJECT-TYPE
			SYNTAX SleControlRequestResultType
			MAX-ACCESS read-only
			STATUS current
			DESCRIPTION
				"Description."
			::= { sleOSPFProcRedistControl 5 }

		
		-- 1.3.6.1.4.1.6296.101.51.2.8.2.6
		sleOSPFProcRedistControlProcID OBJECT-TYPE
			SYNTAX INTEGER (0..65535)
			MAX-ACCESS read-write
			STATUS current
			DESCRIPTION
				"Description."
			::= { sleOSPFProcRedistControl 6 }

		
		-- 1.3.6.1.4.1.6296.101.51.2.8.2.7
		sleOSPFProcRedistControlType OBJECT-TYPE
			SYNTAX INTEGER
				{
				kernel(1),
				connected(2),
				static(3),
				rip(4),
				bgp(5)
				}
			MAX-ACCESS read-write
			STATUS current
			DESCRIPTION
				"Description."
			::= { sleOSPFProcRedistControl 7 }

		
		-- 1.3.6.1.4.1.6296.101.51.2.8.2.8
		sleOSPFProcRedistControlMetricType OBJECT-TYPE
			SYNTAX INTEGER
				{
				external1(1),
				external2(2)
				}
			MAX-ACCESS read-write
			STATUS current
			DESCRIPTION
				"Description."
			::= { sleOSPFProcRedistControl 8 }

		
		-- 1.3.6.1.4.1.6296.101.51.2.8.2.9
		sleOSPFProcRedistControlMetric OBJECT-TYPE
			SYNTAX INTEGER (1..16777214)
			MAX-ACCESS read-write
			STATUS current
			DESCRIPTION
				"Description."
			::= { sleOSPFProcRedistControl 9 }

		
		-- 1.3.6.1.4.1.6296.101.51.2.8.2.10
		sleOSPFProcRedistControlRouteMapName OBJECT-TYPE
			SYNTAX OCTET STRING
			MAX-ACCESS read-write
			STATUS current
			DESCRIPTION
				"Description."
			::= { sleOSPFProcRedistControl 10 }

		
		-- 1.3.6.1.4.1.6296.101.51.2.8.2.11
		sleOSPFProcRedistControlTag OBJECT-TYPE
			SYNTAX Gauge32 (1..4294967295)
			MAX-ACCESS read-write
			STATUS current
			DESCRIPTION
				"Description."
			::= { sleOSPFProcRedistControl 11 }

		
		-- 1.3.6.1.4.1.6296.101.51.2.8.2.12
		sleOSPFProcRedistControlSubnets OBJECT-TYPE
			SYNTAX INTEGER
				{
				disable(0),
				enable(1)
				}
			MAX-ACCESS read-write
			STATUS current
			DESCRIPTION
				"Description."
			::= { sleOSPFProcRedistControl 12 }

		
		-- 1.3.6.1.4.1.6296.101.51.2.8.3
		sleOSPFProcRedistNotification OBJECT IDENTIFIER ::= { sleOSPFProcRedistribute 3 }

		
		-- 1.3.6.1.4.1.6296.101.51.2.8.3.1
		sleOSPFProcRedistCreated NOTIFICATION-TYPE
			OBJECTS { sleOSPFProcRedistControlRequest, sleOSPFProcRedistControlTimeStamp, sleOSPFProcRedistSubnets, sleOSPFProcRedistControlReqResult, sleOSPFProcRedistType, 
				sleOSPFProcRedistMetricType, sleOSPFProcRedistMetric, sleOSPFProcRedistRouteMapName, sleOSPFProcRedistTag }
			STATUS current
			DESCRIPTION 
				"Description."
			::= { sleOSPFProcRedistNotification 1 }

		
		-- 1.3.6.1.4.1.6296.101.51.2.8.3.2
		sleOSPFProcRedistDeleted NOTIFICATION-TYPE
			OBJECTS { sleOSPFProcRedistControlRequest, sleOSPFProcRedistControlReqResult, sleOSPFProcRedistControlTimeStamp, sleOSPFProcID, sleOSPFProcRedistControlType, 
				sleOSPFProcRedistControlMetricType, sleOSPFProcRedistControlMetric, sleOSPFProcRedistControlRouteMapName, sleOSPFProcRedistControlTag, sleOSPFProcRedistControlSubnets
				 }
			STATUS current
			DESCRIPTION 
				"Description."
			::= { sleOSPFProcRedistNotification 2 }

		
		-- 1.3.6.1.4.1.6296.101.51.2.8.3.3
		sleOSPFProcRedistChanged NOTIFICATION-TYPE
			OBJECTS { sleOSPFProcRedistControlRequest, sleOSPFProcRedistControlTimeStamp, sleOSPFProcRedistControlReqResult, sleOSPFProcRedistType, sleOSPFProcRedistMetricType, 
				sleOSPFProcRedistMetric, sleOSPFProcRedistRouteMapName, sleOSPFProcRedistTag, sleOSPFProcRedistControlSubnets }
			STATUS current
			DESCRIPTION 
				"Description."
			::= { sleOSPFProcRedistNotification 3 }

		
		-- 1.3.6.1.4.1.6296.101.51.2.9
		sleOSPFProcArea OBJECT IDENTIFIER ::= { sleOSPFProc 9 }

		
		-- 1.3.6.1.4.1.6296.101.51.2.9.1
		sleOSPFProcAreaInfo OBJECT IDENTIFIER ::= { sleOSPFProcArea 1 }

		
		-- 1.3.6.1.4.1.6296.101.51.2.9.1.1
		sleOSPFProcAreaInfoTable OBJECT-TYPE
			SYNTAX SEQUENCE OF SleOSPFProcAreaInfoEntry
			MAX-ACCESS not-accessible
			STATUS current
			DESCRIPTION
				"Description."
			::= { sleOSPFProcAreaInfo 1 }

		
		-- 1.3.6.1.4.1.6296.101.51.2.9.1.1.1
		sleOSPFProcAreaInfoEntry OBJECT-TYPE
			SYNTAX SleOSPFProcAreaInfoEntry
			MAX-ACCESS not-accessible
			STATUS current
			DESCRIPTION
				"Description."
			INDEX { sleOSPFProcID, sleOSPFProcAreaID }
			::= { sleOSPFProcAreaInfoTable 1 }

		
		SleOSPFProcAreaInfoEntry ::=
			SEQUENCE { 
				sleOSPFProcAreaID
					IpAddress,
				sleOSPFProcAreaType
					INTEGER,
				sleOSPFProcAreaDefaultCost
					INTEGER,
				sleOSPFProcAreaAuthenType
					INTEGER,
				sleOSPFProcAreaFAInName
					OCTET STRING,
				sleOSPFProcAreaFAOutName
					OBJECT IDENTIFIER,
				sleOSPFProcAreaFPInName
					OCTET STRING,
				sleOSPFProcAreaFPOutName
					OCTET STRING,
				sleOSPFProcAreaShortcutType
					INTEGER,
				sleOSPFProcAreaSpfRuns
					INTEGER,
				sleOSPFProcAreaLsaCount
					INTEGER,
				sleOSPFProcAreaLsaCheckSum
					INTEGER,
				sleOSPFProcAreaSummary
					INTEGER,
				sleOSPFProcAreaNssaTransRole
					INTEGER,
				sleOSPFProcAreaNssaNoRedist
					INTEGER,
				sleOSPFProcAreaNssaDefOriginate
					INTEGER,
				sleOSPFProcAreaNssaDefMetricType
					INTEGER,
				sleOSPFProcAreaNssaDefMetric
					INTEGER
			 }

		-- 1.3.6.1.4.1.6296.101.51.2.9.1.1.1.1
		sleOSPFProcAreaID OBJECT-TYPE
			SYNTAX IpAddress
			MAX-ACCESS read-only
			STATUS current
			DESCRIPTION
				"Description."
			::= { sleOSPFProcAreaInfoEntry 1 }

		
		-- 1.3.6.1.4.1.6296.101.51.2.9.1.1.1.2
		sleOSPFProcAreaType OBJECT-TYPE
			SYNTAX INTEGER
				{
				general(0),
				stub(1),
				nssa(2)
				}
			MAX-ACCESS read-only
			STATUS current
			DESCRIPTION
				"Description."
			::= { sleOSPFProcAreaInfoEntry 2 }

		
		-- 1.3.6.1.4.1.6296.101.51.2.9.1.1.1.3
		sleOSPFProcAreaDefaultCost OBJECT-TYPE
			SYNTAX INTEGER (0..16777215)
			MAX-ACCESS read-only
			STATUS current
			DESCRIPTION
				"Description."
			::= { sleOSPFProcAreaInfoEntry 3 }

		
		-- 1.3.6.1.4.1.6296.101.51.2.9.1.1.1.4
		sleOSPFProcAreaAuthenType OBJECT-TYPE
			SYNTAX INTEGER
				{
				null(0),
				simple(1),
				crypt(2)
				}
			MAX-ACCESS read-only
			STATUS current
			DESCRIPTION
				"Description."
			::= { sleOSPFProcAreaInfoEntry 4 }

		
		-- 1.3.6.1.4.1.6296.101.51.2.9.1.1.1.5
		sleOSPFProcAreaFAInName OBJECT-TYPE
			SYNTAX OCTET STRING
			MAX-ACCESS read-only
			STATUS current
			DESCRIPTION
				"Description."
			::= { sleOSPFProcAreaInfoEntry 5 }

		
		-- 1.3.6.1.4.1.6296.101.51.2.9.1.1.1.6
		sleOSPFProcAreaFAOutName OBJECT-TYPE
			SYNTAX OBJECT IDENTIFIER
			MAX-ACCESS read-only
			STATUS current
			DESCRIPTION
				"Description."
			::= { sleOSPFProcAreaInfoEntry 6 }

		
		-- 1.3.6.1.4.1.6296.101.51.2.9.1.1.1.7
		sleOSPFProcAreaFPInName OBJECT-TYPE
			SYNTAX OCTET STRING
			MAX-ACCESS read-only
			STATUS current
			DESCRIPTION
				"Description."
			::= { sleOSPFProcAreaInfoEntry 7 }

		
		-- 1.3.6.1.4.1.6296.101.51.2.9.1.1.1.8
		sleOSPFProcAreaFPOutName OBJECT-TYPE
			SYNTAX OCTET STRING
			MAX-ACCESS read-only
			STATUS current
			DESCRIPTION
				"Description."
			::= { sleOSPFProcAreaInfoEntry 8 }

		
		-- 1.3.6.1.4.1.6296.101.51.2.9.1.1.1.9
		sleOSPFProcAreaShortcutType OBJECT-TYPE
			SYNTAX INTEGER
				{
				default(0),
				enable(1),
				disable(2)
				}
			MAX-ACCESS read-only
			STATUS current
			DESCRIPTION
				"Description."
			::= { sleOSPFProcAreaInfoEntry 9 }

		
		-- 1.3.6.1.4.1.6296.101.51.2.9.1.1.1.10
		sleOSPFProcAreaSpfRuns OBJECT-TYPE
			SYNTAX INTEGER
			MAX-ACCESS read-only
			STATUS current
			DESCRIPTION
				"Description."
			::= { sleOSPFProcAreaInfoEntry 10 }

		
		-- 1.3.6.1.4.1.6296.101.51.2.9.1.1.1.11
		sleOSPFProcAreaLsaCount OBJECT-TYPE
			SYNTAX INTEGER
			MAX-ACCESS read-only
			STATUS current
			DESCRIPTION
				"Description."
			::= { sleOSPFProcAreaInfoEntry 11 }

		
		-- 1.3.6.1.4.1.6296.101.51.2.9.1.1.1.12
		sleOSPFProcAreaLsaCheckSum OBJECT-TYPE
			SYNTAX INTEGER
			MAX-ACCESS read-only
			STATUS current
			DESCRIPTION
				"Description."
			::= { sleOSPFProcAreaInfoEntry 12 }

		
		-- 1.3.6.1.4.1.6296.101.51.2.9.1.1.1.13
		sleOSPFProcAreaSummary OBJECT-TYPE
			SYNTAX INTEGER
				{
				none(0),
				noAreaSummary(1),
				sendAreaSummary(2)
				}
			MAX-ACCESS read-only
			STATUS current
			DESCRIPTION
				"Description."
			::= { sleOSPFProcAreaInfoEntry 13 }

		
		-- 1.3.6.1.4.1.6296.101.51.2.9.1.1.1.14
		sleOSPFProcAreaNssaTransRole OBJECT-TYPE
			SYNTAX INTEGER
				{
				never(0),
				always(1),
				candidate(2),
				none(3)
				}
			MAX-ACCESS read-only
			STATUS current
			DESCRIPTION
				"Description."
			::= { sleOSPFProcAreaInfoEntry 14 }

		
		-- 1.3.6.1.4.1.6296.101.51.2.9.1.1.1.15
		sleOSPFProcAreaNssaNoRedist OBJECT-TYPE
			SYNTAX INTEGER
				{
				none(0),
				enable(1),
				disable(2)
				}
			MAX-ACCESS read-only
			STATUS current
			DESCRIPTION
				"Description."
			::= { sleOSPFProcAreaInfoEntry 15 }

		
		-- 1.3.6.1.4.1.6296.101.51.2.9.1.1.1.16
		sleOSPFProcAreaNssaDefOriginate OBJECT-TYPE
			SYNTAX INTEGER
				{
				disable(0),
				enable(1)
				}
			MAX-ACCESS read-only
			STATUS current
			DESCRIPTION
				"Description."
			::= { sleOSPFProcAreaInfoEntry 16 }

		
		-- 1.3.6.1.4.1.6296.101.51.2.9.1.1.1.17
		sleOSPFProcAreaNssaDefMetricType OBJECT-TYPE
			SYNTAX INTEGER
				{
				none(0),
				external1(1),
				external2(2)
				}
			MAX-ACCESS read-only
			STATUS current
			DESCRIPTION
				"Description."
			::= { sleOSPFProcAreaInfoEntry 17 }

		
		-- 1.3.6.1.4.1.6296.101.51.2.9.1.1.1.18
		sleOSPFProcAreaNssaDefMetric OBJECT-TYPE
			SYNTAX INTEGER (0..16777214)
			MAX-ACCESS read-only
			STATUS current
			DESCRIPTION
				"Description."
			::= { sleOSPFProcAreaInfoEntry 18 }

		
		-- 1.3.6.1.4.1.6296.101.51.2.9.1.2
		sleOSPFProcAreaInfoControl OBJECT IDENTIFIER ::= { sleOSPFProcAreaInfo 2 }

		
		-- 1.3.6.1.4.1.6296.101.51.2.9.1.2.1
		sleOSPFProcAreaControlRequest OBJECT-TYPE
			SYNTAX INTEGER
				{
				createOSPFGeneralArea(1),
				createOSPFStubNssaArea(2),
				deleteOSPFArea(3),
				setOSPFAreaDefaultCostChange(4),
				setOSPFAreaAuthenTypeChange(5),
				setOSPFAreaFAInNameChange(6),
				setOSPFAreaFAOutNameChang(7),
				setOSPFAreaFPInNameChange(8),
				setOSPFAreaFPOutNameChange(9),
				setOSPFAreaShortcutTypeChange(10),
				setOSPFAreaSummary(11),
				setOSPFNssaAreaTranslateRole(12),
				setOSPFNssaAreaNoRedist(13),
				setOSPFNssaAreaDefaultProfile(14)
				}
			MAX-ACCESS read-write
			STATUS current
			DESCRIPTION
				"Description."
			::= { sleOSPFProcAreaInfoControl 1 }

		
		-- 1.3.6.1.4.1.6296.101.51.2.9.1.2.2
		sleOSPFProcAreaControlStatus OBJECT-TYPE
			SYNTAX SleControlStatusType
			MAX-ACCESS read-only
			STATUS current
			DESCRIPTION
				"Description."
			::= { sleOSPFProcAreaInfoControl 2 }

		
		-- 1.3.6.1.4.1.6296.101.51.2.9.1.2.3
		sleOSPFProcAreaControlTimer OBJECT-TYPE
			SYNTAX Gauge32
			MAX-ACCESS read-write
			STATUS current
			DESCRIPTION
				"Description."
			::= { sleOSPFProcAreaInfoControl 3 }

		
		-- 1.3.6.1.4.1.6296.101.51.2.9.1.2.4
		sleOSPFProcAreaControlTimeStamp OBJECT-TYPE
			SYNTAX TimeTicks
			MAX-ACCESS read-only
			STATUS current
			DESCRIPTION
				"Description."
			::= { sleOSPFProcAreaInfoControl 4 }

		
		-- 1.3.6.1.4.1.6296.101.51.2.9.1.2.5
		sleOSPFProcAreaControlReqResult OBJECT-TYPE
			SYNTAX SleControlRequestResultType
			MAX-ACCESS read-only
			STATUS current
			DESCRIPTION
				"Description."
			::= { sleOSPFProcAreaInfoControl 5 }

		
		-- 1.3.6.1.4.1.6296.101.51.2.9.1.2.6
		sleOSPFProcAreaControlProcID OBJECT-TYPE
			SYNTAX INTEGER (0..65535)
			MAX-ACCESS read-write
			STATUS current
			DESCRIPTION
				"Description."
			::= { sleOSPFProcAreaInfoControl 6 }

		
		-- 1.3.6.1.4.1.6296.101.51.2.9.1.2.7
		sleOSPFProcAreaControlID OBJECT-TYPE
			SYNTAX IpAddress
			MAX-ACCESS read-write
			STATUS current
			DESCRIPTION
				"Description."
			::= { sleOSPFProcAreaInfoControl 7 }

		
		-- 1.3.6.1.4.1.6296.101.51.2.9.1.2.8
		sleOSPFProcAreaControlType OBJECT-TYPE
			SYNTAX INTEGER
				{
				general(0),
				stub(1),
				nssa(2)
				}
			MAX-ACCESS read-write
			STATUS current
			DESCRIPTION
				"Description."
			::= { sleOSPFProcAreaInfoControl 8 }

		
		-- 1.3.6.1.4.1.6296.101.51.2.9.1.2.9
		sleOSPFProcAreaControlDefaultCost OBJECT-TYPE
			SYNTAX INTEGER (0..16777215)
			MAX-ACCESS read-write
			STATUS current
			DESCRIPTION
				"Description."
			::= { sleOSPFProcAreaInfoControl 9 }

		
		-- 1.3.6.1.4.1.6296.101.51.2.9.1.2.10
		sleOSPFProcAreaControlAuthenType OBJECT-TYPE
			SYNTAX INTEGER
				{
				null(0),
				simple(1),
				crypt(2)
				}
			MAX-ACCESS read-write
			STATUS current
			DESCRIPTION
				"Description."
			::= { sleOSPFProcAreaInfoControl 10 }

		
		-- 1.3.6.1.4.1.6296.101.51.2.9.1.2.11
		sleOSPFProcAreaControlFAInName OBJECT-TYPE
			SYNTAX OCTET STRING
			MAX-ACCESS read-write
			STATUS current
			DESCRIPTION
				"Description."
			::= { sleOSPFProcAreaInfoControl 11 }

		
		-- 1.3.6.1.4.1.6296.101.51.2.9.1.2.12
		sleOSPFProcAreaControlFAOutName OBJECT-TYPE
			SYNTAX OCTET STRING
			MAX-ACCESS read-write
			STATUS current
			DESCRIPTION
				"Description."
			::= { sleOSPFProcAreaInfoControl 12 }

		
		-- 1.3.6.1.4.1.6296.101.51.2.9.1.2.13
		sleOSPFProcAreaControlFPInName OBJECT-TYPE
			SYNTAX OCTET STRING
			MAX-ACCESS read-write
			STATUS current
			DESCRIPTION
				"Description."
			::= { sleOSPFProcAreaInfoControl 13 }

		
		-- 1.3.6.1.4.1.6296.101.51.2.9.1.2.14
		sleOSPFProcAreaControlFPOutName OBJECT-TYPE
			SYNTAX OCTET STRING
			MAX-ACCESS read-write
			STATUS current
			DESCRIPTION
				"Description."
			::= { sleOSPFProcAreaInfoControl 14 }

		
		-- 1.3.6.1.4.1.6296.101.51.2.9.1.2.15
		sleOSPFProcAreaControlShortcutType OBJECT-TYPE
			SYNTAX INTEGER
				{
				default(0),
				enable(1),
				disable(2)
				}
			MAX-ACCESS read-write
			STATUS current
			DESCRIPTION
				"Description."
			::= { sleOSPFProcAreaInfoControl 15 }

		
		-- 1.3.6.1.4.1.6296.101.51.2.9.1.2.16
		sleOSPFProcAreaControlSummary OBJECT-TYPE
			SYNTAX INTEGER
				{
				noAreaSummary(1),
				sendAreaSummary(2)
				}
			MAX-ACCESS read-write
			STATUS current
			DESCRIPTION
				"Description."
			::= { sleOSPFProcAreaInfoControl 16 }

		
		-- 1.3.6.1.4.1.6296.101.51.2.9.1.2.17
		sleOSPFProcAreaControlNssaTransRole OBJECT-TYPE
			SYNTAX INTEGER
				{
				never(0),
				always(1),
				candidate(2)
				}
			MAX-ACCESS read-write
			STATUS current
			DESCRIPTION
				"Description."
			::= { sleOSPFProcAreaInfoControl 17 }

		
		-- 1.3.6.1.4.1.6296.101.51.2.9.1.2.18
		sleOSPFProcAreaControlNssaNoRedist OBJECT-TYPE
			SYNTAX INTEGER
				{
				enable(1),
				disable(2)
				}
			MAX-ACCESS read-write
			STATUS current
			DESCRIPTION
				"Description."
			::= { sleOSPFProcAreaInfoControl 18 }

		
		-- 1.3.6.1.4.1.6296.101.51.2.9.1.2.19
		sleOSPFProcAreaControlNssaDefOriginate OBJECT-TYPE
			SYNTAX INTEGER
				{
				disable(0),
				enable(1)
				}
			MAX-ACCESS read-write
			STATUS current
			DESCRIPTION
				"Description."
			::= { sleOSPFProcAreaInfoControl 19 }

		
		-- 1.3.6.1.4.1.6296.101.51.2.9.1.2.20
		sleOSPFProcAreaControlNssaDefMetricType OBJECT-TYPE
			SYNTAX INTEGER
				{
				external1(1),
				external2(2)
				}
			MAX-ACCESS read-write
			STATUS current
			DESCRIPTION
				"Description."
			::= { sleOSPFProcAreaInfoControl 20 }

		
		-- 1.3.6.1.4.1.6296.101.51.2.9.1.2.21
		sleOSPFProcAreaControlNssaDefMetric OBJECT-TYPE
			SYNTAX INTEGER (0..16777214)
			MAX-ACCESS read-write
			STATUS current
			DESCRIPTION
				"Description."
			::= { sleOSPFProcAreaInfoControl 21 }

		
		-- 1.3.6.1.4.1.6296.101.51.2.9.1.3
		sleOSPFProcAreaInfoNotification OBJECT IDENTIFIER ::= { sleOSPFProcAreaInfo 3 }

		
		-- 1.3.6.1.4.1.6296.101.51.2.9.1.3.1
		sleOSPFProcGeneralAreaCreated NOTIFICATION-TYPE
			OBJECTS { sleOSPFProcAreaControlRequest, sleOSPFProcAreaControlTimeStamp, sleOSPFProcAreaControlReqResult, sleOSPFProcID, sleOSPFProcAreaID, 
				sleOSPFProcAreaType, sleOSPFProcAreaAuthenType, sleOSPFProcAreaFAInName, sleOSPFProcAreaFAOutName, sleOSPFProcAreaFPInName, 
				sleOSPFProcAreaFPOutName, sleOSPFProcAreaShortcutType }
			STATUS current
			DESCRIPTION 
				"Description."
			::= { sleOSPFProcAreaInfoNotification 1 }

		
		-- 1.3.6.1.4.1.6296.101.51.2.9.1.3.2
		sleOSPFProcStubNssaAreaCreated NOTIFICATION-TYPE
			OBJECTS { sleOSPFProcAreaControlRequest, sleOSPFProcAreaControlTimeStamp, sleOSPFProcAreaControlReqResult, sleOSPFProcID, sleOSPFProcAreaID, 
				sleOSPFProcAreaType }
			STATUS current
			DESCRIPTION 
				"Description."
			::= { sleOSPFProcAreaInfoNotification 2 }

		
		-- 1.3.6.1.4.1.6296.101.51.2.9.1.3.3
		sleOSPFProcAreaDeleted NOTIFICATION-TYPE
			OBJECTS { sleOSPFProcAreaControlRequest, sleOSPFProcAreaControlTimeStamp, sleOSPFProcAreaControlReqResult, sleOSPFProcID, sleOSPFProcAreaControlID, 
				sleOSPFProcAreaControlType }
			STATUS current
			DESCRIPTION 
				"Description."
			::= { sleOSPFProcAreaInfoNotification 3 }

		
		-- 1.3.6.1.4.1.6296.101.51.2.9.1.3.4
		sleOSPFProcAreaDefaultCostChanged NOTIFICATION-TYPE
			OBJECTS { sleOSPFProcAreaControlRequest, sleOSPFProcAreaControlTimeStamp, sleOSPFProcAreaControlReqResult, sleOSPFProcID, sleOSPFProcAreaID, 
				sleOSPFProcAreaType, sleOSPFProcAreaDefaultCost }
			STATUS current
			DESCRIPTION 
				"Description."
			::= { sleOSPFProcAreaInfoNotification 4 }

		
		-- 1.3.6.1.4.1.6296.101.51.2.9.1.3.5
		sleOSPFProcAreaAuthenTypeChanged NOTIFICATION-TYPE
			OBJECTS { sleOSPFProcAreaControlRequest, sleOSPFProcAreaControlTimeStamp, sleOSPFProcAreaControlReqResult, sleOSPFProcID, sleOSPFProcAreaID, 
				sleOSPFProcAreaType, sleOSPFProcAreaAuthenType }
			STATUS current
			DESCRIPTION 
				"Description."
			::= { sleOSPFProcAreaInfoNotification 5 }

		
		-- 1.3.6.1.4.1.6296.101.51.2.9.1.3.6
		sleOSPFProcAreaFAInNameChanged NOTIFICATION-TYPE
			OBJECTS { sleOSPFProcAreaControlRequest, sleOSPFProcAreaControlTimeStamp, sleOSPFProcAreaControlReqResult, sleOSPFProcID, sleOSPFProcAreaID, 
				sleOSPFProcAreaType, sleOSPFProcAreaFAInName }
			STATUS current
			DESCRIPTION 
				"Description."
			::= { sleOSPFProcAreaInfoNotification 6 }

		
		-- 1.3.6.1.4.1.6296.101.51.2.9.1.3.7
		sleOSPFProcAreaFAOutNameChanged NOTIFICATION-TYPE
			OBJECTS { sleOSPFProcAreaControlRequest, sleOSPFProcAreaControlTimeStamp, sleOSPFProcAreaControlReqResult, sleOSPFProcID, sleOSPFProcAreaID, 
				sleOSPFProcAreaType, sleOSPFProcAreaFAOutName }
			STATUS current
			DESCRIPTION 
				"Description."
			::= { sleOSPFProcAreaInfoNotification 7 }

		
		-- 1.3.6.1.4.1.6296.101.51.2.9.1.3.8
		sleOSPFProcAreaFPInNameChanged NOTIFICATION-TYPE
			OBJECTS { sleOSPFProcAreaControlRequest, sleOSPFProcAreaControlTimeStamp, sleOSPFProcAreaControlReqResult, sleOSPFProcID, sleOSPFProcAreaID, 
				sleOSPFProcAreaType, sleOSPFProcAreaFPInName }
			STATUS current
			DESCRIPTION 
				"Description."
			::= { sleOSPFProcAreaInfoNotification 8 }

		
		-- 1.3.6.1.4.1.6296.101.51.2.9.1.3.9
		sleOSPFProcAreaFPOutNameChanged NOTIFICATION-TYPE
			OBJECTS { sleOSPFProcAreaControlRequest, sleOSPFProcAreaControlTimeStamp, sleOSPFProcAreaControlReqResult, sleOSPFProcID, sleOSPFProcAreaID, 
				sleOSPFProcAreaType, sleOSPFProcAreaFPOutName }
			STATUS current
			DESCRIPTION 
				"Description."
			::= { sleOSPFProcAreaInfoNotification 9 }

		
		-- 1.3.6.1.4.1.6296.101.51.2.9.1.3.10
		sleOSPFProcAreaShortcutTypeChanged NOTIFICATION-TYPE
			OBJECTS { sleOSPFProcAreaControlRequest, sleOSPFProcAreaControlTimeStamp, sleOSPFProcAreaControlReqResult, sleOSPFProcID, sleOSPFProcAreaID, 
				sleOSPFProcAreaType, sleOSPFProcAreaShortcutType }
			STATUS current
			DESCRIPTION 
				"Description."
			::= { sleOSPFProcAreaInfoNotification 10 }

		
		-- 1.3.6.1.4.1.6296.101.51.2.9.1.3.11
		sleOSPFProcAreaSummaryChanged NOTIFICATION-TYPE
			OBJECTS { sleOSPFProcAreaControlRequest, sleOSPFProcAreaControlTimeStamp, sleOSPFProcAreaControlReqResult, sleOSPFProcID, sleOSPFProcAreaID, 
				sleOSPFProcAreaType, sleOSPFProcAreaSummary }
			STATUS current
			DESCRIPTION 
				"Description."
			::= { sleOSPFProcAreaInfoNotification 11 }

		
		-- 1.3.6.1.4.1.6296.101.51.2.9.1.3.12
		sleOSPFProcNssaAreaTransRoleChanged NOTIFICATION-TYPE
			OBJECTS { sleOSPFProcAreaControlRequest, sleOSPFProcAreaControlTimeStamp, sleOSPFProcAreaControlReqResult, sleOSPFProcID, sleOSPFProcAreaID, 
				sleOSPFProcAreaType, sleOSPFProcAreaNssaTransRole }
			STATUS current
			DESCRIPTION 
				"Description."
			::= { sleOSPFProcAreaInfoNotification 12 }

		
		-- 1.3.6.1.4.1.6296.101.51.2.9.1.3.13
		sleOSPFProcNssaAreaTransNoRedistChanged NOTIFICATION-TYPE
			OBJECTS { sleOSPFProcAreaControlRequest, sleOSPFProcAreaControlTimeStamp, sleOSPFProcAreaControlReqResult, sleOSPFProcID, sleOSPFProcAreaID, 
				sleOSPFProcAreaType, sleOSPFProcAreaNssaNoRedist }
			STATUS current
			DESCRIPTION 
				"Description."
			::= { sleOSPFProcAreaInfoNotification 13 }

		
		-- 1.3.6.1.4.1.6296.101.51.2.9.1.3.14
		sleOSPFProcNssaAreaDefProfileChanged NOTIFICATION-TYPE
			OBJECTS { sleOSPFProcAreaControlRequest, sleOSPFProcAreaControlTimeStamp, sleOSPFProcAreaControlReqResult, sleOSPFProcID, sleOSPFProcAreaID, 
				sleOSPFProcAreaType, sleOSPFProcAreaNssaDefOriginate, sleOSPFProcAreaNssaDefMetricType, sleOSPFProcAreaNssaDefMetric }
			STATUS current
			DESCRIPTION 
				"Description."
			::= { sleOSPFProcAreaInfoNotification 14 }

		
		-- 1.3.6.1.4.1.6296.101.51.2.9.2
		sleOSPFProcAreaRange OBJECT IDENTIFIER ::= { sleOSPFProcArea 2 }

		
		-- 1.3.6.1.4.1.6296.101.51.2.9.2.1
		sleOSPFProcAreaRangeTable OBJECT-TYPE
			SYNTAX SEQUENCE OF SleOSPFProcAreaRangeEntry
			MAX-ACCESS not-accessible
			STATUS current
			DESCRIPTION
				"Description."
			::= { sleOSPFProcAreaRange 1 }

		
		-- 1.3.6.1.4.1.6296.101.51.2.9.2.1.1
		sleOSPFProcAreaRangeEntry OBJECT-TYPE
			SYNTAX SleOSPFProcAreaRangeEntry
			MAX-ACCESS not-accessible
			STATUS current
			DESCRIPTION
				"Description."
			INDEX { sleOSPFProcID, sleOSPFProcAreaID, sleOSPFProcAreaRangeIP, sleOSPFProcAreaRangeIPMask }
			::= { sleOSPFProcAreaRangeTable 1 }

		
		SleOSPFProcAreaRangeEntry ::=
			SEQUENCE { 
				sleOSPFProcAreaRangeIP
					IpAddress,
				sleOSPFProcAreaRangeIPMask
					Integer32,
				sleOSPFProcAreaRangeAdverType
					INTEGER
			 }

		-- 1.3.6.1.4.1.6296.101.51.2.9.2.1.1.1
		sleOSPFProcAreaRangeIP OBJECT-TYPE
			SYNTAX IpAddress
			MAX-ACCESS read-only
			STATUS current
			DESCRIPTION
				"Description."
			::= { sleOSPFProcAreaRangeEntry 1 }

		
		-- 1.3.6.1.4.1.6296.101.51.2.9.2.1.1.2
		sleOSPFProcAreaRangeIPMask OBJECT-TYPE
			SYNTAX Integer32 (0..32)
			MAX-ACCESS read-only
			STATUS current
			DESCRIPTION
				"Description."
			::= { sleOSPFProcAreaRangeEntry 2 }

		
		-- 1.3.6.1.4.1.6296.101.51.2.9.2.1.1.3
		sleOSPFProcAreaRangeAdverType OBJECT-TYPE
			SYNTAX INTEGER
				{
				notAdvertise(0),
				advertise(1)
				}
			MAX-ACCESS read-only
			STATUS current
			DESCRIPTION
				"Description."
			::= { sleOSPFProcAreaRangeEntry 3 }

		
		-- 1.3.6.1.4.1.6296.101.51.2.9.2.2
		sleOSPFProcAreaRangeControl OBJECT IDENTIFIER ::= { sleOSPFProcAreaRange 2 }

		
		-- 1.3.6.1.4.1.6296.101.51.2.9.2.2.1
		sleOSPFProcAreaRangeControlRequest OBJECT-TYPE
			SYNTAX INTEGER
				{
				createOSPFAreaRange(1),
				deleteOSPFAreaRange(2),
				setOSPFAreaRange(3)
				}
			MAX-ACCESS read-write
			STATUS current
			DESCRIPTION
				"Description."
			::= { sleOSPFProcAreaRangeControl 1 }

		
		-- 1.3.6.1.4.1.6296.101.51.2.9.2.2.2
		sleOSPFProcAreaRangeControlStatus OBJECT-TYPE
			SYNTAX SleControlStatusType
			MAX-ACCESS read-only
			STATUS current
			DESCRIPTION
				"Description."
			::= { sleOSPFProcAreaRangeControl 2 }

		
		-- 1.3.6.1.4.1.6296.101.51.2.9.2.2.3
		sleOSPFProcAreaRangeControlTimer OBJECT-TYPE
			SYNTAX Gauge32
			MAX-ACCESS read-write
			STATUS current
			DESCRIPTION
				"Description."
			::= { sleOSPFProcAreaRangeControl 3 }

		
		-- 1.3.6.1.4.1.6296.101.51.2.9.2.2.4
		sleOSPFProcAreaRangeControlTimeStamp OBJECT-TYPE
			SYNTAX TimeTicks
			MAX-ACCESS read-only
			STATUS current
			DESCRIPTION
				"Description."
			::= { sleOSPFProcAreaRangeControl 4 }

		
		-- 1.3.6.1.4.1.6296.101.51.2.9.2.2.5
		sleOSPFProcAreaRangeControlReqResult OBJECT-TYPE
			SYNTAX SleControlRequestResultType
			MAX-ACCESS read-write
			STATUS current
			DESCRIPTION
				"Description."
			::= { sleOSPFProcAreaRangeControl 5 }

		
		-- 1.3.6.1.4.1.6296.101.51.2.9.2.2.6
		sleOSPFProcAreaRangeControlProcID OBJECT-TYPE
			SYNTAX INTEGER (0..65535)
			MAX-ACCESS read-write
			STATUS current
			DESCRIPTION
				"Description."
			::= { sleOSPFProcAreaRangeControl 6 }

		
		-- 1.3.6.1.4.1.6296.101.51.2.9.2.2.7
		sleOSPFProcAreaRangeControlID OBJECT-TYPE
			SYNTAX IpAddress
			MAX-ACCESS read-write
			STATUS current
			DESCRIPTION
				"Description."
			::= { sleOSPFProcAreaRangeControl 7 }

		
		-- 1.3.6.1.4.1.6296.101.51.2.9.2.2.8
		sleOSPFProcAreaRangeControlIP OBJECT-TYPE
			SYNTAX IpAddress
			MAX-ACCESS read-write
			STATUS current
			DESCRIPTION
				"Description."
			::= { sleOSPFProcAreaRangeControl 8 }

		
		-- 1.3.6.1.4.1.6296.101.51.2.9.2.2.9
		sleOSPFProcAreaRangeControlIPMask OBJECT-TYPE
			SYNTAX INTEGER (0..32)
			MAX-ACCESS read-write
			STATUS current
			DESCRIPTION
				"Description."
			::= { sleOSPFProcAreaRangeControl 9 }

		
		-- 1.3.6.1.4.1.6296.101.51.2.9.2.2.10
		sleOSPFProcAreaRangeControlAdverType OBJECT-TYPE
			SYNTAX INTEGER
				{
				notAdvertise(0),
				advertise(1)
				}
			MAX-ACCESS read-write
			STATUS current
			DESCRIPTION
				"Description."
			::= { sleOSPFProcAreaRangeControl 10 }

		
		-- 1.3.6.1.4.1.6296.101.51.2.9.2.3
		sleOSPFProcAreaRangeNotification OBJECT IDENTIFIER ::= { sleOSPFProcAreaRange 3 }

		
		-- 1.3.6.1.4.1.6296.101.51.2.9.2.3.1
		sleOSPFAreaRangeCreated NOTIFICATION-TYPE
			OBJECTS { sleOSPFProcAreaRangeControlRequest, sleOSPFProcAreaRangeControlTimeStamp, sleOSPFProcAreaRangeControlReqResult, sleOSPFProcID, sleOSPFProcAreaID, 
				sleOSPFProcAreaRangeIP, sleOSPFProcAreaRangeIPMask, sleOSPFProcAreaRangeAdverType }
			STATUS current
			DESCRIPTION 
				"Description."
			::= { sleOSPFProcAreaRangeNotification 1 }

		
		-- 1.3.6.1.4.1.6296.101.51.2.9.2.3.2
		sleOSPFAreaRangeDeleted NOTIFICATION-TYPE
			OBJECTS { sleOSPFProcAreaRangeControlRequest, sleOSPFProcAreaRangeControlTimeStamp, sleOSPFProcAreaRangeControlReqResult, sleOSPFProcID, sleOSPFProcAreaRangeControlID, 
				sleOSPFProcAreaRangeControlIP, sleOSPFProcAreaRangeControlIPMask, sleOSPFProcAreaRangeControlAdverType }
			STATUS current
			DESCRIPTION 
				"Description."
			::= { sleOSPFProcAreaRangeNotification 2 }

		
		-- 1.3.6.1.4.1.6296.101.51.2.9.2.3.3
		sleOSPFAreaRangeChanged NOTIFICATION-TYPE
			OBJECTS { sleOSPFProcAreaRangeControlRequest, sleOSPFProcAreaRangeControlTimeStamp, sleOSPFProcAreaRangeControlReqResult, sleOSPFProcID, sleOSPFProcAreaID, 
				sleOSPFProcAreaRangeIP, sleOSPFProcAreaRangeIPMask, sleOSPFProcAreaRangeAdverType }
			STATUS current
			DESCRIPTION 
				"Description."
			::= { sleOSPFProcAreaRangeNotification 3 }

		
		-- 1.3.6.1.4.1.6296.101.51.2.9.3
		sleOSPFProcAreaVlink OBJECT IDENTIFIER ::= { sleOSPFProcArea 3 }

		
		-- 1.3.6.1.4.1.6296.101.51.2.9.3.1
		sleOSPFProcAreaVlinkInfo OBJECT IDENTIFIER ::= { sleOSPFProcAreaVlink 1 }

		
		-- 1.3.6.1.4.1.6296.101.51.2.9.3.1.1
		sleOSPFProcAreaVlinkInfoTable OBJECT-TYPE
			SYNTAX SEQUENCE OF SleOSPFProcAreaVlinkInfoEntry
			MAX-ACCESS not-accessible
			STATUS current
			DESCRIPTION
				"Description."
			::= { sleOSPFProcAreaVlinkInfo 1 }

		
		-- 1.3.6.1.4.1.6296.101.51.2.9.3.1.1.1
		sleOSPFProcAreaVlinkInfoEntry OBJECT-TYPE
			SYNTAX SleOSPFProcAreaVlinkInfoEntry
			MAX-ACCESS not-accessible
			STATUS current
			DESCRIPTION
				"Description."
			INDEX { sleOSPFProcID, sleOSPFProcAreaID, sleOSPFProcAreaVlinkIP }
			::= { sleOSPFProcAreaVlinkInfoTable 1 }

		
		SleOSPFProcAreaVlinkInfoEntry ::=
			SEQUENCE { 
				sleOSPFProcAreaVlinkIP
					IpAddress,
				sleOSPFProcAreaVlinkAuthenType
					INTEGER,
				sleOSPFProcAreaVlinkAuthenKey
					OCTET STRING,
				sleOSPFProcAreaVlinkDeadInterval
					INTEGER,
				sleOSPFProcAreaVlinkHelloInterval
					INTEGER,
				sleOSPFProcAreaVlinkRetranInterval
					INTEGER,
				sleOSPFProcAreaVlinkTransDelay
					INTEGER
			 }

		-- 1.3.6.1.4.1.6296.101.51.2.9.3.1.1.1.1
		sleOSPFProcAreaVlinkIP OBJECT-TYPE
			SYNTAX IpAddress
			MAX-ACCESS read-only
			STATUS current
			DESCRIPTION
				"Description."
			::= { sleOSPFProcAreaVlinkInfoEntry 1 }

		
		-- 1.3.6.1.4.1.6296.101.51.2.9.3.1.1.1.2
		sleOSPFProcAreaVlinkAuthenType OBJECT-TYPE
			SYNTAX INTEGER
				{
				null(0),
				simple(1),
				crypto(2)
				}
			MAX-ACCESS read-only
			STATUS current
			DESCRIPTION
				"Description."
			::= { sleOSPFProcAreaVlinkInfoEntry 2 }

		
		-- 1.3.6.1.4.1.6296.101.51.2.9.3.1.1.1.3
		sleOSPFProcAreaVlinkAuthenKey OBJECT-TYPE
			SYNTAX OCTET STRING
			MAX-ACCESS read-only
			STATUS current
			DESCRIPTION
				"Description."
			::= { sleOSPFProcAreaVlinkInfoEntry 3 }

		
		-- 1.3.6.1.4.1.6296.101.51.2.9.3.1.1.1.4
		sleOSPFProcAreaVlinkDeadInterval OBJECT-TYPE
			SYNTAX INTEGER (0..65535)
			MAX-ACCESS read-only
			STATUS current
			DESCRIPTION
				"Description."
			::= { sleOSPFProcAreaVlinkInfoEntry 4 }

		
		-- 1.3.6.1.4.1.6296.101.51.2.9.3.1.1.1.5
		sleOSPFProcAreaVlinkHelloInterval OBJECT-TYPE
			SYNTAX INTEGER (0..65535)
			MAX-ACCESS read-only
			STATUS current
			DESCRIPTION
				"Description."
			::= { sleOSPFProcAreaVlinkInfoEntry 5 }

		
		-- 1.3.6.1.4.1.6296.101.51.2.9.3.1.1.1.6
		sleOSPFProcAreaVlinkRetranInterval OBJECT-TYPE
			SYNTAX INTEGER (0..65535)
			MAX-ACCESS read-only
			STATUS current
			DESCRIPTION
				"Description."
			::= { sleOSPFProcAreaVlinkInfoEntry 6 }

		
		-- 1.3.6.1.4.1.6296.101.51.2.9.3.1.1.1.7
		sleOSPFProcAreaVlinkTransDelay OBJECT-TYPE
			SYNTAX INTEGER (0..65535)
			MAX-ACCESS read-only
			STATUS current
			DESCRIPTION
				"Description."
			::= { sleOSPFProcAreaVlinkInfoEntry 7 }

		
		-- 1.3.6.1.4.1.6296.101.51.2.9.3.1.2
		sleOSPFProcAreaVlinkControl OBJECT IDENTIFIER ::= { sleOSPFProcAreaVlinkInfo 2 }

		
		-- 1.3.6.1.4.1.6296.101.51.2.9.3.1.2.1
		sleOSPFProcAreaVlinkControlRequest OBJECT-TYPE
			SYNTAX INTEGER
				{
				createOSPFAreaVlink(1),
				deleteOSPFAreaVlink(2),
				setOSPFAreaVlink(3)
				}
			MAX-ACCESS read-write
			STATUS current
			DESCRIPTION
				"Description."
			::= { sleOSPFProcAreaVlinkControl 1 }

		
		-- 1.3.6.1.4.1.6296.101.51.2.9.3.1.2.2
		sleOSPFProcAreaVlinkControlStatus OBJECT-TYPE
			SYNTAX SleControlStatusType
			MAX-ACCESS read-only
			STATUS current
			DESCRIPTION
				"Description."
			::= { sleOSPFProcAreaVlinkControl 2 }

		
		-- 1.3.6.1.4.1.6296.101.51.2.9.3.1.2.3
		sleOSPFProcAreaVlinkControlTimer OBJECT-TYPE
			SYNTAX Gauge32
			MAX-ACCESS read-write
			STATUS current
			DESCRIPTION
				"Description."
			::= { sleOSPFProcAreaVlinkControl 3 }

		
		-- 1.3.6.1.4.1.6296.101.51.2.9.3.1.2.4
		sleOSPFProcAreaVlinkControlTimeStamp OBJECT-TYPE
			SYNTAX TimeTicks
			MAX-ACCESS read-only
			STATUS current
			DESCRIPTION
				"Description."
			::= { sleOSPFProcAreaVlinkControl 4 }

		
		-- 1.3.6.1.4.1.6296.101.51.2.9.3.1.2.5
		sleOSPFProcAreaVlinkControlReqResult OBJECT-TYPE
			SYNTAX SleControlRequestResultType
			MAX-ACCESS read-only
			STATUS current
			DESCRIPTION
				"Description."
			::= { sleOSPFProcAreaVlinkControl 5 }

		
		-- 1.3.6.1.4.1.6296.101.51.2.9.3.1.2.6
		sleOSPFProcAreaVlinkControlProcID OBJECT-TYPE
			SYNTAX INTEGER (0..65535)
			MAX-ACCESS read-write
			STATUS current
			DESCRIPTION
				"Description."
			::= { sleOSPFProcAreaVlinkControl 6 }

		
		-- 1.3.6.1.4.1.6296.101.51.2.9.3.1.2.7
		sleOSPFProcAreaVlinkControlControlID OBJECT-TYPE
			SYNTAX Gauge32 (0..4294967295)
			MAX-ACCESS read-write
			STATUS current
			DESCRIPTION
				"Description."
			::= { sleOSPFProcAreaVlinkControl 7 }

		
		-- 1.3.6.1.4.1.6296.101.51.2.9.3.1.2.8
		sleOSPFProcAreaVlinkControlIP OBJECT-TYPE
			SYNTAX IpAddress
			MAX-ACCESS read-write
			STATUS current
			DESCRIPTION
				"Description."
			::= { sleOSPFProcAreaVlinkControl 8 }

		
		-- 1.3.6.1.4.1.6296.101.51.2.9.3.1.2.9
		sleOSPFProcAreaVlinkControlAuthenType OBJECT-TYPE
			SYNTAX INTEGER
				{
				null(0),
				simple(1),
				crypto(2)
				}
			MAX-ACCESS read-write
			STATUS current
			DESCRIPTION
				"Description."
			::= { sleOSPFProcAreaVlinkControl 9 }

		
		-- 1.3.6.1.4.1.6296.101.51.2.9.3.1.2.10
		sleOSPFProcAreaVlinkControlAuthenKey OBJECT-TYPE
			SYNTAX OCTET STRING
			MAX-ACCESS read-write
			STATUS current
			DESCRIPTION
				"Description."
			::= { sleOSPFProcAreaVlinkControl 10 }

		
		-- 1.3.6.1.4.1.6296.101.51.2.9.3.1.2.11
		sleOSPFProcAreaVlinkControlDeadInterval OBJECT-TYPE
			SYNTAX INTEGER (0..65535)
			MAX-ACCESS read-write
			STATUS current
			DESCRIPTION
				"Description."
			::= { sleOSPFProcAreaVlinkControl 11 }

		
		-- 1.3.6.1.4.1.6296.101.51.2.9.3.1.2.12
		sleOSPFProcAreaVlinkControlHelloInterval OBJECT-TYPE
			SYNTAX INTEGER (0..65535)
			MAX-ACCESS read-write
			STATUS current
			DESCRIPTION
				"Description."
			::= { sleOSPFProcAreaVlinkControl 12 }

		
		-- 1.3.6.1.4.1.6296.101.51.2.9.3.1.2.13
		sleOSPFProcAreaVlinkControlRetranInterval OBJECT-TYPE
			SYNTAX INTEGER (0..65535)
			MAX-ACCESS read-write
			STATUS current
			DESCRIPTION
				"Description."
			::= { sleOSPFProcAreaVlinkControl 13 }

		
		-- 1.3.6.1.4.1.6296.101.51.2.9.3.1.2.14
		sleOSPFProcAreaVlinkControlTransInterval OBJECT-TYPE
			SYNTAX INTEGER (0..65535)
			MAX-ACCESS read-write
			STATUS current
			DESCRIPTION
				"Description."
			::= { sleOSPFProcAreaVlinkControl 14 }

		
		-- 1.3.6.1.4.1.6296.101.51.2.9.3.1.3
		sleOSPFProcAreaVlinkNotification OBJECT IDENTIFIER ::= { sleOSPFProcAreaVlinkInfo 3 }

		
		-- 1.3.6.1.4.1.6296.101.51.2.9.3.1.3.1
		sleOSPFAreaVlinkCreated NOTIFICATION-TYPE
			OBJECTS { sleOSPFProcAreaVlinkControlRequest, sleOSPFProcAreaVlinkControlTimeStamp, sleOSPFProcAreaVlinkControlReqResult, sleOSPFProcID, sleOSPFProcAreaID, 
				sleOSPFProcAreaVlinkIP, sleOSPFProcAreaVlinkAuthenType, sleOSPFProcAreaVlinkAuthenKey, sleOSPFProcAreaVlinkDeadInterval, sleOSPFProcAreaVlinkHelloInterval, 
				sleOSPFProcAreaVlinkRetranInterval, sleOSPFProcAreaVlinkTransInterval }
			STATUS current
			DESCRIPTION 
				"Description."
			::= { sleOSPFProcAreaVlinkNotification 1 }

		
		-- 1.3.6.1.4.1.6296.101.51.2.9.3.1.3.2
		sleOSPFAreaVLinkDeleted NOTIFICATION-TYPE
			OBJECTS { sleOSPFProcAreaVlinkControlRequest, sleOSPFProcAreaVlinkControlTimeStamp, sleOSPFProcAreaVlinkControlReqResult, sleOSPFProcID, sleOSPFProcAreaVlinkControlControlID, 
				sleOSPFProcAreaVlinkControlIP }
			STATUS current
			DESCRIPTION 
				"Description."
			::= { sleOSPFProcAreaVlinkNotification 2 }

		
		-- 1.3.6.1.4.1.6296.101.51.2.9.3.1.3.3
		sleOSPFAreaVLinkChanged NOTIFICATION-TYPE
			OBJECTS { sleOSPFProcAreaVlinkControlRequest, sleOSPFProcAreaVlinkControlTimeStamp, sleOSPFProcAreaVlinkControlReqResult, sleOSPFProcID, sleOSPFProcAreaID, 
				sleOSPFProcAreaVlinkIP, sleOSPFProcAreaVlinkAuthenType, sleOSPFProcAreaVlinkAuthenKey, sleOSPFProcAreaVlinkDeadInterval, sleOSPFProcAreaVlinkHelloInterval, 
				sleOSPFProcAreaVlinkRetranInterval, sleOSPFProcAreaVlinkTransInterval }
			STATUS current
			DESCRIPTION 
				"Description."
			::= { sleOSPFProcAreaVlinkNotification 3 }

		
		-- 1.3.6.1.4.1.6296.101.51.2.9.3.2
		sleOSPFProcAreaVlinkMsgKey OBJECT IDENTIFIER ::= { sleOSPFProcAreaVlink 2 }

		
		-- 1.3.6.1.4.1.6296.101.51.2.9.3.2.1
		sleOSPFProcAreaVlinkMsgKeyTable OBJECT-TYPE
			SYNTAX SEQUENCE OF SleOSPFProcAreaVlinkMsgKeyEntry
			MAX-ACCESS not-accessible
			STATUS current
			DESCRIPTION
				"Description."
			::= { sleOSPFProcAreaVlinkMsgKey 1 }

		
		-- 1.3.6.1.4.1.6296.101.51.2.9.3.2.1.1
		sleOSPFProcAreaVlinkMsgKeyEntry OBJECT-TYPE
			SYNTAX SleOSPFProcAreaVlinkMsgKeyEntry
			MAX-ACCESS not-accessible
			STATUS current
			DESCRIPTION
				"Description."
			INDEX { sleOSPFProcID, sleOSPFProcAreaID, sleOSPFProcAreaVlinkIP, sleOSPFProcAreaVlinkMsgKeyID }
			::= { sleOSPFProcAreaVlinkMsgKeyTable 1 }

		
		SleOSPFProcAreaVlinkMsgKeyEntry ::=
			SEQUENCE { 
				sleOSPFProcAreaVlinkMsgKeyID
					Integer32,
				sleOSPFProcAreaVlinkMsgKeyVal
					OCTET STRING
			 }

		-- 1.3.6.1.4.1.6296.101.51.2.9.3.2.1.1.1
		sleOSPFProcAreaVlinkMsgKeyID OBJECT-TYPE
			SYNTAX Integer32 (0..255)
			MAX-ACCESS read-only
			STATUS current
			DESCRIPTION
				"Description."
			::= { sleOSPFProcAreaVlinkMsgKeyEntry 1 }

		
		-- 1.3.6.1.4.1.6296.101.51.2.9.3.2.1.1.2
		sleOSPFProcAreaVlinkMsgKeyVal OBJECT-TYPE
			SYNTAX OCTET STRING (SIZE (0..16))
			MAX-ACCESS read-only
			STATUS current
			DESCRIPTION
				"Description."
			::= { sleOSPFProcAreaVlinkMsgKeyEntry 2 }

		
		-- 1.3.6.1.4.1.6296.101.51.2.9.3.2.2
		sleOSPFProcAreaVlinkMsgKeyControl OBJECT IDENTIFIER ::= { sleOSPFProcAreaVlinkMsgKey 2 }

		
		-- 1.3.6.1.4.1.6296.101.51.2.9.3.2.2.1
		sleOSPFProcAreaVlinkMsgKeyControlRequest OBJECT-TYPE
			SYNTAX INTEGER
				{
				createOSPFAreaVlinkMsgKey(1),
				deleteOSPFAreaVlinkMsgKey(2)
				}
			MAX-ACCESS read-write
			STATUS current
			DESCRIPTION
				"Description."
			::= { sleOSPFProcAreaVlinkMsgKeyControl 1 }

		
		-- 1.3.6.1.4.1.6296.101.51.2.9.3.2.2.2
		sleOSPFProcAreaVlinkMsgKeyControlControlStatus OBJECT-TYPE
			SYNTAX SleControlStatusType
			MAX-ACCESS read-only
			STATUS current
			DESCRIPTION
				"Description."
			::= { sleOSPFProcAreaVlinkMsgKeyControl 2 }

		
		-- 1.3.6.1.4.1.6296.101.51.2.9.3.2.2.3
		sleOSPFProcAreaVlinkMsgKeyControlControlTimer OBJECT-TYPE
			SYNTAX Gauge32
			MAX-ACCESS read-write
			STATUS current
			DESCRIPTION
				"Description."
			::= { sleOSPFProcAreaVlinkMsgKeyControl 3 }

		
		-- 1.3.6.1.4.1.6296.101.51.2.9.3.2.2.4
		sleOSPFProcAreaVlinkMsgKeyControlTimeStamp OBJECT-TYPE
			SYNTAX TimeTicks
			MAX-ACCESS read-only
			STATUS current
			DESCRIPTION
				"Description."
			::= { sleOSPFProcAreaVlinkMsgKeyControl 4 }

		
		-- 1.3.6.1.4.1.6296.101.51.2.9.3.2.2.5
		sleOSPFProcAreaVlinkMsgKeyControlReqResult OBJECT-TYPE
			SYNTAX SleControlRequestResultType
			MAX-ACCESS read-only
			STATUS current
			DESCRIPTION
				"Description."
			::= { sleOSPFProcAreaVlinkMsgKeyControl 5 }

		
		-- 1.3.6.1.4.1.6296.101.51.2.9.3.2.2.6
		sleOSPFProcAreaVlinkMsgKeyControlProcID OBJECT-TYPE
			SYNTAX INTEGER (0..65535)
			MAX-ACCESS read-write
			STATUS current
			DESCRIPTION
				"Description."
			::= { sleOSPFProcAreaVlinkMsgKeyControl 6 }

		
		-- 1.3.6.1.4.1.6296.101.51.2.9.3.2.2.7
		sleOSPFProcAreaVlinkMsgKeyControlID OBJECT-TYPE
			SYNTAX Gauge32 (0..4294967295)
			MAX-ACCESS read-write
			STATUS current
			DESCRIPTION
				"Description."
			::= { sleOSPFProcAreaVlinkMsgKeyControl 7 }

		
		-- 1.3.6.1.4.1.6296.101.51.2.9.3.2.2.8
		sleOSPFProcAreaVlinkMsgKeyControlIP OBJECT-TYPE
			SYNTAX IpAddress
			MAX-ACCESS read-write
			STATUS current
			DESCRIPTION
				"Description."
			::= { sleOSPFProcAreaVlinkMsgKeyControl 8 }

		
		-- 1.3.6.1.4.1.6296.101.51.2.9.3.2.2.9
		sleOSPFProcAreaVlinkMsgKeyControlKeyID OBJECT-TYPE
			SYNTAX INTEGER (0..255)
			MAX-ACCESS read-write
			STATUS current
			DESCRIPTION
				"Description."
			::= { sleOSPFProcAreaVlinkMsgKeyControl 9 }

		
		-- 1.3.6.1.4.1.6296.101.51.2.9.3.2.2.10
		sleOSPFProcAreaVlinkMsgKeyControlKeyVal OBJECT-TYPE
			SYNTAX OCTET STRING (SIZE (0..16))
			MAX-ACCESS read-write
			STATUS current
			DESCRIPTION
				"Description."
			::= { sleOSPFProcAreaVlinkMsgKeyControl 10 }

		
		-- 1.3.6.1.4.1.6296.101.51.2.9.3.2.3
		sleOSPFProcAreaVlinkMsgKeyNotification OBJECT IDENTIFIER ::= { sleOSPFProcAreaVlinkMsgKey 3 }

		
		-- 1.3.6.1.4.1.6296.101.51.2.9.3.2.3.1
		sleOSPFAreaVlinkMsgKeyCreated NOTIFICATION-TYPE
			OBJECTS { sleOSPFProcAreaVlinkControlRequest, sleOSPFProcAreaVlinkControlTimeStamp, sleOSPFProcAreaVlinkControlReqResult, sleOSPFProcID, sleOSPFProcAreaID, 
				sleOSPFProcAreaVlinkIP, sleOSPFProcAreaVlinkMsgKeyID, sleOSPFProcAreaVlinkMsgKeyVal }
			STATUS current
			DESCRIPTION 
				"Description."
			::= { sleOSPFProcAreaVlinkMsgKeyNotification 1 }

		
		-- 1.3.6.1.4.1.6296.101.51.2.9.3.2.3.2
		sleOSPFAreaVLinkMsgKeyDeleted NOTIFICATION-TYPE
			OBJECTS { sleOSPFProcAreaVlinkControlRequest, sleOSPFProcAreaVlinkControlTimeStamp, sleOSPFProcAreaVlinkControlReqResult, sleOSPFProcID, sleOSPFProcAreaID, 
				sleOSPFProcAreaVlinkIP, sleOSPFProcAreaVlinkMsgKeyControlKeyID }
			STATUS current
			DESCRIPTION 
				"Description."
			::= { sleOSPFProcAreaVlinkMsgKeyNotification 2 }

		
		-- 1.3.6.1.4.1.6296.101.51.3
		sleOSPFInterface OBJECT IDENTIFIER ::= { sleOspf 3 }

		
		-- 1.3.6.1.4.1.6296.101.51.3.1
		sleOSPFIf OBJECT IDENTIFIER ::= { sleOSPFInterface 1 }

		
		-- 1.3.6.1.4.1.6296.101.51.3.1.1
		sleOSPFIfTable OBJECT-TYPE
			SYNTAX SEQUENCE OF SleOSPFIfEntry
			MAX-ACCESS not-accessible
			STATUS current
			DESCRIPTION
				"Description."
			::= { sleOSPFIf 1 }

		
		-- 1.3.6.1.4.1.6296.101.51.3.1.1.1
		sleOSPFIfEntry OBJECT-TYPE
			SYNTAX SleOSPFIfEntry
			MAX-ACCESS not-accessible
			STATUS current
			DESCRIPTION
				"Description."
			INDEX { sleOSPFIfIndex }
			::= { sleOSPFIfTable 1 }

		
		SleOSPFIfEntry ::=
			SEQUENCE { 
				sleOSPFIfIndex
					Integer32,
				sleOSFPIfEnabled
					INTEGER,
				sleOSPFIfNetworkType
					INTEGER,
				sleOSFPIfMTU
					INTEGER,
				sleOSFPIfBFD
					INTEGER,
				sleOSFPIfEFM
					INTEGER
			 }

		-- 1.3.6.1.4.1.6296.101.51.3.1.1.1.1
		sleOSPFIfIndex OBJECT-TYPE
			SYNTAX Integer32 (1..4097)
			MAX-ACCESS read-only
			STATUS current
			DESCRIPTION
				"Description."
			::= { sleOSPFIfEntry 1 }

		
		-- 1.3.6.1.4.1.6296.101.51.3.1.1.1.2
		sleOSFPIfEnabled OBJECT-TYPE
			SYNTAX INTEGER
				{
				disable(0),
				enable(1)
				}
			MAX-ACCESS read-only
			STATUS current
			DESCRIPTION
				"Description."
			::= { sleOSPFIfEntry 2 }

		
		-- 1.3.6.1.4.1.6296.101.51.3.1.1.1.3
		sleOSPFIfNetworkType OBJECT-TYPE
			SYNTAX INTEGER
				{
				none(0),
				p2p(1),
				broadcast(2),
				nbma(3),
				p2mp(4),
				p2mpNbma(5),
				virtuallink(6),
				loopback(7)
				}
			MAX-ACCESS read-only
			STATUS current
			DESCRIPTION
				"Description."
			::= { sleOSPFIfEntry 3 }

		
		-- 1.3.6.1.4.1.6296.101.51.3.1.1.1.4
		sleOSFPIfMTU OBJECT-TYPE
			SYNTAX INTEGER (576..65535)
			MAX-ACCESS read-only
			STATUS current
			DESCRIPTION
				"Description."
			::= { sleOSPFIfEntry 4 }

		
		-- 1.3.6.1.4.1.6296.101.51.3.1.1.1.5
		sleOSFPIfBFD OBJECT-TYPE
			SYNTAX INTEGER
				{
				disable(0),
				enable(1),
				none(2)
				}
			MAX-ACCESS read-only
			STATUS current
			DESCRIPTION
				"Description."
			::= { sleOSPFIfEntry 5 }

		
		-- 1.3.6.1.4.1.6296.101.51.3.1.1.1.6
		sleOSFPIfEFM OBJECT-TYPE
			SYNTAX INTEGER
				{
				disable(0),
				enable(1),
				none(2)
				}
			MAX-ACCESS read-only
			STATUS current
			DESCRIPTION
				"Description."
			::= { sleOSPFIfEntry 6 }

		
		-- 1.3.6.1.4.1.6296.101.51.3.1.2
		sleOSPFIfControl OBJECT IDENTIFIER ::= { sleOSPFIf 2 }

		
		-- 1.3.6.1.4.1.6296.101.51.3.1.2.1
		sleOSPFIfControlRequest OBJECT-TYPE
			SYNTAX INTEGER
				{
				setOSPFIFEnabled(1),
				setOSPFIFNetworkType(2),
				setOSPFIFMTU(3),
				setOSPFIFBFD(4),
				setOSPFIFEFM(5)
				}
			MAX-ACCESS read-write
			STATUS current
			DESCRIPTION
				"Description."
			::= { sleOSPFIfControl 1 }

		
		-- 1.3.6.1.4.1.6296.101.51.3.1.2.2
		sleOSPFIfControlStatus OBJECT-TYPE
			SYNTAX SleControlStatusType
			MAX-ACCESS read-only
			STATUS current
			DESCRIPTION
				"Description."
			::= { sleOSPFIfControl 2 }

		
		-- 1.3.6.1.4.1.6296.101.51.3.1.2.3
		sleOSPFIfControlTimer OBJECT-TYPE
			SYNTAX Gauge32
			MAX-ACCESS read-write
			STATUS current
			DESCRIPTION
				"Description."
			::= { sleOSPFIfControl 3 }

		
		-- 1.3.6.1.4.1.6296.101.51.3.1.2.4
		sleOSPFIfControlTimeStamp OBJECT-TYPE
			SYNTAX TimeTicks
			MAX-ACCESS read-only
			STATUS current
			DESCRIPTION
				"Description."
			::= { sleOSPFIfControl 4 }

		
		-- 1.3.6.1.4.1.6296.101.51.3.1.2.5
		sleOSPFIfControlReqResult OBJECT-TYPE
			SYNTAX SleControlRequestResultType
			MAX-ACCESS read-only
			STATUS current
			DESCRIPTION
				"Description."
			::= { sleOSPFIfControl 5 }

		
		-- 1.3.6.1.4.1.6296.101.51.3.1.2.6
		sleOSPFIfControlIndex OBJECT-TYPE
			SYNTAX INTEGER (0..65535)
			MAX-ACCESS read-write
			STATUS current
			DESCRIPTION
				"Description."
			::= { sleOSPFIfControl 6 }

		
		-- 1.3.6.1.4.1.6296.101.51.3.1.2.7
		sleOSPFIfControlEnabled OBJECT-TYPE
			SYNTAX INTEGER
				{
				disable(0),
				enable(1)
				}
			MAX-ACCESS read-write
			STATUS current
			DESCRIPTION
				"Description."
			::= { sleOSPFIfControl 7 }

		
		-- 1.3.6.1.4.1.6296.101.51.3.1.2.8
		sleOSPFIfControlNetworkType OBJECT-TYPE
			SYNTAX INTEGER
				{
				none(0),
				p2p(1),
				broadcast(2),
				nbma(3),
				p2mp(4),
				p2mpNbma(5)
				}
			MAX-ACCESS read-write
			STATUS current
			DESCRIPTION
				"Description."
			::= { sleOSPFIfControl 8 }

		
		-- 1.3.6.1.4.1.6296.101.51.3.1.2.9
		sleOSPFIfControlMTU OBJECT-TYPE
			SYNTAX INTEGER (576..65535)
			MAX-ACCESS read-write
			STATUS current
			DESCRIPTION
				"Description."
			::= { sleOSPFIfControl 9 }

		
		-- 1.3.6.1.4.1.6296.101.51.3.1.2.10
		sleOSPFIfControlBFD OBJECT-TYPE
			SYNTAX INTEGER
				{
				disable(0),
				enable(1),
				none(2)
				}
			MAX-ACCESS read-write
			STATUS current
			DESCRIPTION
				"Description."
			::= { sleOSPFIfControl 10 }

		
		-- 1.3.6.1.4.1.6296.101.51.3.1.2.11
		sleOSPFIfControlEFM OBJECT-TYPE
			SYNTAX INTEGER
				{
				disable(0),
				enable(1),
				none(2)
				}
			MAX-ACCESS read-write
			STATUS current
			DESCRIPTION
				"Description."
			::= { sleOSPFIfControl 11 }

		
		-- 1.3.6.1.4.1.6296.101.51.3.1.3
		sleOSPFIfBaseNotification OBJECT IDENTIFIER ::= { sleOSPFIf 3 }

		
		-- 1.3.6.1.4.1.6296.101.51.3.1.3.1
		sleOSPFIfEnableChanged NOTIFICATION-TYPE
			OBJECTS { sleOSPFIfControlRequest, sleOSPFIfControlTimeStamp, sleOSPFIfControlReqResult, sleOSFPIfEnabled, sleOSPFIfIndex
				 }
			STATUS current
			DESCRIPTION 
				"Description."
			::= { sleOSPFIfBaseNotification 1 }

		
		-- 1.3.6.1.4.1.6296.101.51.3.1.3.2
		sleOSPFIfNetworkTypeChanged NOTIFICATION-TYPE
			OBJECTS { sleOSPFIfControlRequest, sleOSPFIfControlTimeStamp, sleOSPFIfControlReqResult, sleOSPFIfIndex, sleOSPFIfNetworkType
				 }
			STATUS current
			DESCRIPTION 
				"Description."
			::= { sleOSPFIfBaseNotification 2 }

		
		-- 1.3.6.1.4.1.6296.101.51.3.1.3.3
		sleOSPFIfMTUChanged NOTIFICATION-TYPE
			OBJECTS { sleOSPFIfControlRequest, sleOSPFIfControlTimeStamp, sleOSPFIfControlReqResult, sleOSPFIfIndex, sleOSFPIfMTU
				 }
			STATUS current
			DESCRIPTION 
				"Description."
			::= { sleOSPFIfBaseNotification 3 }

		
		-- 1.3.6.1.4.1.6296.101.51.3.1.3.4
		sleOSPFIfBFDChanged NOTIFICATION-TYPE
			OBJECTS { sleOSPFIfControlRequest, sleOSPFIfControlTimeStamp, sleOSPFIfControlReqResult, sleOSPFIfIndex, sleOSFPIfBFD
				 }
			STATUS current
			DESCRIPTION 
				"Description."
			::= { sleOSPFIfBaseNotification 4 }

		
		-- 1.3.6.1.4.1.6296.101.51.3.1.3.5
		sleOSPFIfEFMChanged NOTIFICATION-TYPE
			OBJECTS { sleOSPFIfControlRequest, sleOSPFIfControlTimeStamp, sleOSPFIfControlReqResult, sleOSPFIfIndex, sleOSFPIfEFM
				 }
			STATUS current
			DESCRIPTION 
				"Description."
			::= { sleOSPFIfBaseNotification 5 }

		
		-- 1.3.6.1.4.1.6296.101.51.3.2
		sleOSPFIfInfo OBJECT IDENTIFIER ::= { sleOSPFInterface 2 }

		
		-- 1.3.6.1.4.1.6296.101.51.3.2.1
		sleOSPFIfInfoTable OBJECT-TYPE
			SYNTAX SEQUENCE OF SleOSPFIfInfoEntry
			MAX-ACCESS not-accessible
			STATUS current
			DESCRIPTION
				"Description."
			::= { sleOSPFIfInfo 1 }

		
		-- 1.3.6.1.4.1.6296.101.51.3.2.1.1
		sleOSPFIfInfoEntry OBJECT-TYPE
			SYNTAX SleOSPFIfInfoEntry
			MAX-ACCESS not-accessible
			STATUS current
			DESCRIPTION
				"Description."
			INDEX { sleOSPFIfIndex, sleOSPFIfIpAddr }
			::= { sleOSPFIfInfoTable 1 }

		
		SleOSPFIfInfoEntry ::=
			SEQUENCE { 
				sleOSPFIfIpAddr
					IpAddress,
				sleOSPFIfCost
					INTEGER,
				sleOSPFIfTransmitDelay
					INTEGER,
				sleOSPFIfPriority
					INTEGER,
				sleOSPFIfHelloInterval
					INTEGER,
				sleOSPFIfDeadInterval
					INTEGER,
				sleOSPFIfRetransInterval
					INTEGER,
				sleOSPFIfAuth
					INTEGER,
				sleOSPFIfAuthType
					INTEGER,
				sleOSPFIfDataFilterOut
					INTEGER,
				sleOSPFIfMTUIgnore
					INTEGER,
				sleOSPFIfResync
					INTEGER,
				sleOSPFIfResyncTimeout
					INTEGER,
				sleOSPFIfAuthKeyFirst
					OCTET STRING,
				sleOSPFIfAuthKeyFirstAct
					INTEGER,
				sleOSPFIfAuthKeySecond
					OCTET STRING,
				sleOSPFIfAuthKeySecondAct
					INTEGER
			 }

		-- 1.3.6.1.4.1.6296.101.51.3.2.1.1.1
		sleOSPFIfIpAddr OBJECT-TYPE
			SYNTAX IpAddress
			MAX-ACCESS read-only
			STATUS current
			DESCRIPTION
				"Description."
			::= { sleOSPFIfInfoEntry 1 }

		
		-- 1.3.6.1.4.1.6296.101.51.3.2.1.1.2
		sleOSPFIfCost OBJECT-TYPE
			SYNTAX INTEGER (0..65535)
			MAX-ACCESS read-only
			STATUS current
			DESCRIPTION
				"Description."
			::= { sleOSPFIfInfoEntry 2 }

		
		-- 1.3.6.1.4.1.6296.101.51.3.2.1.1.3
		sleOSPFIfTransmitDelay OBJECT-TYPE
			SYNTAX INTEGER (0..65535)
			MAX-ACCESS read-only
			STATUS current
			DESCRIPTION
				"Description."
			::= { sleOSPFIfInfoEntry 3 }

		
		-- 1.3.6.1.4.1.6296.101.51.3.2.1.1.4
		sleOSPFIfPriority OBJECT-TYPE
			SYNTAX INTEGER (0..255)
			MAX-ACCESS read-only
			STATUS current
			DESCRIPTION
				"Description."
			::= { sleOSPFIfInfoEntry 4 }

		
		-- 1.3.6.1.4.1.6296.101.51.3.2.1.1.5
		sleOSPFIfHelloInterval OBJECT-TYPE
			SYNTAX INTEGER (0..65535)
			MAX-ACCESS read-only
			STATUS current
			DESCRIPTION
				"Description."
			::= { sleOSPFIfInfoEntry 5 }

		
		-- 1.3.6.1.4.1.6296.101.51.3.2.1.1.6
		sleOSPFIfDeadInterval OBJECT-TYPE
			SYNTAX INTEGER (0..65535)
			MAX-ACCESS read-only
			STATUS current
			DESCRIPTION
				"Description."
			::= { sleOSPFIfInfoEntry 6 }

		
		-- 1.3.6.1.4.1.6296.101.51.3.2.1.1.7
		sleOSPFIfRetransInterval OBJECT-TYPE
			SYNTAX INTEGER (0..65535)
			MAX-ACCESS read-only
			STATUS current
			DESCRIPTION
				"Description."
			::= { sleOSPFIfInfoEntry 7 }

		
		-- 1.3.6.1.4.1.6296.101.51.3.2.1.1.8
		sleOSPFIfAuth OBJECT-TYPE
			SYNTAX INTEGER
				{
				disable(0),
				enable(1)
				}
			MAX-ACCESS read-only
			STATUS current
			DESCRIPTION
				"Description."
			::= { sleOSPFIfInfoEntry 8 }

		
		-- 1.3.6.1.4.1.6296.101.51.3.2.1.1.9
		sleOSPFIfAuthType OBJECT-TYPE
			SYNTAX INTEGER
				{
				null(0),
				simple(1),
				crypt(2)
				}
			MAX-ACCESS read-only
			STATUS current
			DESCRIPTION
				"Description."
			::= { sleOSPFIfInfoEntry 9 }

		
		-- 1.3.6.1.4.1.6296.101.51.3.2.1.1.10
		sleOSPFIfDataFilterOut OBJECT-TYPE
			SYNTAX INTEGER
				{
				disable(0),
				enable(1)
				}
			MAX-ACCESS read-only
			STATUS current
			DESCRIPTION
				"Description."
			::= { sleOSPFIfInfoEntry 10 }

		
		-- 1.3.6.1.4.1.6296.101.51.3.2.1.1.11
		sleOSPFIfMTUIgnore OBJECT-TYPE
			SYNTAX INTEGER
				{
				disable(0),
				enable(1)
				}
			MAX-ACCESS read-only
			STATUS current
			DESCRIPTION
				"Description."
			::= { sleOSPFIfInfoEntry 11 }

		
		-- 1.3.6.1.4.1.6296.101.51.3.2.1.1.12
		sleOSPFIfResync OBJECT-TYPE
			SYNTAX INTEGER
				{
				disable(0),
				enable(1)
				}
			MAX-ACCESS read-only
			STATUS current
			DESCRIPTION
				"Description."
			::= { sleOSPFIfInfoEntry 12 }

		
		-- 1.3.6.1.4.1.6296.101.51.3.2.1.1.13
		sleOSPFIfResyncTimeout OBJECT-TYPE
			SYNTAX INTEGER (0..65535)
			MAX-ACCESS read-only
			STATUS current
			DESCRIPTION
				"Description."
			::= { sleOSPFIfInfoEntry 13 }

		
		-- 1.3.6.1.4.1.6296.101.51.3.2.1.1.14
		sleOSPFIfAuthKeyFirst OBJECT-TYPE
			SYNTAX OCTET STRING
			MAX-ACCESS read-only
			STATUS current
			DESCRIPTION
				"Description."
			::= { sleOSPFIfInfoEntry 14 }

		
		-- 1.3.6.1.4.1.6296.101.51.3.2.1.1.15
		sleOSPFIfAuthKeyFirstAct OBJECT-TYPE
			SYNTAX INTEGER
				{
				deactive(0),
				active(1)
				}
			MAX-ACCESS read-only
			STATUS current
			DESCRIPTION
				"Description."
			::= { sleOSPFIfInfoEntry 15 }

		
		-- 1.3.6.1.4.1.6296.101.51.3.2.1.1.16
		sleOSPFIfAuthKeySecond OBJECT-TYPE
			SYNTAX OCTET STRING
			MAX-ACCESS read-only
			STATUS current
			DESCRIPTION
				"Description."
			::= { sleOSPFIfInfoEntry 16 }

		
		-- 1.3.6.1.4.1.6296.101.51.3.2.1.1.17
		sleOSPFIfAuthKeySecondAct OBJECT-TYPE
			SYNTAX INTEGER
				{
				deactive(0),
				active(1)
				}
			MAX-ACCESS read-only
			STATUS current
			DESCRIPTION
				"Description."
			::= { sleOSPFIfInfoEntry 17 }

		
		-- 1.3.6.1.4.1.6296.101.51.3.2.2
		sleOSPFIfInfoControl OBJECT IDENTIFIER ::= { sleOSPFIfInfo 2 }

		
		-- 1.3.6.1.4.1.6296.101.51.3.2.2.1
		sleOSPFIfInfoControlRequest OBJECT-TYPE
			SYNTAX INTEGER
				{
				setOSPFIFCost(1),
				setOSPFIFPriority(2),
				setOSPFIFTransmitDelay(3),
				setOSPFIFHelloInterval(4),
				setOSPFIFDeadInterval(5),
				setOSPFIFRetransInterval(6),
				setOSPFIFAuthProfile(7),
				setOSPFIFDataFilterOut(8),
				setOSPFIFMtuIgnore(9),
				setOSPFIFResyncProfile(10),
				setOSPFIFAuthKeyFirstProfile(11),
				setOSPFIFAuthKeySecondProfile(12)
				}
			MAX-ACCESS read-write
			STATUS current
			DESCRIPTION
				"Description."
			::= { sleOSPFIfInfoControl 1 }

		
		-- 1.3.6.1.4.1.6296.101.51.3.2.2.2
		sleOSPFIfInfoControlStatus OBJECT-TYPE
			SYNTAX SleControlStatusType
			MAX-ACCESS read-only
			STATUS current
			DESCRIPTION
				"Description."
			::= { sleOSPFIfInfoControl 2 }

		
		-- 1.3.6.1.4.1.6296.101.51.3.2.2.3
		sleOSPFIfInfoControlTimer OBJECT-TYPE
			SYNTAX Gauge32
			MAX-ACCESS read-write
			STATUS current
			DESCRIPTION
				"Description."
			::= { sleOSPFIfInfoControl 3 }

		
		-- 1.3.6.1.4.1.6296.101.51.3.2.2.4
		sleOSPFIfInfoControlTimeStamp OBJECT-TYPE
			SYNTAX TimeTicks
			MAX-ACCESS read-only
			STATUS current
			DESCRIPTION
				"Description."
			::= { sleOSPFIfInfoControl 4 }

		
		-- 1.3.6.1.4.1.6296.101.51.3.2.2.5
		sleOSPFIfInfoControlReqResult OBJECT-TYPE
			SYNTAX SleControlRequestResultType
			MAX-ACCESS read-only
			STATUS current
			DESCRIPTION
				"Description."
			::= { sleOSPFIfInfoControl 5 }

		
		-- 1.3.6.1.4.1.6296.101.51.3.2.2.6
		sleOSPFIfInfoControlIndex OBJECT-TYPE
			SYNTAX INTEGER (0..65535)
			MAX-ACCESS read-write
			STATUS current
			DESCRIPTION
				"Description."
			::= { sleOSPFIfInfoControl 6 }

		
		-- 1.3.6.1.4.1.6296.101.51.3.2.2.7
		sleOSPFIfInfoControlIpAddr OBJECT-TYPE
			SYNTAX IpAddress
			MAX-ACCESS read-write
			STATUS current
			DESCRIPTION
				"Description."
			::= { sleOSPFIfInfoControl 7 }

		
		-- 1.3.6.1.4.1.6296.101.51.3.2.2.8
		sleOSPFIfInfoControlCost OBJECT-TYPE
			SYNTAX INTEGER (0..65535)
			MAX-ACCESS read-write
			STATUS current
			DESCRIPTION
				"Description."
			::= { sleOSPFIfInfoControl 8 }

		
		-- 1.3.6.1.4.1.6296.101.51.3.2.2.9
		sleOSPFIfInfoControlTransmitDelay OBJECT-TYPE
			SYNTAX INTEGER (0..65535)
			MAX-ACCESS read-write
			STATUS current
			DESCRIPTION
				"Description."
			::= { sleOSPFIfInfoControl 9 }

		
		-- 1.3.6.1.4.1.6296.101.51.3.2.2.10
		sleOSPFIfInfoControlPriority OBJECT-TYPE
			SYNTAX INTEGER (0..255)
			MAX-ACCESS read-write
			STATUS current
			DESCRIPTION
				"Description."
			::= { sleOSPFIfInfoControl 10 }

		
		-- 1.3.6.1.4.1.6296.101.51.3.2.2.11
		sleOSPFIfInfoControlHelloInterval OBJECT-TYPE
			SYNTAX INTEGER (0..65535)
			MAX-ACCESS read-write
			STATUS current
			DESCRIPTION
				"Description."
			::= { sleOSPFIfInfoControl 11 }

		
		-- 1.3.6.1.4.1.6296.101.51.3.2.2.12
		sleOSPFIfInfoControlDeadInterval OBJECT-TYPE
			SYNTAX INTEGER (0..65535)
			MAX-ACCESS read-write
			STATUS current
			DESCRIPTION
				"Description."
			::= { sleOSPFIfInfoControl 12 }

		
		-- 1.3.6.1.4.1.6296.101.51.3.2.2.13
		sleOSPFIfInfoControlRetransInterval OBJECT-TYPE
			SYNTAX INTEGER (0..65535)
			MAX-ACCESS read-write
			STATUS current
			DESCRIPTION
				"Description."
			::= { sleOSPFIfInfoControl 13 }

		
		-- 1.3.6.1.4.1.6296.101.51.3.2.2.14
		sleOSPFIfInfoControlAuth OBJECT-TYPE
			SYNTAX INTEGER
				{
				disable(0),
				enable(1)
				}
			MAX-ACCESS read-write
			STATUS current
			DESCRIPTION
				"Description."
			::= { sleOSPFIfInfoControl 14 }

		
		-- 1.3.6.1.4.1.6296.101.51.3.2.2.15
		sleOSPFIfInfoControlAuthType OBJECT-TYPE
			SYNTAX INTEGER
				{
				null(0),
				simple(1),
				crypt(2)
				}
			MAX-ACCESS read-write
			STATUS current
			DESCRIPTION
				"Description."
			::= { sleOSPFIfInfoControl 15 }

		
		-- 1.3.6.1.4.1.6296.101.51.3.2.2.16
		sleOSPFIfInfoControlDataFilterOut OBJECT-TYPE
			SYNTAX INTEGER
				{
				disable(0),
				enable(1)
				}
			MAX-ACCESS read-write
			STATUS current
			DESCRIPTION
				"Description."
			::= { sleOSPFIfInfoControl 16 }

		
		-- 1.3.6.1.4.1.6296.101.51.3.2.2.17
		sleOSPFIfInfoControlMTUIgnore OBJECT-TYPE
			SYNTAX INTEGER
				{
				disable(0),
				enable(1)
				}
			MAX-ACCESS read-write
			STATUS current
			DESCRIPTION
				"Description."
			::= { sleOSPFIfInfoControl 17 }

		
		-- 1.3.6.1.4.1.6296.101.51.3.2.2.18
		sleOSPFIfInfoControlResync OBJECT-TYPE
			SYNTAX INTEGER
				{
				disable(0),
				enable(1)
				}
			MAX-ACCESS read-write
			STATUS current
			DESCRIPTION
				"Description."
			::= { sleOSPFIfInfoControl 18 }

		
		-- 1.3.6.1.4.1.6296.101.51.3.2.2.19
		sleOSPFIfInfoControlResyncTimeout OBJECT-TYPE
			SYNTAX INTEGER (0..65535)
			MAX-ACCESS read-write
			STATUS current
			DESCRIPTION
				"Description."
			::= { sleOSPFIfInfoControl 19 }

		
		-- 1.3.6.1.4.1.6296.101.51.3.2.2.20
		sleOSPFIfInfoControlAuthKeyFirst OBJECT-TYPE
			SYNTAX OCTET STRING
			MAX-ACCESS read-write
			STATUS current
			DESCRIPTION
				"Description."
			::= { sleOSPFIfInfoControl 20 }

		
		-- 1.3.6.1.4.1.6296.101.51.3.2.2.21
		sleOSPFIfInfoControlAuthKeyFirstAct OBJECT-TYPE
			SYNTAX INTEGER
				{
				deactive(0),
				active(1)
				}
			MAX-ACCESS read-write
			STATUS current
			DESCRIPTION
				"Description."
			::= { sleOSPFIfInfoControl 21 }

		
		-- 1.3.6.1.4.1.6296.101.51.3.2.2.22
		sleOSPFIfInfoControlAuthKeySecond OBJECT-TYPE
			SYNTAX OCTET STRING
			MAX-ACCESS read-write
			STATUS current
			DESCRIPTION
				"Description."
			::= { sleOSPFIfInfoControl 22 }

		
		-- 1.3.6.1.4.1.6296.101.51.3.2.2.23
		sleOSPFIfInfoControlAuthKeySecondAct OBJECT-TYPE
			SYNTAX INTEGER
				{
				deactive(0),
				active(1)
				}
			MAX-ACCESS read-write
			STATUS current
			DESCRIPTION
				"Description."
			::= { sleOSPFIfInfoControl 23 }

		
		-- 1.3.6.1.4.1.6296.101.51.3.2.3
		sleOSPFIfInfoNotification OBJECT IDENTIFIER ::= { sleOSPFIfInfo 3 }

		
		-- 1.3.6.1.4.1.6296.101.51.3.2.3.1
		sleOSPFIfCostChanged NOTIFICATION-TYPE
			OBJECTS { sleOSPFIfInfoControlRequest, sleOSPFIfInfoControlTimeStamp, sleOSPFIfInfoControlReqResult, sleOSPFIfIndex, sleOSPFIfIpAddr, 
				sleOSPFIfCost }
			STATUS current
			DESCRIPTION 
				"Description."
			::= { sleOSPFIfInfoNotification 1 }

		
		-- 1.3.6.1.4.1.6296.101.51.3.2.3.2
		sleOSPFIfPriorityChanged NOTIFICATION-TYPE
			OBJECTS { sleOSPFIfInfoControlRequest, sleOSPFIfInfoControlTimeStamp, sleOSPFIfInfoControlReqResult, sleOSPFIfIndex, sleOSPFIfIpAddr, 
				sleOSPFIfPriority }
			STATUS current
			DESCRIPTION 
				"Description."
			::= { sleOSPFIfInfoNotification 2 }

		
		-- 1.3.6.1.4.1.6296.101.51.3.2.3.3
		sleOSPFIfTransmitDelayChanged NOTIFICATION-TYPE
			OBJECTS { sleOSPFIfInfoControlRequest, sleOSPFIfInfoControlTimeStamp, sleOSPFIfInfoControlReqResult, sleOSPFIfIndex, sleOSPFIfIpAddr, 
				sleOSPFIfTransmitDelay }
			STATUS current
			DESCRIPTION 
				"Description."
			::= { sleOSPFIfInfoNotification 3 }

		
		-- 1.3.6.1.4.1.6296.101.51.3.2.3.4
		sleOSPFIfHelloIntervalChanged NOTIFICATION-TYPE
			OBJECTS { sleOSPFIfInfoControlRequest, sleOSPFIfInfoControlTimeStamp, sleOSPFIfInfoControlReqResult, sleOSPFIfIndex, sleOSPFIfIpAddr, 
				sleOSPFIfHelloInterval }
			STATUS current
			DESCRIPTION 
				"Description."
			::= { sleOSPFIfInfoNotification 4 }

		
		-- 1.3.6.1.4.1.6296.101.51.3.2.3.5
		sleOSPFIfDeadIntervalChanged NOTIFICATION-TYPE
			OBJECTS { sleOSPFIfInfoControlRequest, sleOSPFIfInfoControlTimeStamp, sleOSPFIfInfoControlReqResult, sleOSPFIfIndex, sleOSPFIfIpAddr, 
				sleOSPFIfDeadInterval }
			STATUS current
			DESCRIPTION 
				"Description."
			::= { sleOSPFIfInfoNotification 5 }

		
		-- 1.3.6.1.4.1.6296.101.51.3.2.3.6
		sleOSPFIfRetransIntervalChanged NOTIFICATION-TYPE
			OBJECTS { sleOSPFIfInfoControlRequest, sleOSPFIfInfoControlTimeStamp, sleOSPFIfInfoControlReqResult, sleOSPFIfIndex, sleOSPFIfIpAddr, 
				sleOSPFIfRetransInterval }
			STATUS current
			DESCRIPTION 
				"Description."
			::= { sleOSPFIfInfoNotification 6 }

		
		-- 1.3.6.1.4.1.6296.101.51.3.2.3.7
		sleOSPFIfAuthProfileChanged NOTIFICATION-TYPE
			OBJECTS { sleOSPFIfInfoControlRequest, sleOSPFIfInfoControlTimeStamp, sleOSPFIfInfoControlReqResult, sleOSPFIfIndex, sleOSPFIfIpAddr, 
				sleOSPFIfAuth, sleOSPFIfAuthType }
			STATUS current
			DESCRIPTION 
				"Description."
			::= { sleOSPFIfInfoNotification 7 }

		
		-- 1.3.6.1.4.1.6296.101.51.3.2.3.8
		sleOSPFIfDatafilterOutChanged NOTIFICATION-TYPE
			OBJECTS { sleOSPFIfInfoControlRequest, sleOSPFIfInfoControlTimeStamp, sleOSPFIfInfoControlReqResult, sleOSPFIfIndex, sleOSPFIfIpAddr, 
				sleOSPFIfDataFilterOut }
			STATUS current
			DESCRIPTION 
				"Description."
			::= { sleOSPFIfInfoNotification 8 }

		
		-- 1.3.6.1.4.1.6296.101.51.3.2.3.9
		sleOSPFIfMTUIgnoreChanged NOTIFICATION-TYPE
			OBJECTS { sleOSPFIfInfoControlRequest, sleOSPFIfInfoControlTimeStamp, sleOSPFIfInfoControlReqResult, sleOSPFIfIndex, sleOSPFIfIpAddr, 
				sleOSPFIfMTUIgnore }
			STATUS current
			DESCRIPTION 
				"Description."
			::= { sleOSPFIfInfoNotification 9 }

		
		-- 1.3.6.1.4.1.6296.101.51.3.2.3.10
		sleOSPFIfResyncProfileChanged NOTIFICATION-TYPE
			OBJECTS { sleOSPFIfInfoControlRequest, sleOSPFIfInfoControlTimeStamp, sleOSPFIfInfoControlReqResult, sleOSPFIfIndex, sleOSPFIfIpAddr, 
				sleOSPFIfResync, sleOSPFIfResyncTimeout }
			STATUS current
			DESCRIPTION 
				"Description."
			::= { sleOSPFIfInfoNotification 10 }

		
		-- 1.3.6.1.4.1.6296.101.51.3.2.3.11
		sleOSPFIfAuthKeyFirstProfileChanged NOTIFICATION-TYPE
			OBJECTS { sleOSPFIfInfoControlRequest, sleOSPFIfInfoControlTimeStamp, sleOSPFIfInfoControlReqResult, sleOSPFIfIndex, sleOSPFIfIpAddr, 
				sleOSPFIfAuthKeyFirst, sleOSPFIfAuthKeyFirstAct }
			STATUS current
			DESCRIPTION 
				"Description."
			::= { sleOSPFIfInfoNotification 11 }

		
		-- 1.3.6.1.4.1.6296.101.51.3.2.3.12
		sleOSPFIfAuthKeyProfileSecondChanged NOTIFICATION-TYPE
			OBJECTS { sleOSPFIfInfoControlRequest, sleOSPFIfInfoControlTimeStamp, sleOSPFIfInfoControlReqResult, sleOSPFIfIndex, sleOSPFIfIpAddr, 
				sleOSPFIfAuthKeySecond, sleOSPFIfAuthKeySecondAct }
			STATUS current
			DESCRIPTION 
				"Description."
			::= { sleOSPFIfInfoNotification 12 }

		
		-- 1.3.6.1.4.1.6296.101.51.3.3
		sleOSPFIfMsgKey OBJECT IDENTIFIER ::= { sleOSPFInterface 3 }

		
		-- 1.3.6.1.4.1.6296.101.51.3.3.1
		sleOSPFIfMsgKeyTable OBJECT-TYPE
			SYNTAX SEQUENCE OF SleOSPFIfMsgKeyEntry
			MAX-ACCESS not-accessible
			STATUS current
			DESCRIPTION
				"Description."
			::= { sleOSPFIfMsgKey 1 }

		
		-- 1.3.6.1.4.1.6296.101.51.3.3.1.1
		sleOSPFIfMsgKeyEntry OBJECT-TYPE
			SYNTAX SleOSPFIfMsgKeyEntry
			MAX-ACCESS not-accessible
			STATUS current
			DESCRIPTION
				"Description."
			INDEX { sleOSPFIfIndex, sleOSPFIfIpAddr, sleOSPFIfMsgKeyID }
			::= { sleOSPFIfMsgKeyTable 1 }

		
		SleOSPFIfMsgKeyEntry ::=
			SEQUENCE { 
				sleOSPFIfMsgKeyID
					Integer32,
				sleOSPFIfMsgKeyVal
					OCTET STRING,
				sleOSPFIfMsgKeyAct
					INTEGER
			 }

		-- 1.3.6.1.4.1.6296.101.51.3.3.1.1.1
		sleOSPFIfMsgKeyID OBJECT-TYPE
			SYNTAX Integer32 (0..255)
			MAX-ACCESS read-only
			STATUS current
			DESCRIPTION
				"Description."
			::= { sleOSPFIfMsgKeyEntry 1 }

		
		-- 1.3.6.1.4.1.6296.101.51.3.3.1.1.2
		sleOSPFIfMsgKeyVal OBJECT-TYPE
			SYNTAX OCTET STRING
			MAX-ACCESS read-only
			STATUS current
			DESCRIPTION
				"Description."
			::= { sleOSPFIfMsgKeyEntry 2 }

		
		-- 1.3.6.1.4.1.6296.101.51.3.3.1.1.3
		sleOSPFIfMsgKeyAct OBJECT-TYPE
			SYNTAX INTEGER
				{
				deactive(0),
				active(1)
				}
			MAX-ACCESS read-only
			STATUS current
			DESCRIPTION
				"Description."
			::= { sleOSPFIfMsgKeyEntry 3 }

		
		-- 1.3.6.1.4.1.6296.101.51.3.3.2
		sleOSPFIfMsgKeyControl OBJECT IDENTIFIER ::= { sleOSPFIfMsgKey 2 }

		
		-- 1.3.6.1.4.1.6296.101.51.3.3.2.1
		sleOSPFIfMsgKeyControlRequest OBJECT-TYPE
			SYNTAX INTEGER
				{
				createMsgDigestKey(1),
				deleteMsgDigestKey(2)
				}
			MAX-ACCESS read-write
			STATUS current
			DESCRIPTION
				"Description."
			::= { sleOSPFIfMsgKeyControl 1 }

		
		-- 1.3.6.1.4.1.6296.101.51.3.3.2.2
		sleOSPFIfMsgKeyControlStatus OBJECT-TYPE
			SYNTAX SleControlStatusType
			MAX-ACCESS read-only
			STATUS current
			DESCRIPTION
				"Description."
			::= { sleOSPFIfMsgKeyControl 2 }

		
		-- 1.3.6.1.4.1.6296.101.51.3.3.2.3
		sleOSPFIfMsgKeyControlTimer OBJECT-TYPE
			SYNTAX Gauge32
			MAX-ACCESS read-write
			STATUS current
			DESCRIPTION
				"Description."
			::= { sleOSPFIfMsgKeyControl 3 }

		
		-- 1.3.6.1.4.1.6296.101.51.3.3.2.4
		sleOSPFIfMsgKeyControlTimeStamp OBJECT-TYPE
			SYNTAX TimeTicks
			MAX-ACCESS read-only
			STATUS current
			DESCRIPTION
				"Description."
			::= { sleOSPFIfMsgKeyControl 4 }

		
		-- 1.3.6.1.4.1.6296.101.51.3.3.2.5
		sleOSPFIfMsgKeyControlReqResult OBJECT-TYPE
			SYNTAX SleControlRequestResultType
			MAX-ACCESS read-only
			STATUS current
			DESCRIPTION
				"Description."
			::= { sleOSPFIfMsgKeyControl 5 }

		
		-- 1.3.6.1.4.1.6296.101.51.3.3.2.6
		sleOSPFIfMsgKeyControlIndex OBJECT-TYPE
			SYNTAX INTEGER (0..65535)
			MAX-ACCESS read-write
			STATUS current
			DESCRIPTION
				"Description."
			::= { sleOSPFIfMsgKeyControl 6 }

		
		-- 1.3.6.1.4.1.6296.101.51.3.3.2.7
		sleOSPFIfMsgKeyControlIpAddr OBJECT-TYPE
			SYNTAX IpAddress
			MAX-ACCESS read-write
			STATUS current
			DESCRIPTION
				"Description."
			::= { sleOSPFIfMsgKeyControl 7 }

		
		-- 1.3.6.1.4.1.6296.101.51.3.3.2.8
		sleOSPFIfMsgKeyControlKeyID OBJECT-TYPE
			SYNTAX INTEGER (0..255)
			MAX-ACCESS read-write
			STATUS current
			DESCRIPTION
				"Description."
			::= { sleOSPFIfMsgKeyControl 8 }

		
		-- 1.3.6.1.4.1.6296.101.51.3.3.2.9
		sleOSPFIfMsgKeyControlKeyVal OBJECT-TYPE
			SYNTAX OCTET STRING
			MAX-ACCESS read-write
			STATUS current
			DESCRIPTION
				"Description."
			::= { sleOSPFIfMsgKeyControl 9 }

		
		-- 1.3.6.1.4.1.6296.101.51.3.3.2.10
		sleOSPFIfMsgKeyControlKeyAct OBJECT-TYPE
			SYNTAX INTEGER
				{
				deactive(0),
				active(1)
				}
			MAX-ACCESS read-write
			STATUS current
			DESCRIPTION
				"Description."
			::= { sleOSPFIfMsgKeyControl 10 }

		
		-- 1.3.6.1.4.1.6296.101.51.3.3.3
		sleOSPFIfMsgKeyNotification OBJECT IDENTIFIER ::= { sleOSPFIfMsgKey 3 }

		
		-- 1.3.6.1.4.1.6296.101.51.3.3.3.1
		sleOSPFIfMsgKeyCreated NOTIFICATION-TYPE
			OBJECTS { sleOSPFIfInfoControlRequest, sleOSPFIfInfoControlTimeStamp, sleOSPFIfInfoControlReqResult, sleOSPFIfIndex, sleOSPFIfIpAddr, 
				sleOSPFIfMsgKeyID, sleOSPFIfMsgKeyVal, sleOSPFIfMsgKeyAct }
			STATUS current
			DESCRIPTION 
				"Description."
			::= { sleOSPFIfMsgKeyNotification 1 }

		
		-- 1.3.6.1.4.1.6296.101.51.3.3.3.2
		sleOSPFIfMsgKeyDeleted NOTIFICATION-TYPE
			OBJECTS { sleOSPFIfInfoControlRequest, sleOSPFIfInfoControlTimeStamp, sleOSPFIfInfoControlReqResult, sleOSPFIfIndex, sleOSPFIfIpAddr, 
				sleOSPFIfMsgKeyControlKeyID }
			STATUS current
			DESCRIPTION 
				"Description."
			::= { sleOSPFIfMsgKeyNotification 2 }

		
		-- 1.3.6.1.4.1.6296.101.51.3.4
		sleOSPFIfStatus OBJECT IDENTIFIER ::= { sleOSPFInterface 4 }

		
		-- 1.3.6.1.4.1.6296.101.51.3.4.1
		sleOSPFIfStatusTable OBJECT-TYPE
			SYNTAX SEQUENCE OF SleOSPFIfStatusEntry
			MAX-ACCESS not-accessible
			STATUS current
			DESCRIPTION
				"Description."
			::= { sleOSPFIfStatus 1 }

		
		-- 1.3.6.1.4.1.6296.101.51.3.4.1.1
		sleOSPFIfStatusEntry OBJECT-TYPE
			SYNTAX SleOSPFIfStatusEntry
			MAX-ACCESS not-accessible
			STATUS current
			DESCRIPTION
				"Description."
			INDEX { sleOSPFIfIndex, sleOSPFIfIpAddr }
			::= { sleOSPFIfStatusTable 1 }

		
		SleOSPFIfStatusEntry ::=
			SEQUENCE { 
				sleOSPFIfStatusAddr
					IpAddress,
				sleOSPFIfStatusUpState
					INTEGER,
				sleOSPFIfStatusAreaID
					IpAddress,
				sleOSPFIfStatusProcID
					INTEGER,
				sleOSPFIfStatusRouterID
					IpAddress,
				sleOSPFIfStatusNetworkType
					INTEGER,
				sleOSPFIfStatusCost
					INTEGER,
				sleOSPFIfStatusTransmitDelay
					INTEGER,
				sleOSPFIfStatusState
					INTEGER,
				sleOSPFIfStatusPriorityUse
					INTEGER,
				sleOSPFIfStatusPriority
					INTEGER,
				sleOSPFIfStatusDRRouterUse
					INTEGER,
				sleOSPFIfStatusDRRouterID
					IpAddress,
				sleOSPFIfStatusDRIfIpAddr
					IpAddress,
				sleOSPFIfStatusBDRRouterUse
					INTEGER,
				sleOSPFIfStatusBDRRouterID
					IpAddress,
				sleOSPFIfStatusBDRIfIpAddr
					IpAddress,
				sleOSPFIfStatusHelloInterval
					INTEGER,
				sleOSPFIfStatusDeadInterval
					INTEGER,
				sleOSPFIfStatusRetransInterval
					INTEGER,
				sleOSPFIfStatusWaitInterval
					INTEGER,
				sleOSPFIfStatusNeighborCount
					INTEGER,
				sleOSPFIfCryptSeqNum
					Gauge32,
				sleOSPFIfStatusRcvHello
					Gauge32,
				sleOSPFIfStatusSendHello
					Gauge32,
				sleOSPFIfStatusRcvDD
					Gauge32,
				sleOSPFIfStatusSendDD
					Gauge32,
				sleOSPFIfStatusRcvLSReq
					Gauge32,
				sleOSPFIfStatusSendLSReq
					Gauge32,
				sleOSPFIfStatusRcvLSUpd
					Gauge32,
				sleOSPFIfStatusSendLSUpd
					Gauge32,
				sleOSPFIfStatusRcvLSAck
					Gauge32,
				sleOSPFIfStatusSendLSAck
					Gauge32,
				sleOSPFIfStatusDiscarded
					Gauge32,
				sleOSPFIfStatusMtu
					Integer32
			 }

		-- 1.3.6.1.4.1.6296.101.51.3.4.1.1.1
		sleOSPFIfStatusAddr OBJECT-TYPE
			SYNTAX IpAddress
			MAX-ACCESS read-only
			STATUS current
			DESCRIPTION
				"Description."
			::= { sleOSPFIfStatusEntry 1 }

		
		-- 1.3.6.1.4.1.6296.101.51.3.4.1.1.2
		sleOSPFIfStatusUpState OBJECT-TYPE
			SYNTAX INTEGER
				{
				down(0),
				up(1)
				}
			MAX-ACCESS read-only
			STATUS current
			DESCRIPTION
				"Description."
			::= { sleOSPFIfStatusEntry 2 }

		
		-- 1.3.6.1.4.1.6296.101.51.3.4.1.1.3
		sleOSPFIfStatusAreaID OBJECT-TYPE
			SYNTAX IpAddress
			MAX-ACCESS read-only
			STATUS current
			DESCRIPTION
				"Description."
			::= { sleOSPFIfStatusEntry 3 }

		
		-- 1.3.6.1.4.1.6296.101.51.3.4.1.1.4
		sleOSPFIfStatusProcID OBJECT-TYPE
			SYNTAX INTEGER (0..65535)
			MAX-ACCESS read-only
			STATUS current
			DESCRIPTION
				"Description."
			::= { sleOSPFIfStatusEntry 4 }

		
		-- 1.3.6.1.4.1.6296.101.51.3.4.1.1.5
		sleOSPFIfStatusRouterID OBJECT-TYPE
			SYNTAX IpAddress
			MAX-ACCESS read-only
			STATUS current
			DESCRIPTION
				"Description."
			::= { sleOSPFIfStatusEntry 5 }

		
		-- 1.3.6.1.4.1.6296.101.51.3.4.1.1.6
		sleOSPFIfStatusNetworkType OBJECT-TYPE
			SYNTAX INTEGER
				{
				none(0),
				pointTopoint(1),
				broadcast(2),
				nbma(3),
				pointTomultipoint(4),
				poiintTomultipointnbma(5),
				virtuallink(6),
				loopback(7)
				}
			MAX-ACCESS read-only
			STATUS current
			DESCRIPTION
				"Description."
			::= { sleOSPFIfStatusEntry 6 }

		
		-- 1.3.6.1.4.1.6296.101.51.3.4.1.1.7
		sleOSPFIfStatusCost OBJECT-TYPE
			SYNTAX INTEGER (0..65535)
			MAX-ACCESS read-only
			STATUS current
			DESCRIPTION
				"Description."
			::= { sleOSPFIfStatusEntry 7 }

		
		-- 1.3.6.1.4.1.6296.101.51.3.4.1.1.8
		sleOSPFIfStatusTransmitDelay OBJECT-TYPE
			SYNTAX INTEGER (0..65535)
			MAX-ACCESS read-only
			STATUS current
			DESCRIPTION
				"Description."
			::= { sleOSPFIfStatusEntry 8 }

		
		-- 1.3.6.1.4.1.6296.101.51.3.4.1.1.9
		sleOSPFIfStatusState OBJECT-TYPE
			SYNTAX INTEGER
				{
				dependUpon(0),
				down(1),
				loopback(2),
				waiting(3),
				pointTopoint(4),
				drother(5),
				backup(6),
				dr(7)
				}
			MAX-ACCESS read-only
			STATUS current
			DESCRIPTION
				"Description."
			::= { sleOSPFIfStatusEntry 9 }

		
		-- 1.3.6.1.4.1.6296.101.51.3.4.1.1.10
		sleOSPFIfStatusPriorityUse OBJECT-TYPE
			SYNTAX INTEGER
				{
				nouse(0),
				use(1)
				}
			MAX-ACCESS read-only
			STATUS current
			DESCRIPTION
				"Description."
			::= { sleOSPFIfStatusEntry 10 }

		
		-- 1.3.6.1.4.1.6296.101.51.3.4.1.1.11
		sleOSPFIfStatusPriority OBJECT-TYPE
			SYNTAX INTEGER (0..255)
			MAX-ACCESS read-only
			STATUS current
			DESCRIPTION
				"Description."
			::= { sleOSPFIfStatusEntry 11 }

		
		-- 1.3.6.1.4.1.6296.101.51.3.4.1.1.12
		sleOSPFIfStatusDRRouterUse OBJECT-TYPE
			SYNTAX INTEGER
				{
				nouse(0),
				use(1)
				}
			MAX-ACCESS read-only
			STATUS current
			DESCRIPTION
				"Description."
			::= { sleOSPFIfStatusEntry 12 }

		
		-- 1.3.6.1.4.1.6296.101.51.3.4.1.1.13
		sleOSPFIfStatusDRRouterID OBJECT-TYPE
			SYNTAX IpAddress
			MAX-ACCESS read-only
			STATUS current
			DESCRIPTION
				"Description."
			::= { sleOSPFIfStatusEntry 13 }

		
		-- 1.3.6.1.4.1.6296.101.51.3.4.1.1.14
		sleOSPFIfStatusDRIfIpAddr OBJECT-TYPE
			SYNTAX IpAddress
			MAX-ACCESS read-only
			STATUS current
			DESCRIPTION
				"Description."
			::= { sleOSPFIfStatusEntry 14 }

		
		-- 1.3.6.1.4.1.6296.101.51.3.4.1.1.15
		sleOSPFIfStatusBDRRouterUse OBJECT-TYPE
			SYNTAX INTEGER
				{
				nouse(0),
				use(1)
				}
			MAX-ACCESS read-only
			STATUS current
			DESCRIPTION
				"Description."
			::= { sleOSPFIfStatusEntry 15 }

		
		-- 1.3.6.1.4.1.6296.101.51.3.4.1.1.16
		sleOSPFIfStatusBDRRouterID OBJECT-TYPE
			SYNTAX IpAddress
			MAX-ACCESS read-only
			STATUS current
			DESCRIPTION
				"Description."
			::= { sleOSPFIfStatusEntry 16 }

		
		-- 1.3.6.1.4.1.6296.101.51.3.4.1.1.17
		sleOSPFIfStatusBDRIfIpAddr OBJECT-TYPE
			SYNTAX IpAddress
			MAX-ACCESS read-only
			STATUS current
			DESCRIPTION
				"Description."
			::= { sleOSPFIfStatusEntry 17 }

		
		-- 1.3.6.1.4.1.6296.101.51.3.4.1.1.18
		sleOSPFIfStatusHelloInterval OBJECT-TYPE
			SYNTAX INTEGER (0..65535)
			MAX-ACCESS read-only
			STATUS current
			DESCRIPTION
				"Description."
			::= { sleOSPFIfStatusEntry 18 }

		
		-- 1.3.6.1.4.1.6296.101.51.3.4.1.1.19
		sleOSPFIfStatusDeadInterval OBJECT-TYPE
			SYNTAX INTEGER (0..65535)
			MAX-ACCESS read-only
			STATUS current
			DESCRIPTION
				"Description."
			::= { sleOSPFIfStatusEntry 19 }

		
		-- 1.3.6.1.4.1.6296.101.51.3.4.1.1.20
		sleOSPFIfStatusRetransInterval OBJECT-TYPE
			SYNTAX INTEGER (0..65535)
			MAX-ACCESS read-only
			STATUS current
			DESCRIPTION
				"Description."
			::= { sleOSPFIfStatusEntry 20 }

		
		-- 1.3.6.1.4.1.6296.101.51.3.4.1.1.21
		sleOSPFIfStatusWaitInterval OBJECT-TYPE
			SYNTAX INTEGER (0..65535)
			MAX-ACCESS read-only
			STATUS current
			DESCRIPTION
				"Description."
			::= { sleOSPFIfStatusEntry 21 }

		
		-- 1.3.6.1.4.1.6296.101.51.3.4.1.1.22
		sleOSPFIfStatusNeighborCount OBJECT-TYPE
			SYNTAX INTEGER
			MAX-ACCESS read-only
			STATUS current
			DESCRIPTION
				"Description."
			::= { sleOSPFIfStatusEntry 22 }

		
		-- 1.3.6.1.4.1.6296.101.51.3.4.1.1.23
		sleOSPFIfCryptSeqNum OBJECT-TYPE
			SYNTAX Gauge32
			MAX-ACCESS read-only
			STATUS current
			DESCRIPTION
				"Description."
			::= { sleOSPFIfStatusEntry 23 }

		
		-- 1.3.6.1.4.1.6296.101.51.3.4.1.1.24
		sleOSPFIfStatusRcvHello OBJECT-TYPE
			SYNTAX Gauge32
			MAX-ACCESS read-only
			STATUS current
			DESCRIPTION
				"Description."
			::= { sleOSPFIfStatusEntry 24 }

		
		-- 1.3.6.1.4.1.6296.101.51.3.4.1.1.25
		sleOSPFIfStatusSendHello OBJECT-TYPE
			SYNTAX Gauge32
			MAX-ACCESS read-only
			STATUS current
			DESCRIPTION
				"Description."
			::= { sleOSPFIfStatusEntry 25 }

		
		-- 1.3.6.1.4.1.6296.101.51.3.4.1.1.26
		sleOSPFIfStatusRcvDD OBJECT-TYPE
			SYNTAX Gauge32
			MAX-ACCESS read-only
			STATUS current
			DESCRIPTION
				"Description."
			::= { sleOSPFIfStatusEntry 26 }

		
		-- 1.3.6.1.4.1.6296.101.51.3.4.1.1.27
		sleOSPFIfStatusSendDD OBJECT-TYPE
			SYNTAX Gauge32
			MAX-ACCESS read-only
			STATUS current
			DESCRIPTION
				"Description."
			::= { sleOSPFIfStatusEntry 27 }

		
		-- 1.3.6.1.4.1.6296.101.51.3.4.1.1.28
		sleOSPFIfStatusRcvLSReq OBJECT-TYPE
			SYNTAX Gauge32
			MAX-ACCESS read-only
			STATUS current
			DESCRIPTION
				"Description."
			::= { sleOSPFIfStatusEntry 28 }

		
		-- 1.3.6.1.4.1.6296.101.51.3.4.1.1.29
		sleOSPFIfStatusSendLSReq OBJECT-TYPE
			SYNTAX Gauge32
			MAX-ACCESS read-only
			STATUS current
			DESCRIPTION
				"Description."
			::= { sleOSPFIfStatusEntry 29 }

		
		-- 1.3.6.1.4.1.6296.101.51.3.4.1.1.30
		sleOSPFIfStatusRcvLSUpd OBJECT-TYPE
			SYNTAX Gauge32
			MAX-ACCESS read-only
			STATUS current
			DESCRIPTION
				"Description."
			::= { sleOSPFIfStatusEntry 30 }

		
		-- 1.3.6.1.4.1.6296.101.51.3.4.1.1.31
		sleOSPFIfStatusSendLSUpd OBJECT-TYPE
			SYNTAX Gauge32
			MAX-ACCESS read-only
			STATUS current
			DESCRIPTION
				"Description."
			::= { sleOSPFIfStatusEntry 31 }

		
		-- 1.3.6.1.4.1.6296.101.51.3.4.1.1.32
		sleOSPFIfStatusRcvLSAck OBJECT-TYPE
			SYNTAX Gauge32
			MAX-ACCESS read-only
			STATUS current
			DESCRIPTION
				"Description."
			::= { sleOSPFIfStatusEntry 32 }

		
		-- 1.3.6.1.4.1.6296.101.51.3.4.1.1.33
		sleOSPFIfStatusSendLSAck OBJECT-TYPE
			SYNTAX Gauge32
			MAX-ACCESS read-only
			STATUS current
			DESCRIPTION
				"Description."
			::= { sleOSPFIfStatusEntry 33 }

		
		-- 1.3.6.1.4.1.6296.101.51.3.4.1.1.34
		sleOSPFIfStatusDiscarded OBJECT-TYPE
			SYNTAX Gauge32
			MAX-ACCESS read-only
			STATUS current
			DESCRIPTION
				"Description."
			::= { sleOSPFIfStatusEntry 34 }

		
		-- 1.3.6.1.4.1.6296.101.51.3.4.1.1.35
		sleOSPFIfStatusMtu OBJECT-TYPE
			SYNTAX Integer32
			MAX-ACCESS read-only
			STATUS current
			DESCRIPTION
				"The MTU of OSPF interface."
			::= { sleOSPFIfStatusEntry 35 }

		
		-- 1.3.6.1.4.1.6296.101.51.4
		sleOSPFLsa OBJECT IDENTIFIER ::= { sleOspf 4 }

		
		-- 1.3.6.1.4.1.6296.101.51.4.1
		sleOSPFLsaTable OBJECT-TYPE
			SYNTAX SEQUENCE OF SleOSPFLsaEntry
			MAX-ACCESS not-accessible
			STATUS current
			DESCRIPTION
				"Description."
			::= { sleOSPFLsa 1 }

		
		-- 1.3.6.1.4.1.6296.101.51.4.1.1
		sleOSPFLsaEntry OBJECT-TYPE
			SYNTAX SleOSPFLsaEntry
			MAX-ACCESS not-accessible
			STATUS current
			DESCRIPTION
				"Description."
			INDEX { sleOSPFProcID, sleOSPFLsaType, sleOSPFLsaAreaID, sleOSPFLsaLinkID, sleOSPFLsaAdvRouter
				 }
			::= { sleOSPFLsaTable 1 }

		
		SleOSPFLsaEntry ::=
			SEQUENCE { 
				sleOSPFLsaType
					INTEGER,
				sleOSPFLsaAreaID
					IpAddress,
				sleOSPFLsaLinkID
					IpAddress,
				sleOSPFLsaAdvRouter
					IpAddress,
				sleOSPFLsaAge
					INTEGER,
				sleOSPFLsaSequence
					Gauge32
			 }

		-- 1.3.6.1.4.1.6296.101.51.4.1.1.1
		sleOSPFLsaType OBJECT-TYPE
			SYNTAX INTEGER
				{
				unknown(1),
				routerLsa(2),
				networkLsa(3),
				summaryLsa(4),
				summaryLsaAsbr(5),
				asExternalLsa(6),
				groupMemberLsa(7),
				asNssaLsa(8),
				externalAttributeLsa(9),
				linkOpaqueLsa(10),
				areaOpaqueLsa(11),
				asOpaqueLsa(12)
				}
			MAX-ACCESS read-only
			STATUS current
			DESCRIPTION
				"Description."
			::= { sleOSPFLsaEntry 1 }

		
		-- 1.3.6.1.4.1.6296.101.51.4.1.1.2
		sleOSPFLsaAreaID OBJECT-TYPE
			SYNTAX IpAddress
			MAX-ACCESS read-only
			STATUS current
			DESCRIPTION
				"Description."
			::= { sleOSPFLsaEntry 2 }

		
		-- 1.3.6.1.4.1.6296.101.51.4.1.1.3
		sleOSPFLsaLinkID OBJECT-TYPE
			SYNTAX IpAddress
			MAX-ACCESS read-only
			STATUS current
			DESCRIPTION
				"Description."
			::= { sleOSPFLsaEntry 3 }

		
		-- 1.3.6.1.4.1.6296.101.51.4.1.1.4
		sleOSPFLsaAdvRouter OBJECT-TYPE
			SYNTAX IpAddress
			MAX-ACCESS read-only
			STATUS current
			DESCRIPTION
				"Description."
			::= { sleOSPFLsaEntry 4 }

		
		-- 1.3.6.1.4.1.6296.101.51.4.1.1.5
		sleOSPFLsaAge OBJECT-TYPE
			SYNTAX INTEGER
			MAX-ACCESS read-only
			STATUS current
			DESCRIPTION
				"Description."
			::= { sleOSPFLsaEntry 5 }

		
		-- 1.3.6.1.4.1.6296.101.51.4.1.1.6
		sleOSPFLsaSequence OBJECT-TYPE
			SYNTAX Gauge32
			MAX-ACCESS read-only
			STATUS current
			DESCRIPTION
				"Description."
			::= { sleOSPFLsaEntry 6 }

		
		-- 1.3.6.1.4.1.6296.101.51.5
		sleOSPFNeighbor OBJECT IDENTIFIER ::= { sleOspf 5 }

		
		-- 1.3.6.1.4.1.6296.101.51.5.1
		sleOSPFNeighborTable OBJECT-TYPE
			SYNTAX SEQUENCE OF SleOSPFNeighborEntry
			MAX-ACCESS not-accessible
			STATUS current
			DESCRIPTION
				"Description."
			::= { sleOSPFNeighbor 1 }

		
		-- 1.3.6.1.4.1.6296.101.51.5.1.1
		sleOSPFNeighborEntry OBJECT-TYPE
			SYNTAX SleOSPFNeighborEntry
			MAX-ACCESS not-accessible
			STATUS current
			DESCRIPTION
				"Description."
			INDEX { sleOSPFProcID, sleOSPFNeighborIPAddr }
			::= { sleOSPFNeighborTable 1 }

		
		SleOSPFNeighborEntry ::=
			SEQUENCE { 
				sleOSPFNeighborIPAddr
					IpAddress,
				sleOSPFNeighborID
					IpAddress,
				sleOSPFNeighborPriority
					INTEGER,
				sleOSPFNeighborState
					INTEGER,
				sleOSPFNeighborIfName
					OCTET STRING
			 }

		-- 1.3.6.1.4.1.6296.101.51.5.1.1.1
		sleOSPFNeighborIPAddr OBJECT-TYPE
			SYNTAX IpAddress
			MAX-ACCESS read-only
			STATUS current
			DESCRIPTION
				"Description."
			::= { sleOSPFNeighborEntry 1 }

		
		-- 1.3.6.1.4.1.6296.101.51.5.1.1.2
		sleOSPFNeighborID OBJECT-TYPE
			SYNTAX IpAddress
			MAX-ACCESS read-only
			STATUS current
			DESCRIPTION
				"Description."
			::= { sleOSPFNeighborEntry 2 }

		
		-- 1.3.6.1.4.1.6296.101.51.5.1.1.3
		sleOSPFNeighborPriority OBJECT-TYPE
			SYNTAX INTEGER
			MAX-ACCESS read-only
			STATUS current
			DESCRIPTION
				"Description."
			::= { sleOSPFNeighborEntry 3 }

		
		-- 1.3.6.1.4.1.6296.101.51.5.1.1.4
		sleOSPFNeighborState OBJECT-TYPE
			SYNTAX INTEGER
				{
				dependUpon(0),
				down(1),
				attempt(2),
				init(3),
				twoway(4),
				exstart(5),
				exchange(6),
				loading(7),
				full(8)
				}
			MAX-ACCESS read-only
			STATUS current
			DESCRIPTION
				"Description."
			::= { sleOSPFNeighborEntry 4 }

		
		-- 1.3.6.1.4.1.6296.101.51.5.1.1.5
		sleOSPFNeighborIfName OBJECT-TYPE
			SYNTAX OCTET STRING
			MAX-ACCESS read-only
			STATUS current
			DESCRIPTION
				"Description."
			::= { sleOSPFNeighborEntry 5 }

		
		-- 1.3.6.1.4.1.6296.101.51.6
		sleOSPFRoute OBJECT IDENTIFIER ::= { sleOspf 6 }

		
		-- 1.3.6.1.4.1.6296.101.51.6.1
		sleOSPFRouteTable OBJECT-TYPE
			SYNTAX SEQUENCE OF SleOSPFRouteEntry
			MAX-ACCESS not-accessible
			STATUS current
			DESCRIPTION
				"Description."
			::= { sleOSPFRoute 1 }

		
		-- 1.3.6.1.4.1.6296.101.51.6.1.1
		sleOSPFRouteEntry OBJECT-TYPE
			SYNTAX SleOSPFRouteEntry
			MAX-ACCESS not-accessible
			STATUS current
			DESCRIPTION
				"Description."
			INDEX { sleOSPFProcID, sleOSPFRouteNexthop, sleOSPFRouteNbrID, sleOSPFRoutePathType }
			::= { sleOSPFRouteTable 1 }

		
		SleOSPFRouteEntry ::=
			SEQUENCE { 
				sleOSPFRoutePathType
					INTEGER,
				sleOSPFRouteNexthop
					IpAddress,
				sleOSPFRouteNbrID
					IpAddress,
				sleOSPFRoutePathTypeCode
					INTEGER,
				sleOSPFRouteMetric
					INTEGER,
				sleOSPFRouteIfName
					OCTET STRING,
				sleOSPFRouteAreaUse
					INTEGER,
				sleOSPFRouteAreaID
					IpAddress
			 }

		-- 1.3.6.1.4.1.6296.101.51.6.1.1.1
		sleOSPFRoutePathType OBJECT-TYPE
			SYNTAX INTEGER
				{
				connected(1),
				intraArea(2),
				interArea(3),
				external(4),
				discard(5),
				unknown(255)
				}
			MAX-ACCESS read-only
			STATUS current
			DESCRIPTION
				"Description."
			::= { sleOSPFRouteEntry 1 }

		
		-- 1.3.6.1.4.1.6296.101.51.6.1.1.2
		sleOSPFRouteNexthop OBJECT-TYPE
			SYNTAX IpAddress
			MAX-ACCESS read-only
			STATUS current
			DESCRIPTION
				"Description."
			::= { sleOSPFRouteEntry 2 }

		
		-- 1.3.6.1.4.1.6296.101.51.6.1.1.3
		sleOSPFRouteNbrID OBJECT-TYPE
			SYNTAX IpAddress
			MAX-ACCESS read-only
			STATUS current
			DESCRIPTION
				"Description."
			::= { sleOSPFRouteEntry 3 }

		
		-- 1.3.6.1.4.1.6296.101.51.6.1.1.4
		sleOSPFRoutePathTypeCode OBJECT-TYPE
			SYNTAX INTEGER
				{
				unknown(0),
				connected(1),
				discard(2),
				ospf(3),
				ia(4),
				e1(5),
				e2(6),
				n1(7),
				n2(8)
				}
			MAX-ACCESS read-only
			STATUS current
			DESCRIPTION
				"Description."
			::= { sleOSPFRouteEntry 4 }

		
		-- 1.3.6.1.4.1.6296.101.51.6.1.1.5
		sleOSPFRouteMetric OBJECT-TYPE
			SYNTAX INTEGER (0..65535)
			MAX-ACCESS read-only
			STATUS current
			DESCRIPTION
				"Description."
			::= { sleOSPFRouteEntry 5 }

		
		-- 1.3.6.1.4.1.6296.101.51.6.1.1.6
		sleOSPFRouteIfName OBJECT-TYPE
			SYNTAX OCTET STRING
			MAX-ACCESS read-only
			STATUS current
			DESCRIPTION
				"Description."
			::= { sleOSPFRouteEntry 6 }

		
		-- 1.3.6.1.4.1.6296.101.51.6.1.1.7
		sleOSPFRouteAreaUse OBJECT-TYPE
			SYNTAX INTEGER
				{
				nouse(0),
				use(1)
				}
			MAX-ACCESS read-only
			STATUS current
			DESCRIPTION
				"Description."
			::= { sleOSPFRouteEntry 7 }

		
		-- 1.3.6.1.4.1.6296.101.51.6.1.1.8
		sleOSPFRouteAreaID OBJECT-TYPE
			SYNTAX IpAddress
			MAX-ACCESS read-only
			STATUS current
			DESCRIPTION
				"Description."
			::= { sleOSPFRouteEntry 8 }

		
		-- 1.3.6.1.4.1.6296.101.51.7
		sleOspfGroup OBJECT-GROUP
			OBJECTS { sleOSPFRestartPeriod, sleOSPFRestartHelperPolicy, sleOSPFRestartHelperPeriod, sleOSPFControlRequest, sleOSPFControlStatus, 
				sleOSPFControlTimer, sleOSPFControlTimeStamp, sleOSPFControlReqResult, sleOSPFControlRestartPeriod, sleOSPFControlRestartHelperPolicy, 
				sleOSPFControlRestartHelperPeriod, sleOSPFProcID, sleOSPFProcRouterID, sleOSPFProcSPFDelayTime, sleOSPFProcSPFHoldTime, 
				sleOSPFProcAutoCost, sleOSPFProcAbrType, sleOSPFProcSnmpNotification, sleOSPFProcDefaultMetricConfig, sleOSPFProcDefaultMetricValue, 
				sleOSPFProcMaxArea, sleOSPFProcMaxConcurrentDD, sleOSPFProcCompatiblerfc1583, sleOSPFProcCapabilityOpaque, sleOSPFProcLSDBOverflowType, 
				sleOSPFProcLSDBOverflowLimit, sleOSPFProcExtLSDBLimit, sleOSPFProcExitOverFlowInterval, sleOSPFProcAdminDistance, sleOSPFProcExternalDistance, 
				sleOSPFProcIntraAreaDistance, sleOSPFProcInterAreaDistance, sleOSPFProcDefaultOriginType, sleOSPFProcDefaultOriginMetricType, sleOSPFProcDefaultOriginMetric, 
				sleOSPFProcDefaultOriginRouteMap, sleOSPFProcLogNeighborChange, sleOSPFProcPassiveIfAll, sleOSPFProcBfdIFAll, sleOSPFProcEfmIFAll, 
				sleOSPFProcCapabilityRestart, sleOSPFProcControlRequest, sleOSPFProcControlStatus, sleOSPFProcControlTimer, sleOSPFProcControlTimeStamp, 
				sleOSPFProcControlReqResult, sleOSPFProcControlID, sleOSPFProcControlRouterID, sleOSPFProcControlSPFDelayTime, sleOSPFProcControlSPFHoldTime, 
				sleOSPFProcControlAutoCost, sleOSPFProcControlAbrType, sleOSPFProcControlSnmpNotification, sleOSPFProcControlDefaultMetricConfig, sleOSPFProcControlDefaultMetricValue, 
				sleOSPFProcControlMaxArea, sleOSPFProcControlMaxConcurDD, sleOSPFProcControlComprfc1583, sleOSPFProcControlCapabilityOpaque, sleOSPFProcControlLSDBOverflowType, 
				sleOSPFProcControlLSDBOverflowLimit, sleOSPFProcControlExtLSDBLimit, sleOSPFProcControlExitOverFlowInterval, sleOSPFProcControlAdminDistance, sleOSPFProcControlExtDistance, 
				sleOSPFProcControlIntraAreaDistance, sleOSPFProcControlInterAreaDistance, sleOSPFProcControlDefOriginType, sleOSPFProcControlDefOriginMetricType, sleOSPFProcControlDefOriginMetric, 
				sleOSPFProcControlDefOriginRouteMap, sleOSPFProcControlLogNeighborChange, sleOSPFProcControlPassiveIFAll, sleOSPFProcControlBfdIFAll, sleOSPFProcControlEfmIFAll, 
				sleOSPFProcControlCapabilityRestart, sleOSPFProcNetworkIP, sleOSPFProcNetworkIPMask, sleOSPFProcNetworkAreaID, sleOSPFProcNetworkControlRequest, 
				sleOSPFProcNetworkControlStatus, sleOSPFProcNetworkControlTimer, sleOSPFProcNetworkControlTimeStamp, sleOSPFProcNetworkControlReqResult, sleOSPFProcNetworkControlProcID, 
				sleOSPFProcNetworkControlIP, sleOSPFProcNetworkControlIPMask, sleOSPFProcNetworkControlAreaID, sleOSPFProcSummaryIPAddress, sleOSPFProcSummaryIPMask, 
				sleOSPFProcSummaryTag, sleOSPFProcSummaryAdvertiseFlag, sleOSPFProcSummaryControlRequest, sleOSPFProcSummaryControlStatus, sleOSPFProcSummaryControlTimer, 
				sleOSPFProcSummaryControlTimeStamp, sleOSPFProcSummaryControlReqResult, sleOSPFProcSummaryControlProcID, sleOSPFProcSummaryControlIPAddress, sleOSPFProcSummaryControlIPMask, 
				sleOSPFProcSummaryControlTag, sleOSPFProcSummaryControlAdvertiseFlag, sleOSPFProcDistributeListOutFilterType, sleOSPFProcDistributeListAccessName, sleOSPFProcDistributeListControlRequest, 
				sleOSPFProcDistributeListControlStatus, sleOSPFProcDistributeListControlTimer, sleOSPFProcDistributeListControlTimeStamp, sleOSPFProcDistributeListControlReqResult, sleOSPFProcDistributeListControlProcID, 
				sleOSPFProcDistributeListControlOutFilterType, sleOSPFProcDistributeListControlAccessName, sleOSPFProcNeighborIPAddr, sleOSPFProcNeighborPriority, sleOSPFProcNeighborPollInterval, 
				sleOSPFProcNeighborCost, sleOSPFProcNeighborControlRequest, sleOSPFProcNeighborControlStatus, sleOSPFProcNeighborControlTimer, sleOSPFProcNeighborControlTimeStamp, 
				sleOSPFProcNeighborControlReqResult, sleOSPFProcNeighborControlProcID, sleOSPFProcNeighborControlIPAddr, sleOSPFProcNeighborControlPriority, sleOSPFProcNeighborControlPollInterval, 
				sleOSPFProcNeighborControlCost, sleOSPFProcPassIfAddr, sleOSPFProcPassIfName, sleOSPFProcPassIfControlRequest, sleOSPFProcPassIfControlStatus, 
				sleOSPFProcPassIfControlTimer, sleOSPFProcPassIfControlTimeStamp, sleOSPFProcPassIfControlReqResult, sleOSPFProcPassIfControlProcID, sleOSPFProcPassIfControlIPAddr, 
				sleOSPFProcPassIfControlName, sleOSPFProcHostIPAddr, sleOSPFProcHostAreaID, sleOSPFProcHostAreaCost, sleOSPFProcHostControlRequest, 
				sleOSPFProcHostControlStatus, sleOSPFProcHostControlTimer, sleOSPFProcHostControlTimeStamp, sleOSPFProcHostControlReqResult, sleOSPFProcHostControlProcID, 
				sleOSPFProcHostControlIPAddr, sleOSPFProcHostControlAreaID, sleOSPFProcHostControlAreaCost, sleOSPFProcRedistType, sleOSPFProcRedistMetricType, 
				sleOSPFProcRedistMetric, sleOSPFProcRedistRouteMapName, sleOSPFProcRedistTag, sleOSPFProcRedistSubnets, sleOSPFProcRedistControlRequest, 
				sleOSPFProcRedistControlStatus, sleOSPFProcRedistControlTimer, sleOSPFProcRedistControlTimeStamp, sleOSPFProcRedistControlReqResult, sleOSPFProcRedistControlProcID, 
				sleOSPFProcRedistControlType, sleOSPFProcRedistControlMetricType, sleOSPFProcRedistControlMetric, sleOSPFProcRedistControlRouteMapName, sleOSPFProcRedistControlTag, 
				sleOSPFProcRedistControlSubnets, sleOSPFProcAreaID, sleOSPFProcAreaType, sleOSPFProcAreaDefaultCost, sleOSPFProcAreaAuthenType, 
				sleOSPFProcAreaFAInName, sleOSPFProcAreaFAOutName, sleOSPFProcAreaFPInName, sleOSPFProcAreaFPOutName, sleOSPFProcAreaShortcutType, 
				sleOSPFProcAreaSpfRuns, sleOSPFProcAreaLsaCount, sleOSPFProcAreaLsaCheckSum, sleOSPFProcAreaSummary, sleOSPFProcAreaNssaTransRole, 
				sleOSPFProcAreaNssaNoRedist, sleOSPFProcAreaNssaDefOriginate, sleOSPFProcAreaNssaDefMetricType, sleOSPFProcAreaNssaDefMetric, sleOSPFProcAreaControlRequest, 
				sleOSPFProcAreaControlStatus, sleOSPFProcAreaControlTimer, sleOSPFProcAreaControlTimeStamp, sleOSPFProcAreaControlReqResult, sleOSPFProcAreaControlProcID, 
				sleOSPFProcAreaControlID, sleOSPFProcAreaControlType, sleOSPFProcAreaControlDefaultCost, sleOSPFProcAreaControlAuthenType, sleOSPFProcAreaControlFAInName, 
				sleOSPFProcAreaControlFAOutName, sleOSPFProcAreaControlFPInName, sleOSPFProcAreaControlFPOutName, sleOSPFProcAreaControlShortcutType, sleOSPFProcAreaControlSummary, 
				sleOSPFProcAreaControlNssaTransRole, sleOSPFProcAreaControlNssaNoRedist, sleOSPFProcAreaControlNssaDefOriginate, sleOSPFProcAreaControlNssaDefMetricType, sleOSPFProcAreaControlNssaDefMetric, 
				sleOSPFProcAreaRangeIP, sleOSPFProcAreaRangeIPMask, sleOSPFProcAreaRangeAdverType, sleOSPFProcAreaRangeControlRequest, sleOSPFProcAreaRangeControlStatus, 
				sleOSPFProcAreaRangeControlTimer, sleOSPFProcAreaRangeControlTimeStamp, sleOSPFProcAreaRangeControlReqResult, sleOSPFProcAreaRangeControlProcID, sleOSPFProcAreaRangeControlID, 
				sleOSPFProcAreaRangeControlIP, sleOSPFProcAreaRangeControlIPMask, sleOSPFProcAreaRangeControlAdverType, sleOSPFProcAreaVlinkIP, sleOSPFProcAreaVlinkAuthenType, 
				sleOSPFProcAreaVlinkAuthenKey, sleOSPFProcAreaVlinkDeadInterval, sleOSPFProcAreaVlinkHelloInterval, sleOSPFProcAreaVlinkRetranInterval, sleOSPFProcAreaVlinkTransDelay, 
				sleOSPFProcAreaVlinkControlRequest, sleOSPFProcAreaVlinkControlStatus, sleOSPFProcAreaVlinkControlTimer, sleOSPFProcAreaVlinkControlTimeStamp, sleOSPFProcAreaVlinkControlReqResult, 
				sleOSPFProcAreaVlinkControlProcID, sleOSPFProcAreaVlinkControlControlID, sleOSPFProcAreaVlinkControlIP, sleOSPFProcAreaVlinkControlAuthenType, sleOSPFProcAreaVlinkControlAuthenKey, 
				sleOSPFProcAreaVlinkControlDeadInterval, sleOSPFProcAreaVlinkControlHelloInterval, sleOSPFProcAreaVlinkControlRetranInterval, sleOSPFProcAreaVlinkControlTransInterval, sleOSPFProcAreaVlinkMsgKeyID, 
				sleOSPFProcAreaVlinkMsgKeyVal, sleOSPFProcAreaVlinkMsgKeyControlRequest, sleOSPFProcAreaVlinkMsgKeyControlControlStatus, sleOSPFProcAreaVlinkMsgKeyControlControlTimer, sleOSPFProcAreaVlinkMsgKeyControlTimeStamp, 
				sleOSPFProcAreaVlinkMsgKeyControlReqResult, sleOSPFProcAreaVlinkMsgKeyControlProcID, sleOSPFProcAreaVlinkMsgKeyControlID, sleOSPFProcAreaVlinkMsgKeyControlIP, sleOSPFProcAreaVlinkMsgKeyControlKeyID, 
				sleOSPFProcAreaVlinkMsgKeyControlKeyVal, sleOSPFIfIndex, sleOSFPIfEnabled, sleOSPFIfNetworkType, sleOSFPIfMTU, 
				sleOSFPIfBFD, sleOSFPIfEFM, sleOSPFIfControlRequest, sleOSPFIfControlStatus, sleOSPFIfControlTimer, 
				sleOSPFIfControlTimeStamp, sleOSPFIfControlReqResult, sleOSPFIfControlIndex, sleOSPFIfControlEnabled, sleOSPFIfControlNetworkType, 
				sleOSPFIfControlMTU, sleOSPFIfControlBFD, sleOSPFIfControlEFM, sleOSPFIfIpAddr, sleOSPFIfCost, 
				sleOSPFIfTransmitDelay, sleOSPFIfPriority, sleOSPFIfHelloInterval, sleOSPFIfDeadInterval, sleOSPFIfRetransInterval, 
				sleOSPFIfAuth, sleOSPFIfAuthType, sleOSPFIfDataFilterOut, sleOSPFIfMTUIgnore, sleOSPFIfResync, 
				sleOSPFIfResyncTimeout, sleOSPFIfAuthKeyFirst, sleOSPFIfAuthKeyFirstAct, sleOSPFIfAuthKeySecond, sleOSPFIfAuthKeySecondAct, 
				sleOSPFIfInfoControlRequest, sleOSPFIfInfoControlStatus, sleOSPFIfInfoControlTimer, sleOSPFIfInfoControlTimeStamp, sleOSPFIfInfoControlReqResult, 
				sleOSPFIfInfoControlIndex, sleOSPFIfInfoControlIpAddr, sleOSPFIfInfoControlCost, sleOSPFIfInfoControlTransmitDelay, sleOSPFIfInfoControlPriority, 
				sleOSPFIfInfoControlHelloInterval, sleOSPFIfInfoControlDeadInterval, sleOSPFIfInfoControlRetransInterval, sleOSPFIfInfoControlAuth, sleOSPFIfInfoControlAuthType, 
				sleOSPFIfInfoControlDataFilterOut, sleOSPFIfInfoControlMTUIgnore, sleOSPFIfInfoControlResync, sleOSPFIfInfoControlResyncTimeout, sleOSPFIfInfoControlAuthKeyFirst, 
				sleOSPFIfInfoControlAuthKeyFirstAct, sleOSPFIfInfoControlAuthKeySecond, sleOSPFIfInfoControlAuthKeySecondAct, sleOSPFIfMsgKeyID, sleOSPFIfMsgKeyVal, 
				sleOSPFIfMsgKeyAct, sleOSPFIfMsgKeyControlRequest, sleOSPFIfMsgKeyControlStatus, sleOSPFIfMsgKeyControlTimer, sleOSPFIfMsgKeyControlTimeStamp, 
				sleOSPFIfMsgKeyControlReqResult, sleOSPFIfMsgKeyControlIndex, sleOSPFIfMsgKeyControlIpAddr, sleOSPFIfMsgKeyControlKeyID, sleOSPFIfMsgKeyControlKeyVal, 
				sleOSPFIfMsgKeyControlKeyAct, sleOSPFIfStatusAddr, sleOSPFIfStatusUpState, sleOSPFIfStatusAreaID, sleOSPFIfStatusProcID, 
				sleOSPFIfStatusRouterID, sleOSPFIfStatusNetworkType, sleOSPFIfStatusCost, sleOSPFIfStatusTransmitDelay, sleOSPFIfStatusState, 
				sleOSPFIfStatusPriorityUse, sleOSPFIfStatusPriority, sleOSPFIfStatusDRRouterUse, sleOSPFIfStatusDRRouterID, sleOSPFIfStatusDRIfIpAddr, 
				sleOSPFIfStatusBDRRouterUse, sleOSPFIfStatusBDRRouterID, sleOSPFIfStatusBDRIfIpAddr, sleOSPFIfStatusHelloInterval, sleOSPFIfStatusDeadInterval, 
				sleOSPFIfStatusRetransInterval, sleOSPFIfStatusWaitInterval, sleOSPFIfStatusNeighborCount, sleOSPFIfCryptSeqNum, sleOSPFIfStatusRcvHello, 
				sleOSPFIfStatusSendHello, sleOSPFIfStatusRcvDD, sleOSPFIfStatusSendDD, sleOSPFIfStatusRcvLSReq, sleOSPFIfStatusSendLSReq, 
				sleOSPFIfStatusRcvLSUpd, sleOSPFIfStatusSendLSUpd, sleOSPFIfStatusRcvLSAck, sleOSPFIfStatusSendLSAck, sleOSPFIfStatusDiscarded, 
				sleOSPFLsaType, sleOSPFLsaAreaID, sleOSPFLsaLinkID, sleOSPFLsaAdvRouter, sleOSPFLsaAge, 
				sleOSPFLsaSequence, sleOSPFNeighborIPAddr, sleOSPFNeighborID, sleOSPFNeighborPriority, sleOSPFNeighborState, 
				sleOSPFNeighborIfName, sleOSPFRoutePathType, sleOSPFRouteNexthop, sleOSPFRouteNbrID, sleOSPFRoutePathTypeCode, 
				sleOSPFRouteMetric, sleOSPFRouteIfName, sleOSPFRouteAreaUse, sleOSPFRouteAreaID }
			STATUS current
			DESCRIPTION 
				"Description."
			::= { sleOspf 7 }

		
		-- 1.3.6.1.4.1.6296.101.51.8
		sleOspfNotificationGroup NOTIFICATION-GROUP
			NOTIFICATIONS { sleOSPFRestartPeriodChanged, sleOSPFRestartHelperProfileChanged, sleOSPFGracefulRestarted, sleOSPFProcCreated, sleOSPFProcDeleted, 
				sleOSPFRouterIDCreated, sleOSPFRouterIDDeleted, sleOSPFProcSPFTimerChanged, sleOSPFProcAutoCostChanged, sleOSPFProcAbrTypeChanged, 
				sleOSPFProcSnmpNotificationChanged, sleOSPFProcDefaultMetricProfileChanged, sleOSPFProcMaxAreaChanged, sleOSPFProcMaxConcurDDChanged, sleOSPFProcComrfc1853Changed, 
				sleOSPFProcCapOpaqueChanged, sleOSPFProcLSDBOverflowProfileChanged, sleOSPFProcExtOverflowProfileChanged, sleOSPFProcAdminDistanceChanged, sleOSPFProcExtDistanceChanged, 
				sleOSPFProcIntraDistanceChanged, sleOSPFProcInterDistanceChanged, sleOSPFProcDefaultOriginTypeChanged, sleOSPFProcDefaultOriginMetricTypeChanged, sleOSPFProcDefaultOriginMetricChanged, 
				sleOSPFProcDefaultOriginRouteMapChanged, sleOSPFProcLogNeighborChanged, sleOSPFProcPassiveIFAllChanged, sleOSPFProcBfdIFAllChanged, sleOSPFProcEfmIFAllChanged, 
				sleOSPFProcCapRestartChanged, sleOSPFProcCleared, sleOSPFProcNetworkCreated, sleOSPFProcNetworkDeleted, sleOSPFSummaryCreated, 
				sleOSPFSummaryDeleted, sleOSPFSummaryChanged, sleOSPFDistributeListCreated, sleOSPFDistributeListDeleted, sleOSPFProcNeighborCreated, 
				sleOSPFProcNeighborDeleted, sleOSPFProcNeighborChanged, sleOSPFPassInterfaceCreated, sleOSPFPassInterfaceDeleted, sleOSPFProcHostCreated, 
				sleOSPFProcHostDeleted, sleOSPFProcHostCostChanged, sleOSPFProcRedistCreated, sleOSPFProcRedistDeleted, sleOSPFProcRedistChanged, 
				sleOSPFProcGeneralAreaCreated, sleOSPFProcStubNssaAreaCreated, sleOSPFProcAreaDeleted, sleOSPFProcAreaDefaultCostChanged, sleOSPFProcAreaAuthenTypeChanged, 
				sleOSPFProcAreaFAInNameChanged, sleOSPFProcAreaFAOutNameChanged, sleOSPFProcAreaFPInNameChanged, sleOSPFProcAreaFPOutNameChanged, sleOSPFProcAreaShortcutTypeChanged, 
				sleOSPFProcAreaSummaryChanged, sleOSPFProcNssaAreaTransRoleChanged, sleOSPFProcNssaAreaTransNoRedistChanged, sleOSPFProcNssaAreaDefProfileChanged, sleOSPFAreaRangeCreated, 
				sleOSPFAreaRangeDeleted, sleOSPFAreaRangeChanged, sleOSPFAreaVlinkCreated, sleOSPFAreaVLinkDeleted, sleOSPFAreaVLinkChanged, 
				sleOSPFAreaVlinkMsgKeyCreated, sleOSPFAreaVLinkMsgKeyDeleted, sleOSPFIfEnableChanged, sleOSPFIfNetworkTypeChanged, sleOSPFIfMTUChanged, 
				sleOSPFIfBFDChanged, sleOSPFIfEFMChanged, sleOSPFIfCostChanged, sleOSPFIfPriorityChanged, sleOSPFIfTransmitDelayChanged, 
				sleOSPFIfHelloIntervalChanged, sleOSPFIfDeadIntervalChanged, sleOSPFIfRetransIntervalChanged, sleOSPFIfAuthProfileChanged, sleOSPFIfDatafilterOutChanged, 
				sleOSPFIfMTUIgnoreChanged, sleOSPFIfResyncProfileChanged, sleOSPFIfAuthKeyFirstProfileChanged, sleOSPFIfAuthKeyProfileSecondChanged, sleOSPFIfMsgKeyCreated, 
				sleOSPFIfMsgKeyDeleted }
			STATUS current
			DESCRIPTION 
				"Description."
			::= { sleOspf 8 }

		
	
	END

--
-- SLE-OSPF-MIB.my
--
