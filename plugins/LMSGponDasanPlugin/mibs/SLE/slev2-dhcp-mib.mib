--
-- slev2-dhcp-mib.mib
-- MIB generated by MG-SOFT Visual MIB Builder Version 6.0  Build 88
-- Monday, April 08, 2013 at 19:49:45
--

	SLEV2-DHCP-MIB DEFINITIONS ::= BEGIN
 
		IMPORTS
			sleV2Mgmt			
				FROM DASAN-SMI			
			InterfaceIndex			
				FROM IF-MIB			
			SleControlStatusType, SleControlRequestResultType			
				FROM SLE-TC-MIB			
			OBJECT-GROUP, NOTIFICATION-GROUP			
				FROM SNMPv2-CONF			
			TimeTicks, IpAddress, Integer32, Unsigned32, Gauge32, 
			Counter32, BITS, OBJECT-TYPE, MODULE-IDENTITY, NOTIFICATION-TYPE			
				FROM SNMPv2-SMI			
			MacAddress			
				FROM SNMPv2-TC;
	
	
		-- 1.3.6.1.4.1.6296.102.6
		sleV2Dhcp MODULE-IDENTITY 
			LAST-UPDATED "200510241120Z"		-- October 24, 2005 at 11:20 GMT
			ORGANIZATION 
				"Dasan Co., Ltd."
			CONTACT-INFO 
				" "
			DESCRIPTION 
				"This MIB contains all needed informations about DHCP and
				all supported sle DHCP features."
			::= { sleV2Mgmt 6 }

		
	
--
-- Type definitions
--
	
		Boolean ::= INTEGER
			{
			disable(0),
			enable(1)
			}

	
	
--
-- Node definitions
--
	
		-- 1.3.6.1.4.1.6296.102.6.1
		sleV2DhcpBase OBJECT IDENTIFIER ::= { sleV2Dhcp 1 }

		
		-- 1.3.6.1.4.1.6296.102.6.2
		sleV2Dhcp4 OBJECT IDENTIFIER ::= { sleV2Dhcp 2 }

		
		-- 1.3.6.1.4.1.6296.102.6.2.1
		sleV2Dhcp4Base OBJECT IDENTIFIER ::= { sleV2Dhcp4 1 }

		
		-- 1.3.6.1.4.1.6296.102.6.2.1.1
		sleV2Dhcp4Info OBJECT IDENTIFIER ::= { sleV2Dhcp4Base 1 }

		
		-- 1.3.6.1.4.1.6296.102.6.2.1.1.1
		sleV2Dhcp4ServiceActivity OBJECT-TYPE
			SYNTAX INTEGER
				{
				disable(0),
				enable(1)
				}
			MAX-ACCESS read-only
			STATUS current
			DESCRIPTION
				"This object indicates whether DHCP servie is disable or enable.
				"
			::= { sleV2Dhcp4Info 1 }

		
		-- 1.3.6.1.4.1.6296.102.6.2.1.1.2
		sleV2Dhcp4DatabaseURL OBJECT-TYPE
			SYNTAX IpAddress
			MAX-ACCESS read-only
			STATUS current
			DESCRIPTION
				"The IP address of back up server.
				"
			::= { sleV2Dhcp4Info 2 }

		
		-- 1.3.6.1.4.1.6296.102.6.2.1.1.3
		sleV2Dhcp4DatabaseInterval OBJECT-TYPE
			SYNTAX INTEGER (0 | 1..2147483637)
			MAX-ACCESS read-only
			STATUS current
			DESCRIPTION
				"The backup interval to backup server.
				"
			::= { sleV2Dhcp4Info 3 }

		
		-- 1.3.6.1.4.1.6296.102.6.2.1.1.4
		sleV2Dhcp4ArpPingFlag OBJECT-TYPE
			SYNTAX INTEGER
				{
				ping(0),
				arp(1)
				}
			MAX-ACCESS read-only
			STATUS current
			DESCRIPTION
				"This object indicates whether it's ping or arp that is for validation using ip before DHCP server assign IP address."
			DEFVAL { ping }
			::= { sleV2Dhcp4Info 4 }

		
		-- 1.3.6.1.4.1.6296.102.6.2.1.1.5
		sleV2Dhcp4ArpRetransmits OBJECT-TYPE
			SYNTAX INTEGER (0..20)
			MAX-ACCESS read-only
			STATUS current
			DESCRIPTION
				"The number of retransmission for Arp"
			::= { sleV2Dhcp4Info 5 }

		
		-- 1.3.6.1.4.1.6296.102.6.2.1.1.6
		sleV2Dhcp4ArpTimeout OBJECT-TYPE
			SYNTAX INTEGER (100..5000)
			MAX-ACCESS read-only
			STATUS current
			DESCRIPTION
				"The timeout of the Arp"
			::= { sleV2Dhcp4Info 6 }

		
		-- 1.3.6.1.4.1.6296.102.6.2.1.1.7
		sleV2Dhcp4PingRetransmits OBJECT-TYPE
			SYNTAX INTEGER (0..20)
			MAX-ACCESS read-only
			STATUS current
			DESCRIPTION
				"The number of retransmission for Ping"
			::= { sleV2Dhcp4Info 7 }

		
		-- 1.3.6.1.4.1.6296.102.6.2.1.1.8
		sleV2Dhcp4PingTimeout OBJECT-TYPE
			SYNTAX INTEGER (100..5000)
			MAX-ACCESS read-only
			STATUS current
			DESCRIPTION
				"The timeout of the ping"
			::= { sleV2Dhcp4Info 8 }

		
		-- 1.3.6.1.4.1.6296.102.6.2.1.1.9
		sleV2Dhcp4ClassUsage OBJECT-TYPE
			SYNTAX INTEGER
				{
				disable(0),
				enable(1)
				}
			MAX-ACCESS read-only
			STATUS current
			DESCRIPTION
				"This object indicates whether the class function of DHCP is disable or enable."
			::= { sleV2Dhcp4Info 9 }

		
		-- 1.3.6.1.4.1.6296.102.6.2.1.1.10
		sleV2Dhcp4SmartRelayUsage OBJECT-TYPE
			SYNTAX INTEGER
				{
				disable(0),
				enable(1)
				}
			MAX-ACCESS read-only
			STATUS current
			DESCRIPTION
				"This object indicates whether the smart relay function of DHCP is disable or enable.
				"
			::= { sleV2Dhcp4Info 10 }

		
		-- 1.3.6.1.4.1.6296.102.6.2.1.1.11
		sleV2Dhcp4Option82Usage OBJECT-TYPE
			SYNTAX INTEGER
				{
				disable(0),
				enable(1)
				}
			MAX-ACCESS read-only
			STATUS current
			DESCRIPTION
				"This object indicates whether the option82 function in the DHCP is disable or enable.
				"
			::= { sleV2Dhcp4Info 11 }

		
		-- 1.3.6.1.4.1.6296.102.6.2.1.1.12
		sleV2Dhcp4Option82Drop OBJECT-TYPE
			SYNTAX INTEGER
				{
				none(0),
				normal(1),
				option82(2)
				}
			MAX-ACCESS read-only
			STATUS current
			DESCRIPTION
				"The drop policy of the request packet.
				"
			::= { sleV2Dhcp4Info 12 }

		
		-- 1.3.6.1.4.1.6296.102.6.2.1.1.13
		sleV2Dhcp4Option82Policy OBJECT-TYPE
			SYNTAX INTEGER
				{
				keep(0),
				replace(1)
				}
			MAX-ACCESS read-only
			STATUS current
			DESCRIPTION
				"The policy of the relay agent information option.
				"
			::= { sleV2Dhcp4Info 13 }

		
		-- 1.3.6.1.4.1.6296.102.6.2.1.1.14
		sleV2Dhcp4Option82TrustDefault OBJECT-TYPE
			SYNTAX INTEGER
				{
				deny(0),
				permit(1)
				}
			MAX-ACCESS read-only
			STATUS current
			DESCRIPTION
				"The Dhcp operation mode."
			::= { sleV2Dhcp4Info 14 }

		
		-- 1.3.6.1.4.1.6296.102.6.2.1.1.15
		sleV2Dhcp4Option82SystemRemoteType OBJECT-TYPE
			SYNTAX INTEGER
				{
				ipaddress(1),
				hex(2),
				text(3),
				host(4),
				index(5),
				option(6),
				undef(255)
				}
			MAX-ACCESS read-only
			STATUS current
			DESCRIPTION
				"The type of remote ID for the option82 systme of DHCP 
				Ipaddress, Hex, Text, Index"
			::= { sleV2Dhcp4Info 15 }

		
		-- 1.3.6.1.4.1.6296.102.6.2.1.1.16
		sleV2Dhcp4Option82SystemRemoteId OBJECT-TYPE
			SYNTAX OCTET STRING (SIZE (0 | 1..64))
			MAX-ACCESS read-only
			STATUS current
			DESCRIPTION
				"The remote identifier for the option82 system of DHCP.
				"
			::= { sleV2Dhcp4Info 16 }

		
		-- 1.3.6.1.4.1.6296.102.6.2.1.1.17
		sleV2Dhcp4DatabaseKey OBJECT-TYPE
			SYNTAX INTEGER
				{
				clientid(0),
				hwaddress(1)
				}
			MAX-ACCESS read-only
			STATUS current
			DESCRIPTION
				"The Database-key Setting for dhcp daemon.
				"
			::= { sleV2Dhcp4Info 17 }

		
		-- 1.3.6.1.4.1.6296.102.6.2.1.1.18
		sleV2Dhcp4DebugStatus OBJECT-TYPE
			SYNTAX BITS
				{
				debugFilter(0),
				debugLease(1),
				debugPacket(2),
				debugServices(3)
				}
			MAX-ACCESS read-write
			STATUS current
			DESCRIPTION
				"The  debug option setting of dhcp daemon.
				debugNo(0)
				debugFilter(1)
				debugLease(2)
				debugPacket(4)
				debugService(8)
				The above value is denotes by 'or'.
				debugAll(16)
				
				"
			::= { sleV2Dhcp4Info 18 }

		
		-- 1.3.6.1.4.1.6296.102.6.2.1.1.19
		sleV2Dhcp4AuthArpTime OBJECT-TYPE
			SYNTAX INTEGER (0 | 120..2147483637)
			UNITS "second"
			MAX-ACCESS read-only
			STATUS current
			DESCRIPTION
				"The set of starting Time for secure ARP function."
			::= { sleV2Dhcp4Info 19 }

		
		-- 1.3.6.1.4.1.6296.102.6.2.1.1.20
		sleV2Dhcp4AuthArpLeft OBJECT-TYPE
			SYNTAX Unsigned32
			UNITS "second"
			MAX-ACCESS read-only
			STATUS current
			DESCRIPTION
				"The left Time until authorized-arp function will be start.
				It denotes such as '01:20:31'"
			::= { sleV2Dhcp4Info 20 }

		
		-- 1.3.6.1.4.1.6296.102.6.2.1.1.21
		sleV2Dhcp4ClientHardwareAddress OBJECT-TYPE
			SYNTAX Boolean
			MAX-ACCESS read-only
			STATUS current
			DESCRIPTION
				"Prevent a client from getting multiple IP address"
			::= { sleV2Dhcp4Info 21 }

		
		-- 1.3.6.1.4.1.6296.102.6.2.1.1.22
		sleV2Dhcp4PEStatus OBJECT-TYPE
			SYNTAX INTEGER
				{
				disable(0),
				enable(1)
				}
			MAX-ACCESS read-only
			STATUS current
			DESCRIPTION
				"The debug option setting of DHCP daemon.
				"
			::= { sleV2Dhcp4Info 22 }

		
		-- 1.3.6.1.4.1.6296.102.6.2.1.1.23
		sleV2Dhcp4AuthArpReadyTime OBJECT-TYPE
			SYNTAX INTEGER (0 | 120..2147483637)
			MAX-ACCESS read-only
			STATUS current
			DESCRIPTION
				"Authorzed Arp starting time.
				"
			::= { sleV2Dhcp4Info 23 }

		
		-- 1.3.6.1.4.1.6296.102.6.2.1.1.24
		sleV2Dhcp4AuthArpRemainTime OBJECT-TYPE
			SYNTAX INTEGER (0..2147483637)
			MAX-ACCESS read-write
			STATUS current
			DESCRIPTION
				"Authorzed Arp remain time.
				"
			::= { sleV2Dhcp4Info 24 }

		
		-- 1.3.6.1.4.1.6296.102.6.2.1.1.25
		sleV2Dhcp4Option82SystemRemoteOption OBJECT-TYPE
			SYNTAX OCTET STRING (SIZE (0..16))
			MAX-ACCESS read-only
			STATUS current
			DESCRIPTION
				"Option82 system remote option.
				"
			::= { sleV2Dhcp4Info 25 }

		
		-- 1.3.6.1.4.1.6296.102.6.2.1.1.26
		sleV2Dhcp4Option82SystemCircuitPortType OBJECT-TYPE
			SYNTAX INTEGER
				{
				physical(1),
				logical(2)
				}
			MAX-ACCESS read-only
			STATUS current
			DESCRIPTION
				"The system-circuit-id port-type of option82.
				physical/logical"
			::= { sleV2Dhcp4Info 26 }

		
		-- 1.3.6.1.4.1.6296.102.6.2.1.2
		sleV2Dhcp4Control OBJECT IDENTIFIER ::= { sleV2Dhcp4Base 2 }

		
		-- 1.3.6.1.4.1.6296.102.6.2.1.2.1
		sleV2Dhcp4ControlRequest OBJECT-TYPE
			SYNTAX INTEGER
				{
				setDhcpServiceActivity(1),
				setDhcpDatabaseProfile(2),
				setDhcpArpPingProfile(3),
				setDhcpClassState(4),
				setDhcpSmartRelayState(5),
				setDhcpOption82State(6),
				setDhcpOption82Policy(7),
				setDhcpOption82TrustDefault(8),
				setDhcpOption82SystemRemoteId(9),
				setDhcpDatabaseKey(10),
				setDhcpDebugStatus(11),
				setDhcpAuthArpTime(12),
				setDhcpClientHardwareAddress(13),
				setDhcpPEStatus(14),
				setDhcpOption82SystemRemoteOption(15),
				setDhcpOption82SystemCircuitIdPortType(16)
				}
			MAX-ACCESS read-write
			STATUS current
			DESCRIPTION
				"The request of a user command."
			::= { sleV2Dhcp4Control 1 }

		
		-- 1.3.6.1.4.1.6296.102.6.2.1.2.2
		sleV2Dhcp4ControlStatus OBJECT-TYPE
			SYNTAX SleControlStatusType
			MAX-ACCESS read-only
			STATUS current
			DESCRIPTION
				"The status of a user command."
			::= { sleV2Dhcp4Control 2 }

		
		-- 1.3.6.1.4.1.6296.102.6.2.1.2.3
		sleV2Dhcp4ControlTimer OBJECT-TYPE
			SYNTAX Gauge32
			MAX-ACCESS read-write
			STATUS current
			DESCRIPTION
				"The maximum wait Time for the manager for a long running user command."
			::= { sleV2Dhcp4Control 3 }

		
		-- 1.3.6.1.4.1.6296.102.6.2.1.2.4
		sleV2Dhcp4ControlTimeStamp OBJECT-TYPE
			SYNTAX TimeTicks
			MAX-ACCESS read-only
			STATUS current
			DESCRIPTION
				"The Time stamp of the last command (end of command)."
			::= { sleV2Dhcp4Control 4 }

		
		-- 1.3.6.1.4.1.6296.102.6.2.1.2.5
		sleV2Dhcp4ControlReqResult OBJECT-TYPE
			SYNTAX SleControlRequestResultType
			MAX-ACCESS read-only
			STATUS current
			DESCRIPTION
				"The result of the last user command."
			::= { sleV2Dhcp4Control 5 }

		
		-- 1.3.6.1.4.1.6296.102.6.2.1.2.6
		sleV2Dhcp4ControlServiceActivity OBJECT-TYPE
			SYNTAX INTEGER
				{
				disable(0),
				enable(1)
				}
			MAX-ACCESS read-write
			STATUS current
			DESCRIPTION
				"This object indicates whether DHCP servie is disable or enable.
				"
			::= { sleV2Dhcp4Control 6 }

		
		-- 1.3.6.1.4.1.6296.102.6.2.1.2.7
		sleV2Dhcp4ControlDatabaseURL OBJECT-TYPE
			SYNTAX IpAddress
			MAX-ACCESS read-write
			STATUS current
			DESCRIPTION
				"The IP address of back up server.
				"
			::= { sleV2Dhcp4Control 7 }

		
		-- 1.3.6.1.4.1.6296.102.6.2.1.2.8
		sleV2Dhcp4ControlDatabaseInterval OBJECT-TYPE
			SYNTAX INTEGER (0 | 1..2147483637)
			MAX-ACCESS read-write
			STATUS current
			DESCRIPTION
				"The backup interval to backup server.
				"
			::= { sleV2Dhcp4Control 8 }

		
		-- 1.3.6.1.4.1.6296.102.6.2.1.2.9
		sleV2Dhcp4ControlArpPingFlag OBJECT-TYPE
			SYNTAX INTEGER
				{
				ping(0),
				arp(1)
				}
			MAX-ACCESS read-write
			STATUS current
			DESCRIPTION
				"This object indicates whether it's ping or arp that is for validation using ip before DHCP server assign IP address."
			DEFVAL { ping }
			::= { sleV2Dhcp4Control 9 }

		
		-- 1.3.6.1.4.1.6296.102.6.2.1.2.10
		sleV2Dhcp4ControlArpRetransmits OBJECT-TYPE
			SYNTAX INTEGER (0..20)
			MAX-ACCESS read-write
			STATUS current
			DESCRIPTION
				"The number of retransmission for Arp"
			::= { sleV2Dhcp4Control 10 }

		
		-- 1.3.6.1.4.1.6296.102.6.2.1.2.11
		sleV2Dhcp4ControlArpTimeout OBJECT-TYPE
			SYNTAX INTEGER (100..5000)
			MAX-ACCESS read-write
			STATUS current
			DESCRIPTION
				"The timeout of the Arp"
			::= { sleV2Dhcp4Control 11 }

		
		-- 1.3.6.1.4.1.6296.102.6.2.1.2.12
		sleV2Dhcp4ControlPingRetransmits OBJECT-TYPE
			SYNTAX INTEGER (0..20)
			MAX-ACCESS read-write
			STATUS current
			DESCRIPTION
				"The number of retransmission for Ping.
				"
			::= { sleV2Dhcp4Control 12 }

		
		-- 1.3.6.1.4.1.6296.102.6.2.1.2.13
		sleV2Dhcp4ControlPingTimeout OBJECT-TYPE
			SYNTAX INTEGER (100..5000)
			MAX-ACCESS read-write
			STATUS current
			DESCRIPTION
				"The timeout of the ping.
				"
			::= { sleV2Dhcp4Control 13 }

		
		-- 1.3.6.1.4.1.6296.102.6.2.1.2.14
		sleV2Dhcp4ControlClassUsage OBJECT-TYPE
			SYNTAX INTEGER
				{
				disable(0),
				enable(1)
				}
			MAX-ACCESS read-write
			STATUS current
			DESCRIPTION
				"This object indicates whether the class function of DHCP is disable or enable.
				"
			::= { sleV2Dhcp4Control 14 }

		
		-- 1.3.6.1.4.1.6296.102.6.2.1.2.15
		sleV2Dhcp4ControlSmartRelayUsage OBJECT-TYPE
			SYNTAX INTEGER
				{
				disable(0),
				enable(1)
				}
			MAX-ACCESS read-write
			STATUS current
			DESCRIPTION
				"This object indicates whether the smart relay function of DHCP is disable or enable.
				"
			::= { sleV2Dhcp4Control 15 }

		
		-- 1.3.6.1.4.1.6296.102.6.2.1.2.16
		sleV2Dhcp4ControlOption82Usage OBJECT-TYPE
			SYNTAX INTEGER
				{
				disable(0),
				enable(1)
				}
			MAX-ACCESS read-write
			STATUS current
			DESCRIPTION
				"This object indicates whether the option82 function in the DHCP is disable or enable.
				"
			::= { sleV2Dhcp4Control 16 }

		
		-- 1.3.6.1.4.1.6296.102.6.2.1.2.17
		sleV2Dhcp4ControlOption82Drop OBJECT-TYPE
			SYNTAX INTEGER
				{
				none(0),
				normal(1),
				option82(2)
				}
			MAX-ACCESS read-write
			STATUS current
			DESCRIPTION
				"The drop policy of the request packet.
				"
			::= { sleV2Dhcp4Control 17 }

		
		-- 1.3.6.1.4.1.6296.102.6.2.1.2.18
		sleV2Dhcp4ControlOption82Policy OBJECT-TYPE
			SYNTAX INTEGER
				{
				keep(0),
				replace(1)
				}
			MAX-ACCESS read-write
			STATUS current
			DESCRIPTION
				"The policy of the relay agent information option.
				"
			::= { sleV2Dhcp4Control 18 }

		
		-- 1.3.6.1.4.1.6296.102.6.2.1.2.19
		sleV2Dhcp4ControlOption82TrustDefault OBJECT-TYPE
			SYNTAX INTEGER
				{
				deny(0),
				permit(1)
				}
			MAX-ACCESS read-write
			STATUS current
			DESCRIPTION
				"The default policy of the trust for the relay agent information option.
				"
			::= { sleV2Dhcp4Control 19 }

		
		-- 1.3.6.1.4.1.6296.102.6.2.1.2.20
		sleV2Dhcp4ControlOption82SystemRemoteType OBJECT-TYPE
			SYNTAX INTEGER
				{
				ipaddress(1),
				hex(2),
				text(3),
				host(4),
				index(5),
				option(6),
				undef(255)
				}
			MAX-ACCESS read-write
			STATUS current
			DESCRIPTION
				"The type of remote ID for the option82 systme of DHCP 
				Ipaddress, Hex, Text, Index"
			::= { sleV2Dhcp4Control 20 }

		
		-- 1.3.6.1.4.1.6296.102.6.2.1.2.21
		sleV2Dhcp4ControlOption82SystemRemoteId OBJECT-TYPE
			SYNTAX OCTET STRING (SIZE (0 | 1..64))
			MAX-ACCESS read-write
			STATUS current
			DESCRIPTION
				"The remote identifier for the option82 system of DHCP.
				"
			::= { sleV2Dhcp4Control 21 }

		
		-- 1.3.6.1.4.1.6296.102.6.2.1.2.22
		sleV2Dhcp4ControlDatabaseKey OBJECT-TYPE
			SYNTAX INTEGER
				{
				clientid(0),
				hwaddress(1)
				}
			MAX-ACCESS read-write
			STATUS current
			DESCRIPTION
				"The database key on the relay.
				"
			::= { sleV2Dhcp4Control 22 }

		
		-- 1.3.6.1.4.1.6296.102.6.2.1.2.23
		sleV2Dhcp4ControlDebugStatus OBJECT-TYPE
			SYNTAX BITS
				{
				debugFilter(0),
				debugLease(1),
				debugPacket(2),
				debugServices(3)
				}
			MAX-ACCESS read-write
			STATUS current
			DESCRIPTION
				"The  debug option setting of dhcp daemon.
				The  debug option setting of dhcp daemon.
				debugNo(0)
				debugFilter(1)
				debugLease(2)
				debugPacket(4)
				debugService(8)
				The above value is denotes by 'or'.
				debugAll(16)
				
				"
			::= { sleV2Dhcp4Control 23 }

		
		-- 1.3.6.1.4.1.6296.102.6.2.1.2.24
		sleV2Dhcp4ControlAuthArpTime OBJECT-TYPE
			SYNTAX INTEGER (0 | 120..2147483637)
			UNITS "second"
			MAX-ACCESS read-write
			STATUS current
			DESCRIPTION
				"Authorized Arp timeout.
				"
			::= { sleV2Dhcp4Control 24 }

		
		-- 1.3.6.1.4.1.6296.102.6.2.1.2.25
		sleV2Dhcp4ControlClientHardwareAddress OBJECT-TYPE
			SYNTAX Boolean
			MAX-ACCESS read-write
			STATUS current
			DESCRIPTION
				"The left time until authorized arp time out.
				"
			::= { sleV2Dhcp4Control 25 }

		
		-- 1.3.6.1.4.1.6296.102.6.2.1.2.26
		sleV2Dhcp4ControlPEStatus OBJECT-TYPE
			SYNTAX INTEGER
				{
				disable(0),
				enable(1)
				}
			MAX-ACCESS read-write
			STATUS current
			DESCRIPTION
				"The debug option setting of DHCP daemon.
				"
			::= { sleV2Dhcp4Control 26 }

		
		-- 1.3.6.1.4.1.6296.102.6.2.1.2.27
		sleV2Dhcp4ControlAuthArpReadyTime OBJECT-TYPE
			SYNTAX INTEGER (0 | 120..2147483637)
			MAX-ACCESS read-write
			STATUS current
			DESCRIPTION
				"Authorzed Arp Staring time.
				"
			::= { sleV2Dhcp4Control 27 }

		
		-- 1.3.6.1.4.1.6296.102.6.2.1.2.28
		sleV2Dhcp4ControlOption82SystemRemoteOption OBJECT-TYPE
			SYNTAX OCTET STRING (SIZE (0..16))
			MAX-ACCESS read-write
			STATUS current
			DESCRIPTION
				"Option82 system remote option.
				"
			::= { sleV2Dhcp4Control 28 }

		
		-- 1.3.6.1.4.1.6296.102.6.2.1.2.29
		sleV2Dhcp4ControlOption82SystemCircuitPortType OBJECT-TYPE
			SYNTAX INTEGER
				{
				physical(1),
				logical(2)
				}
			MAX-ACCESS read-write
			STATUS current
			DESCRIPTION
				"The system-circuit-id port-type of option82.
				physical/logical"
			::= { sleV2Dhcp4Control 29 }

		
		-- 1.3.6.1.4.1.6296.102.6.2.1.3
		sleV2Dhcp4Notification OBJECT IDENTIFIER ::= { sleV2Dhcp4Base 3 }

		
		-- 1.3.6.1.4.1.6296.102.6.2.1.3.1
		sleV2Dhcp4ServiceActivityChanged NOTIFICATION-TYPE
			OBJECTS { sleV2Dhcp4ControlRequest, sleV2Dhcp4ControlTimeStamp, sleV2Dhcp4ControlReqResult, sleV2Dhcp4ServiceActivity }
			STATUS current
			DESCRIPTION 
				"Description."
			::= { sleV2Dhcp4Notification 1 }

		
		-- 1.3.6.1.4.1.6296.102.6.2.1.3.2
		sleV2Dhcp4DatabaseProfileChanged NOTIFICATION-TYPE
			OBJECTS { sleV2Dhcp4ControlRequest, sleV2Dhcp4ControlTimeStamp, sleV2Dhcp4ControlReqResult, sleV2Dhcp4DatabaseURL, sleV2Dhcp4DatabaseInterval
				 }
			STATUS current
			DESCRIPTION 
				"Description."
			::= { sleV2Dhcp4Notification 2 }

		
		-- 1.3.6.1.4.1.6296.102.6.2.1.3.3
		sleV2Dhcp4ArpPingProfileChanged NOTIFICATION-TYPE
			OBJECTS { sleV2Dhcp4ControlRequest, sleV2Dhcp4ControlTimeStamp, sleV2Dhcp4ControlReqResult, sleV2Dhcp4ArpPingFlag, sleV2Dhcp4ArpRetransmits, 
				sleV2Dhcp4ArpTimeout, sleV2Dhcp4PingRetransmits, sleV2Dhcp4PingTimeout }
			STATUS current
			DESCRIPTION 
				"Description."
			::= { sleV2Dhcp4Notification 3 }

		
		-- 1.3.6.1.4.1.6296.102.6.2.1.3.4
		sleV2Dhcp4ClassUsageChanged NOTIFICATION-TYPE
			OBJECTS { sleV2Dhcp4ControlRequest, sleV2Dhcp4ControlTimeStamp, sleV2Dhcp4ControlReqResult, sleV2Dhcp4ClassUsage }
			STATUS current
			DESCRIPTION 
				"Description."
			::= { sleV2Dhcp4Notification 4 }

		
		-- 1.3.6.1.4.1.6296.102.6.2.1.3.5
		sleV2Dhcp4SmartRelayUsageChanged NOTIFICATION-TYPE
			OBJECTS { sleV2Dhcp4ControlRequest, sleV2Dhcp4ControlTimeStamp, sleV2Dhcp4ControlReqResult, sleV2Dhcp4SmartRelayUsage }
			STATUS current
			DESCRIPTION 
				"Description."
			::= { sleV2Dhcp4Notification 5 }

		
		-- 1.3.6.1.4.1.6296.102.6.2.1.3.6
		sleV2Dhcp4Option82UsageChanged NOTIFICATION-TYPE
			OBJECTS { sleV2Dhcp4ControlRequest, sleV2Dhcp4ControlTimeStamp, sleV2Dhcp4ControlReqResult, sleV2Dhcp4Option82Usage }
			STATUS current
			DESCRIPTION 
				"Description."
			::= { sleV2Dhcp4Notification 6 }

		
		-- 1.3.6.1.4.1.6296.102.6.2.1.3.7
		sleV2Dhcp4Option82PolicyChanged NOTIFICATION-TYPE
			OBJECTS { sleV2Dhcp4ControlRequest, sleV2Dhcp4ControlTimeStamp, sleV2Dhcp4ControlReqResult, sleV2Dhcp4Option82Drop, sleV2Dhcp4Option82Policy
				 }
			STATUS current
			DESCRIPTION 
				"Description."
			::= { sleV2Dhcp4Notification 7 }

		
		-- 1.3.6.1.4.1.6296.102.6.2.1.3.8
		sleV2Dhcp4Option82TrustDefaultChanged NOTIFICATION-TYPE
			OBJECTS { sleV2Dhcp4ControlRequest, sleV2Dhcp4ControlTimeStamp, sleV2Dhcp4ControlReqResult, sleV2Dhcp4Option82TrustDefault }
			STATUS current
			DESCRIPTION 
				"Description."
			::= { sleV2Dhcp4Notification 8 }

		
		-- 1.3.6.1.4.1.6296.102.6.2.1.3.9
		sleV2Dhcp4Option82SystemRemoteIdChanged NOTIFICATION-TYPE
			OBJECTS { sleV2Dhcp4ControlRequest, sleV2Dhcp4ControlTimeStamp, sleV2Dhcp4ControlReqResult, sleV2Dhcp4Option82SystemRemoteId, sleV2Dhcp4Option82SystemRemoteType
				 }
			STATUS current
			DESCRIPTION 
				"Description."
			::= { sleV2Dhcp4Notification 9 }

		
		-- 1.3.6.1.4.1.6296.102.6.2.1.3.10
		sleV2Dhcp4DatabaseKeyChanged NOTIFICATION-TYPE
			OBJECTS { sleV2Dhcp4ControlRequest, sleV2Dhcp4ControlTimeStamp, sleV2Dhcp4ControlReqResult, sleV2Dhcp4DatabaseKey }
			STATUS current
			DESCRIPTION 
				"Description."
			::= { sleV2Dhcp4Notification 10 }

		
		-- 1.3.6.1.4.1.6296.102.6.2.1.3.11
		sleV2Dhcp4DebugStatusChanged NOTIFICATION-TYPE
			OBJECTS { sleV2Dhcp4ControlRequest, sleV2Dhcp4ControlTimeStamp, sleV2Dhcp4ControlReqResult, sleV2Dhcp4DebugStatus }
			STATUS current
			DESCRIPTION 
				"Description."
			::= { sleV2Dhcp4Notification 11 }

		
		-- 1.3.6.1.4.1.6296.102.6.2.1.3.12
		sleV2Dhcp4AuthoArpTimeChanged NOTIFICATION-TYPE
			OBJECTS { sleV2Dhcp4ControlRequest, sleV2Dhcp4ControlTimeStamp, sleV2Dhcp4ControlReqResult, sleV2Dhcp4AuthArpTime, sleV2Dhcp4AuthArpReadyTime
				 }
			STATUS current
			DESCRIPTION 
				"Description."
			::= { sleV2Dhcp4Notification 12 }

		
		-- 1.3.6.1.4.1.6296.102.6.2.1.3.13
		sleV2Dhcp4ClientHardwareAddressChanged NOTIFICATION-TYPE
			OBJECTS { sleV2Dhcp4ControlRequest, sleV2Dhcp4ControlTimeStamp, sleV2Dhcp4ControlReqResult, sleV2Dhcp4ControlClientHardwareAddress }
			STATUS current
			DESCRIPTION 
				"Description."
			::= { sleV2Dhcp4Notification 13 }

		
		-- 1.3.6.1.4.1.6296.102.6.2.1.3.14
		sleV2Dhcp4PEStatusChanged NOTIFICATION-TYPE
			OBJECTS { sleV2Dhcp4ControlRequest, sleV2Dhcp4ControlTimeStamp, sleV2Dhcp4ControlReqResult, sleV2Dhcp4ControlPEStatus }
			STATUS current
			DESCRIPTION 
				"Description."
			::= { sleV2Dhcp4Notification 14 }

		
		-- 1.3.6.1.4.1.6296.102.6.2.1.3.15
		sleV2Dhcp4Option82SystemRemoteOptionChanged NOTIFICATION-TYPE
			OBJECTS { sleV2Dhcp4ControlRequest, sleV2Dhcp4ControlTimeStamp, sleV2Dhcp4ControlReqResult, sleV2Dhcp4ControlOption82SystemRemoteOption }
			STATUS current
			DESCRIPTION 
				"Description."
			::= { sleV2Dhcp4Notification 15 }

		
		-- 1.3.6.1.4.1.6296.102.6.2.1.3.16
		sleV2DhcpOption82SystemCirucitIdPortTypeChanged NOTIFICATION-TYPE
			OBJECTS { sleV2Dhcp4ControlRequest, sleV2Dhcp4ControlTimeStamp, sleV2Dhcp4ControlReqResult, sleV2Dhcp4ControlOption82SystemCircuitPortType }
			STATUS current
			DESCRIPTION 
				"setDhcpOption82SystemCircuitIdPortType"
			::= { sleV2Dhcp4Notification 16 }

		
		-- 1.3.6.1.4.1.6296.102.6.2.2
		sleV2Dhcp4Pool OBJECT IDENTIFIER ::= { sleV2Dhcp4 2 }

		
		-- 1.3.6.1.4.1.6296.102.6.2.2.1
		sleV2Dhcp4PoolBase OBJECT IDENTIFIER ::= { sleV2Dhcp4Pool 1 }

		
		-- 1.3.6.1.4.1.6296.102.6.2.2.1.1
		sleV2Dhcp4PoolTable OBJECT-TYPE
			SYNTAX SEQUENCE OF SleV2Dhcp4PoolEntry
			MAX-ACCESS not-accessible
			STATUS current
			DESCRIPTION
				"Description."
			::= { sleV2Dhcp4PoolBase 1 }

		
		-- 1.3.6.1.4.1.6296.102.6.2.2.1.1.1
		sleV2Dhcp4PoolEntry OBJECT-TYPE
			SYNTAX SleV2Dhcp4PoolEntry
			MAX-ACCESS not-accessible
			STATUS current
			DESCRIPTION
				"Description."
			INDEX { sleV2Dhcp4PoolIndex }
			::= { sleV2Dhcp4PoolTable 1 }

		
		SleV2Dhcp4PoolEntry ::=
			SEQUENCE { 
				sleV2Dhcp4PoolIndex
					INTEGER,
				sleV2Dhcp4PoolName
					OCTET STRING,
				sleV2Dhcp4PoolDefaultLeaseTime
					INTEGER,
				sleV2Dhcp4PoolMaxLeaseTime
					INTEGER,
				sleV2Dhcp4PoolDomainName
					OCTET STRING,
				sleV2Dhcp4PoolSummaryTotal
					Unsigned32,
				sleV2Dhcp4PoolSummaryAllocated
					Unsigned32,
				sleV2Dhcp4PoolSummaryBound
					Unsigned32,
				sleV2Dhcp4PoolSummaryOffered
					Unsigned32,
				sleV2Dhcp4PoolSummaryFixed
					Unsigned32,
				sleV2Dhcp4PoolSummaryAbandon
					Unsigned32,
				sleV2Dhcp4PoolSummaryAvailable
					Unsigned32,
				sleV2Dhcp4PoolMeritDumpPath
					OCTET STRING,
				sleV2Dhcp4PoolRootPath
					OCTET STRING,
				sleV2Dhcp4PoolSummaryNetwork
					Unsigned32
			 }

		-- 1.3.6.1.4.1.6296.102.6.2.2.1.1.1.1
		sleV2Dhcp4PoolIndex OBJECT-TYPE
			SYNTAX INTEGER (1..255)
			MAX-ACCESS read-only
			STATUS current
			DESCRIPTION
				"The Pool index"
			::= { sleV2Dhcp4PoolEntry 1 }

		
		-- 1.3.6.1.4.1.6296.102.6.2.2.1.1.1.2
		sleV2Dhcp4PoolName OBJECT-TYPE
			SYNTAX OCTET STRING (SIZE (1..32))
			MAX-ACCESS read-only
			STATUS current
			DESCRIPTION
				"The Pool name."
			::= { sleV2Dhcp4PoolEntry 2 }

		
		-- 1.3.6.1.4.1.6296.102.6.2.2.1.1.1.3
		sleV2Dhcp4PoolDefaultLeaseTime OBJECT-TYPE
			SYNTAX INTEGER (0 | 120..2147483637)
			UNITS "second"
			MAX-ACCESS read-only
			STATUS current
			DESCRIPTION
				"The default Time assigned to Lease in Pool.
				The value of 0 denotes that the default Time was not set."
			::= { sleV2Dhcp4PoolEntry 3 }

		
		-- 1.3.6.1.4.1.6296.102.6.2.2.1.1.1.4
		sleV2Dhcp4PoolMaxLeaseTime OBJECT-TYPE
			SYNTAX INTEGER (0 | 120..2147483637)
			UNITS "second"
			MAX-ACCESS read-only
			STATUS current
			DESCRIPTION
				"The max Time assigned to Lease in Pool.
				The value of 0 denotes that the max Time was not set"
			::= { sleV2Dhcp4PoolEntry 4 }

		
		-- 1.3.6.1.4.1.6296.102.6.2.2.1.1.1.5
		sleV2Dhcp4PoolDomainName OBJECT-TYPE
			SYNTAX OCTET STRING (SIZE (0 | 1..64))
			MAX-ACCESS read-only
			STATUS current
			DESCRIPTION
				"The Pool Domain Name."
			::= { sleV2Dhcp4PoolEntry 5 }

		
		-- 1.3.6.1.4.1.6296.102.6.2.2.1.1.1.6
		sleV2Dhcp4PoolSummaryTotal OBJECT-TYPE
			SYNTAX Unsigned32
			MAX-ACCESS read-only
			STATUS current
			DESCRIPTION
				"The number of Total Leases in Pool."
			::= { sleV2Dhcp4PoolEntry 6 }

		
		-- 1.3.6.1.4.1.6296.102.6.2.2.1.1.1.7
		sleV2Dhcp4PoolSummaryAllocated OBJECT-TYPE
			SYNTAX Unsigned32
			MAX-ACCESS read-only
			STATUS current
			DESCRIPTION
				"The number of Allocated Leases in Pool."
			::= { sleV2Dhcp4PoolEntry 7 }

		
		-- 1.3.6.1.4.1.6296.102.6.2.2.1.1.1.8
		sleV2Dhcp4PoolSummaryBound OBJECT-TYPE
			SYNTAX Unsigned32
			MAX-ACCESS read-only
			STATUS current
			DESCRIPTION
				"The number of Bound Leases in Pool."
			::= { sleV2Dhcp4PoolEntry 8 }

		
		-- 1.3.6.1.4.1.6296.102.6.2.2.1.1.1.9
		sleV2Dhcp4PoolSummaryOffered OBJECT-TYPE
			SYNTAX Unsigned32
			MAX-ACCESS read-only
			STATUS current
			DESCRIPTION
				"The number of Offered Leases in Pool."
			::= { sleV2Dhcp4PoolEntry 9 }

		
		-- 1.3.6.1.4.1.6296.102.6.2.2.1.1.1.10
		sleV2Dhcp4PoolSummaryFixed OBJECT-TYPE
			SYNTAX Unsigned32
			MAX-ACCESS read-only
			STATUS current
			DESCRIPTION
				"The number of Fixed Leases in Pool."
			::= { sleV2Dhcp4PoolEntry 10 }

		
		-- 1.3.6.1.4.1.6296.102.6.2.2.1.1.1.11
		sleV2Dhcp4PoolSummaryAbandon OBJECT-TYPE
			SYNTAX Unsigned32
			MAX-ACCESS read-only
			STATUS current
			DESCRIPTION
				"The number of Abandon Leases in Pool."
			::= { sleV2Dhcp4PoolEntry 11 }

		
		-- 1.3.6.1.4.1.6296.102.6.2.2.1.1.1.12
		sleV2Dhcp4PoolSummaryAvailable OBJECT-TYPE
			SYNTAX Unsigned32
			MAX-ACCESS read-only
			STATUS current
			DESCRIPTION
				"The number of Available Leases in Pool."
			::= { sleV2Dhcp4PoolEntry 12 }

		
		-- 1.3.6.1.4.1.6296.102.6.2.2.1.1.1.13
		sleV2Dhcp4PoolMeritDumpPath OBJECT-TYPE
			SYNTAX OCTET STRING (SIZE (1..255))
			MAX-ACCESS read-only
			STATUS current
			DESCRIPTION
				"This value specifies the path name of a file which the client's core image should be dumped in the event the client crashes."
			::= { sleV2Dhcp4PoolEntry 13 }

		
		-- 1.3.6.1.4.1.6296.102.6.2.2.1.1.1.14
		sleV2Dhcp4PoolRootPath OBJECT-TYPE
			SYNTAX OCTET STRING (SIZE (1..255))
			MAX-ACCESS read-only
			STATUS current
			DESCRIPTION
				"Description."
			::= { sleV2Dhcp4PoolEntry 14 }

		
		-- 1.3.6.1.4.1.6296.102.6.2.2.1.1.1.15
		sleV2Dhcp4PoolSummaryNetwork OBJECT-TYPE
			SYNTAX Unsigned32
			MAX-ACCESS read-only
			STATUS current
			DESCRIPTION
				"Description."
			::= { sleV2Dhcp4PoolEntry 15 }

		
		-- 1.3.6.1.4.1.6296.102.6.2.2.1.2
		sleV2Dhcp4PoolControl OBJECT IDENTIFIER ::= { sleV2Dhcp4PoolBase 2 }

		
		-- 1.3.6.1.4.1.6296.102.6.2.2.1.2.1
		sleV2Dhcp4PoolControlRequest OBJECT-TYPE
			SYNTAX INTEGER
				{
				createDhcpPool(1),
				destroyDhcpPool(2),
				setPoolDhcpLeaseTimeProfile(3),
				setPoolDhcpDomainName(4),
				setPoolDhcpOriginProfile(5),
				setPoolDhcpMeritDumpPath(6),
				setPoolDhcpRootPath(7)
				}
			MAX-ACCESS read-write
			STATUS current
			DESCRIPTION
				"The request of a user command."
			::= { sleV2Dhcp4PoolControl 1 }

		
		-- 1.3.6.1.4.1.6296.102.6.2.2.1.2.2
		sleV2Dhcp4PoolControlStatus OBJECT-TYPE
			SYNTAX SleControlStatusType
			MAX-ACCESS read-only
			STATUS current
			DESCRIPTION
				"The status of a user command."
			::= { sleV2Dhcp4PoolControl 2 }

		
		-- 1.3.6.1.4.1.6296.102.6.2.2.1.2.3
		sleV2Dhcp4PoolControlTimer OBJECT-TYPE
			SYNTAX Gauge32
			MAX-ACCESS read-write
			STATUS current
			DESCRIPTION
				"The maximum wait Time for the manager for a long running user command."
			::= { sleV2Dhcp4PoolControl 3 }

		
		-- 1.3.6.1.4.1.6296.102.6.2.2.1.2.4
		sleV2Dhcp4PoolControlTimeStamp OBJECT-TYPE
			SYNTAX TimeTicks
			MAX-ACCESS read-only
			STATUS current
			DESCRIPTION
				"The Time stamp of the last command (end of command)."
			::= { sleV2Dhcp4PoolControl 4 }

		
		-- 1.3.6.1.4.1.6296.102.6.2.2.1.2.5
		sleV2Dhcp4PoolControlReqResult OBJECT-TYPE
			SYNTAX SleControlRequestResultType
			MAX-ACCESS read-only
			STATUS current
			DESCRIPTION
				"The result of the last user command."
			::= { sleV2Dhcp4PoolControl 5 }

		
		-- 1.3.6.1.4.1.6296.102.6.2.2.1.2.6
		sleV2Dhcp4PoolControlIndex OBJECT-TYPE
			SYNTAX INTEGER (1..255)
			MAX-ACCESS read-write
			STATUS current
			DESCRIPTION
				"Description."
			::= { sleV2Dhcp4PoolControl 6 }

		
		-- 1.3.6.1.4.1.6296.102.6.2.2.1.2.7
		sleV2Dhcp4PoolControlName OBJECT-TYPE
			SYNTAX OCTET STRING (SIZE (1..32))
			MAX-ACCESS read-write
			STATUS current
			DESCRIPTION
				"The Pool name."
			::= { sleV2Dhcp4PoolControl 7 }

		
		-- 1.3.6.1.4.1.6296.102.6.2.2.1.2.8
		sleV2Dhcp4PoolControlDefaultLeaseTime OBJECT-TYPE
			SYNTAX INTEGER (0 | 120..2147483637)
			UNITS "second"
			MAX-ACCESS read-write
			STATUS current
			DESCRIPTION
				"The default Time assigned to Lease in Pool.
				If 0, the default Time is clear"
			DEFVAL { 3600 }
			::= { sleV2Dhcp4PoolControl 8 }

		
		-- 1.3.6.1.4.1.6296.102.6.2.2.1.2.9
		sleV2Dhcp4PoolControlMaxLeaseTime OBJECT-TYPE
			SYNTAX INTEGER (0 | 120..2147483637)
			UNITS "second"
			MAX-ACCESS read-write
			STATUS current
			DESCRIPTION
				"The max Time assigned to Lease in Pool.
				If 0, the max Time is clear."
			DEFVAL { 3600 }
			::= { sleV2Dhcp4PoolControl 9 }

		
		-- 1.3.6.1.4.1.6296.102.6.2.2.1.2.10
		sleV2Dhcp4PoolControlDomainName OBJECT-TYPE
			SYNTAX OCTET STRING (SIZE (0 | 1..64))
			MAX-ACCESS read-write
			STATUS current
			DESCRIPTION
				"."
			::= { sleV2Dhcp4PoolControl 10 }

		
		-- 1.3.6.1.4.1.6296.102.6.2.2.1.2.11
		sleV2Dhcp4PoolControlOriginURL OBJECT-TYPE
			SYNTAX IpAddress
			MAX-ACCESS read-write
			STATUS current
			DESCRIPTION
				"."
			::= { sleV2Dhcp4PoolControl 11 }

		
		-- 1.3.6.1.4.1.6296.102.6.2.2.1.2.12
		sleV2Dhcp4PoolControlOriginFileName OBJECT-TYPE
			SYNTAX OCTET STRING (SIZE (0 | 1..64))
			MAX-ACCESS read-write
			STATUS current
			DESCRIPTION
				"."
			::= { sleV2Dhcp4PoolControl 12 }

		
		-- 1.3.6.1.4.1.6296.102.6.2.2.1.2.13
		sleV2Dhcp4PoolControlMeritDumpPath OBJECT-TYPE
			SYNTAX OCTET STRING (SIZE (1..255))
			MAX-ACCESS read-write
			STATUS current
			DESCRIPTION
				"Description."
			::= { sleV2Dhcp4PoolControl 13 }

		
		-- 1.3.6.1.4.1.6296.102.6.2.2.1.2.14
		sleV2Dhcp4PoolControlRootPath OBJECT-TYPE
			SYNTAX OCTET STRING (SIZE (1..255))
			MAX-ACCESS read-write
			STATUS current
			DESCRIPTION
				"Description."
			::= { sleV2Dhcp4PoolControl 14 }

		
		-- 1.3.6.1.4.1.6296.102.6.2.2.1.3
		sleV2Dhcp4PoolNotification OBJECT IDENTIFIER ::= { sleV2Dhcp4PoolBase 3 }

		
		-- 1.3.6.1.4.1.6296.102.6.2.2.1.3.1
		sleV2Dhcp4PoolCreated NOTIFICATION-TYPE
			OBJECTS { sleV2Dhcp4PoolName, sleV2Dhcp4PoolDefaultLeaseTime, sleV2Dhcp4PoolMaxLeaseTime, sleV2Dhcp4PoolDomainName, sleV2Dhcp4PoolControlRequest, 
				sleV2Dhcp4PoolControlTimeStamp, sleV2Dhcp4PoolControlReqResult, sleV2Dhcp4PoolMeritDumpPath, sleV2Dhcp4PoolRootPath }
			STATUS current
			DESCRIPTION 
				"Description."
			::= { sleV2Dhcp4PoolNotification 1 }

		
		-- 1.3.6.1.4.1.6296.102.6.2.2.1.3.2
		sleV2Dhcp4PoolDestroyed NOTIFICATION-TYPE
			OBJECTS { sleV2Dhcp4PoolControlRequest, sleV2Dhcp4PoolControlTimeStamp, sleV2Dhcp4PoolControlReqResult, sleV2Dhcp4PoolControlIndex }
			STATUS current
			DESCRIPTION 
				"Description."
			::= { sleV2Dhcp4PoolNotification 2 }

		
		-- 1.3.6.1.4.1.6296.102.6.2.2.1.3.3
		sleV2Dhcp4PoolLeaseTimeProfileChanged NOTIFICATION-TYPE
			OBJECTS { sleV2Dhcp4PoolDefaultLeaseTime, sleV2Dhcp4PoolMaxLeaseTime, sleV2Dhcp4PoolControlRequest, sleV2Dhcp4PoolControlTimeStamp, sleV2Dhcp4PoolControlReqResult
				 }
			STATUS current
			DESCRIPTION 
				"Description."
			::= { sleV2Dhcp4PoolNotification 3 }

		
		-- 1.3.6.1.4.1.6296.102.6.2.2.1.3.4
		sleV2Dhcp4PoolDomainNameChanged NOTIFICATION-TYPE
			OBJECTS { sleV2Dhcp4PoolControlRequest, sleV2Dhcp4PoolControlTimeStamp, sleV2Dhcp4PoolControlReqResult, sleV2Dhcp4PoolDomainName }
			STATUS current
			DESCRIPTION 
				"Description."
			::= { sleV2Dhcp4PoolNotification 4 }

		
		-- 1.3.6.1.4.1.6296.102.6.2.2.1.3.5
		sleV2Dhcp4PoolOriginProfileChanged NOTIFICATION-TYPE
			OBJECTS { sleV2Dhcp4PoolControlRequest, sleV2Dhcp4PoolControlTimeStamp, sleV2Dhcp4PoolControlReqResult, sleV2Dhcp4PoolControlOriginURL, sleV2Dhcp4PoolControlOriginFileName
				 }
			STATUS current
			DESCRIPTION 
				"Description."
			::= { sleV2Dhcp4PoolNotification 5 }

		
		-- 1.3.6.1.4.1.6296.102.6.2.2.1.3.6
		sleV2Dhcp4PoolMeritDumpPathChanged NOTIFICATION-TYPE
			OBJECTS { sleV2Dhcp4PoolControlRequest, sleV2Dhcp4PoolControlTimeStamp, sleV2Dhcp4PoolControlReqResult, sleV2Dhcp4PoolMeritDumpPath }
			STATUS current
			DESCRIPTION 
				"Description."
			::= { sleV2Dhcp4PoolNotification 6 }

		
		-- 1.3.6.1.4.1.6296.102.6.2.2.1.3.7
		sleV2Dhcp4PoolRootPathChanged NOTIFICATION-TYPE
			OBJECTS { sleV2Dhcp4PoolControlRequest, sleV2Dhcp4PoolControlTimeStamp, sleV2Dhcp4PoolControlReqResult, sleV2Dhcp4PoolRootPath }
			STATUS current
			DESCRIPTION 
				"Description."
			::= { sleV2Dhcp4PoolNotification 7 }

		
		-- 1.3.6.1.4.1.6296.102.6.2.2.2
		sleV2Dhcp4Network OBJECT IDENTIFIER ::= { sleV2Dhcp4Pool 2 }

		
		-- 1.3.6.1.4.1.6296.102.6.2.2.2.1
		sleV2Dhcp4NetworkTable OBJECT-TYPE
			SYNTAX SEQUENCE OF SleV2Dhcp4NetworkEntry
			MAX-ACCESS not-accessible
			STATUS current
			DESCRIPTION
				"Description."
			::= { sleV2Dhcp4Network 1 }

		
		-- 1.3.6.1.4.1.6296.102.6.2.2.2.1.1
		sleV2Dhcp4NetworkEntry OBJECT-TYPE
			SYNTAX SleV2Dhcp4NetworkEntry
			MAX-ACCESS not-accessible
			STATUS current
			DESCRIPTION
				"Description."
			INDEX { sleV2Dhcp4PoolIndex, sleV2Dhcp4NetworkAddress, sleV2Dhcp4NetworkMask }
			::= { sleV2Dhcp4NetworkTable 1 }

		
		SleV2Dhcp4NetworkEntry ::=
			SEQUENCE { 
				sleV2Dhcp4NetworkAddress
					IpAddress,
				sleV2Dhcp4NetworkMask
					INTEGER
			 }

		-- 1.3.6.1.4.1.6296.102.6.2.2.2.1.1.1
		sleV2Dhcp4NetworkAddress OBJECT-TYPE
			SYNTAX IpAddress
			MAX-ACCESS read-only
			STATUS current
			DESCRIPTION
				"The Subnet IP Address."
			::= { sleV2Dhcp4NetworkEntry 1 }

		
		-- 1.3.6.1.4.1.6296.102.6.2.2.2.1.1.2
		sleV2Dhcp4NetworkMask OBJECT-TYPE
			SYNTAX INTEGER (1..32)
			MAX-ACCESS read-only
			STATUS current
			DESCRIPTION
				"The Subnet Mask prefix length."
			::= { sleV2Dhcp4NetworkEntry 2 }

		
		-- 1.3.6.1.4.1.6296.102.6.2.2.2.2
		sleV2Dhcp4NetworkControl OBJECT IDENTIFIER ::= { sleV2Dhcp4Network 2 }

		
		-- 1.3.6.1.4.1.6296.102.6.2.2.2.2.1
		sleV2Dhcp4NetworkControlRequest OBJECT-TYPE
			SYNTAX INTEGER
				{
				createDhcpNetwork(1),
				destroyDhcpNetwork(2)
				}
			MAX-ACCESS read-write
			STATUS current
			DESCRIPTION
				"The request of a user command."
			::= { sleV2Dhcp4NetworkControl 1 }

		
		-- 1.3.6.1.4.1.6296.102.6.2.2.2.2.2
		sleV2Dhcp4NetworkControlStatus OBJECT-TYPE
			SYNTAX SleControlStatusType
			MAX-ACCESS read-only
			STATUS current
			DESCRIPTION
				"The status of a user command."
			::= { sleV2Dhcp4NetworkControl 2 }

		
		-- 1.3.6.1.4.1.6296.102.6.2.2.2.2.3
		sleV2Dhcp4NetworkControlTimer OBJECT-TYPE
			SYNTAX Gauge32
			MAX-ACCESS read-write
			STATUS current
			DESCRIPTION
				"The maximum wait Time for the manager for a long running user command."
			::= { sleV2Dhcp4NetworkControl 3 }

		
		-- 1.3.6.1.4.1.6296.102.6.2.2.2.2.4
		sleV2Dhcp4NetworkControlTimeStamp OBJECT-TYPE
			SYNTAX TimeTicks
			MAX-ACCESS read-only
			STATUS current
			DESCRIPTION
				"The Time stamp of the last command (end of command)."
			::= { sleV2Dhcp4NetworkControl 4 }

		
		-- 1.3.6.1.4.1.6296.102.6.2.2.2.2.5
		sleV2Dhcp4NetworkControlReqResult OBJECT-TYPE
			SYNTAX SleControlRequestResultType
			MAX-ACCESS read-only
			STATUS current
			DESCRIPTION
				"The result of the last user command."
			::= { sleV2Dhcp4NetworkControl 5 }

		
		-- 1.3.6.1.4.1.6296.102.6.2.2.2.2.6
		sleV2Dhcp4NetworkControlPoolIndex OBJECT-TYPE
			SYNTAX INTEGER (1..255)
			MAX-ACCESS read-write
			STATUS current
			DESCRIPTION
				"Description."
			::= { sleV2Dhcp4NetworkControl 6 }

		
		-- 1.3.6.1.4.1.6296.102.6.2.2.2.2.7
		sleV2Dhcp4NetworkControlAddress OBJECT-TYPE
			SYNTAX IpAddress
			MAX-ACCESS read-only
			STATUS current
			DESCRIPTION
				"The result of the last user command."
			::= { sleV2Dhcp4NetworkControl 7 }

		
		-- 1.3.6.1.4.1.6296.102.6.2.2.2.2.8
		sleV2Dhcp4NetworkControlMask OBJECT-TYPE
			SYNTAX INTEGER (1..32)
			MAX-ACCESS read-only
			STATUS current
			DESCRIPTION
				"The result of the last user command."
			::= { sleV2Dhcp4NetworkControl 8 }

		
		-- 1.3.6.1.4.1.6296.102.6.2.2.2.3
		sleV2Dhcp4NetworkNotification OBJECT IDENTIFIER ::= { sleV2Dhcp4Network 3 }

		
		-- 1.3.6.1.4.1.6296.102.6.2.2.2.3.1
		sleV2Dhcp4NetworkCreated NOTIFICATION-TYPE
			OBJECTS { sleV2Dhcp4NetworkControlRequest, sleV2Dhcp4NetworkControlTimeStamp, sleV2Dhcp4NetworkControlReqResult, sleV2Dhcp4NetworkControlPoolIndex, sleV2Dhcp4NetworkControlAddress, 
				sleV2Dhcp4NetworkControlMask }
			STATUS current
			DESCRIPTION 
				"Description."
			::= { sleV2Dhcp4NetworkNotification 1 }

		
		-- 1.3.6.1.4.1.6296.102.6.2.2.2.3.2
		sleV2Dhcp4NetworkDestroyed NOTIFICATION-TYPE
			OBJECTS { sleV2Dhcp4NetworkControlRequest, sleV2Dhcp4NetworkControlTimeStamp, sleV2Dhcp4NetworkControlReqResult, sleV2Dhcp4NetworkControlPoolIndex, sleV2Dhcp4NetworkControlAddress, 
				sleV2Dhcp4NetworkControlMask }
			STATUS current
			DESCRIPTION 
				"Description."
			::= { sleV2Dhcp4NetworkNotification 2 }

		
		-- 1.3.6.1.4.1.6296.102.6.2.2.3
		sleV2Dhcp4Range OBJECT IDENTIFIER ::= { sleV2Dhcp4Pool 3 }

		
		-- 1.3.6.1.4.1.6296.102.6.2.2.3.1
		sleV2Dhcp4RangeTable OBJECT-TYPE
			SYNTAX SEQUENCE OF SleV2Dhcp4RangeEntry
			MAX-ACCESS not-accessible
			STATUS current
			DESCRIPTION
				"Description."
			::= { sleV2Dhcp4Range 1 }

		
		-- 1.3.6.1.4.1.6296.102.6.2.2.3.1.1
		sleV2Dhcp4RangeEntry OBJECT-TYPE
			SYNTAX SleV2Dhcp4RangeEntry
			MAX-ACCESS not-accessible
			STATUS current
			DESCRIPTION
				"Description."
			INDEX { sleV2Dhcp4PoolIndex, sleV2Dhcp4RangeStart, sleV2Dhcp4RangeEnd }
			::= { sleV2Dhcp4RangeTable 1 }

		
		SleV2Dhcp4RangeEntry ::=
			SEQUENCE { 
				sleV2Dhcp4RangeStart
					IpAddress,
				sleV2Dhcp4RangeEnd
					IpAddress
			 }

		-- 1.3.6.1.4.1.6296.102.6.2.2.3.1.1.1
		sleV2Dhcp4RangeStart OBJECT-TYPE
			SYNTAX IpAddress
			MAX-ACCESS read-only
			STATUS current
			DESCRIPTION
				"The start IP of subnet's range."
			::= { sleV2Dhcp4RangeEntry 1 }

		
		-- 1.3.6.1.4.1.6296.102.6.2.2.3.1.1.2
		sleV2Dhcp4RangeEnd OBJECT-TYPE
			SYNTAX IpAddress
			MAX-ACCESS read-only
			STATUS current
			DESCRIPTION
				"The end IP of subnet's range."
			::= { sleV2Dhcp4RangeEntry 2 }

		
		-- 1.3.6.1.4.1.6296.102.6.2.2.3.2
		sleV2Dhcp4RangeControl OBJECT IDENTIFIER ::= { sleV2Dhcp4Range 2 }

		
		-- 1.3.6.1.4.1.6296.102.6.2.2.3.2.1
		sleV2Dhcp4RangeControlRequest OBJECT-TYPE
			SYNTAX INTEGER
				{
				createDhcpRange(1),
				destroyDhcpRange(2)
				}
			MAX-ACCESS read-write
			STATUS current
			DESCRIPTION
				"The request of a user command."
			::= { sleV2Dhcp4RangeControl 1 }

		
		-- 1.3.6.1.4.1.6296.102.6.2.2.3.2.2
		sleV2Dhcp4RangeControlStatus OBJECT-TYPE
			SYNTAX SleControlStatusType
			MAX-ACCESS read-only
			STATUS current
			DESCRIPTION
				"The status of a user command."
			::= { sleV2Dhcp4RangeControl 2 }

		
		-- 1.3.6.1.4.1.6296.102.6.2.2.3.2.3
		sleV2Dhcp4RangeControlTimer OBJECT-TYPE
			SYNTAX Gauge32
			MAX-ACCESS read-write
			STATUS current
			DESCRIPTION
				"The maximum wait Time for the manager for a long running user command."
			::= { sleV2Dhcp4RangeControl 3 }

		
		-- 1.3.6.1.4.1.6296.102.6.2.2.3.2.4
		sleV2Dhcp4RangeControlTimeStamp OBJECT-TYPE
			SYNTAX TimeTicks
			MAX-ACCESS read-only
			STATUS current
			DESCRIPTION
				"The Time stamp of the last command (end of command)."
			::= { sleV2Dhcp4RangeControl 4 }

		
		-- 1.3.6.1.4.1.6296.102.6.2.2.3.2.5
		sleV2Dhcp4RangeControlReqResult OBJECT-TYPE
			SYNTAX SleControlRequestResultType
			MAX-ACCESS read-only
			STATUS current
			DESCRIPTION
				"The result of the last user command."
			::= { sleV2Dhcp4RangeControl 5 }

		
		-- 1.3.6.1.4.1.6296.102.6.2.2.3.2.6
		sleV2Dhcp4RangeControlPoolIndex OBJECT-TYPE
			SYNTAX INTEGER (1..255)
			MAX-ACCESS read-write
			STATUS current
			DESCRIPTION
				"Description."
			::= { sleV2Dhcp4RangeControl 6 }

		
		-- 1.3.6.1.4.1.6296.102.6.2.2.3.2.7
		sleV2Dhcp4RangeControlStart OBJECT-TYPE
			SYNTAX IpAddress
			MAX-ACCESS read-write
			STATUS current
			DESCRIPTION
				"Description."
			::= { sleV2Dhcp4RangeControl 7 }

		
		-- 1.3.6.1.4.1.6296.102.6.2.2.3.2.8
		sleV2Dhcp4RangeControlEnd OBJECT-TYPE
			SYNTAX IpAddress
			MAX-ACCESS read-write
			STATUS current
			DESCRIPTION
				"Description."
			::= { sleV2Dhcp4RangeControl 8 }

		
		-- 1.3.6.1.4.1.6296.102.6.2.2.3.3
		sleV2Dhcp4RangeNotification OBJECT IDENTIFIER ::= { sleV2Dhcp4Range 3 }

		
		-- 1.3.6.1.4.1.6296.102.6.2.2.3.3.1
		sleV2Dhcp4RangeCreated NOTIFICATION-TYPE
			OBJECTS { sleV2Dhcp4RangeControlRequest, sleV2Dhcp4RangeControlTimeStamp, sleV2Dhcp4RangeControlReqResult, sleV2Dhcp4RangeControlPoolIndex, sleV2Dhcp4RangeControlStart, 
				sleV2Dhcp4RangeControlEnd }
			STATUS current
			DESCRIPTION 
				"Description."
			::= { sleV2Dhcp4RangeNotification 1 }

		
		-- 1.3.6.1.4.1.6296.102.6.2.2.3.3.2
		sleV2Dhcp4RangeDestroyed NOTIFICATION-TYPE
			OBJECTS { sleV2Dhcp4RangeControlRequest, sleV2Dhcp4RangeControlTimeStamp, sleV2Dhcp4RangeControlReqResult, sleV2Dhcp4RangeControlPoolIndex, sleV2Dhcp4RangeControlStart, 
				sleV2Dhcp4RangeControlEnd }
			STATUS current
			DESCRIPTION 
				"Description."
			::= { sleV2Dhcp4RangeNotification 2 }

		
		-- 1.3.6.1.4.1.6296.102.6.2.2.4
		sleV2Dhcp4Fixed OBJECT IDENTIFIER ::= { sleV2Dhcp4Pool 4 }

		
		-- 1.3.6.1.4.1.6296.102.6.2.2.4.1
		sleV2Dhcp4FixedTable OBJECT-TYPE
			SYNTAX SEQUENCE OF SleV2Dhcp4FixedEntry
			MAX-ACCESS not-accessible
			STATUS current
			DESCRIPTION
				"Description."
			::= { sleV2Dhcp4Fixed 1 }

		
		-- 1.3.6.1.4.1.6296.102.6.2.2.4.1.1
		sleV2Dhcp4FixedEntry OBJECT-TYPE
			SYNTAX SleV2Dhcp4FixedEntry
			MAX-ACCESS not-accessible
			STATUS current
			DESCRIPTION
				"Description."
			INDEX { sleV2Dhcp4PoolIndex, sleV2Dhcp4FixedMac, sleV2Dhcp4FixedAddress }
			::= { sleV2Dhcp4FixedTable 1 }

		
		SleV2Dhcp4FixedEntry ::=
			SEQUENCE { 
				sleV2Dhcp4FixedMac
					MacAddress,
				sleV2Dhcp4FixedAddress
					IpAddress
			 }

		-- 1.3.6.1.4.1.6296.102.6.2.2.4.1.1.1
		sleV2Dhcp4FixedMac OBJECT-TYPE
			SYNTAX MacAddress
			MAX-ACCESS read-only
			STATUS current
			DESCRIPTION
				"The MAC address for the fixed Lease."
			::= { sleV2Dhcp4FixedEntry 1 }

		
		-- 1.3.6.1.4.1.6296.102.6.2.2.4.1.1.2
		sleV2Dhcp4FixedAddress OBJECT-TYPE
			SYNTAX IpAddress
			MAX-ACCESS read-only
			STATUS current
			DESCRIPTION
				"The IP address for the fixed Lease."
			::= { sleV2Dhcp4FixedEntry 2 }

		
		-- 1.3.6.1.4.1.6296.102.6.2.2.4.2
		sleV2Dhcp4FixedControl OBJECT IDENTIFIER ::= { sleV2Dhcp4Fixed 2 }

		
		-- 1.3.6.1.4.1.6296.102.6.2.2.4.2.1
		sleV2Dhcp4FixedControlRequest OBJECT-TYPE
			SYNTAX INTEGER
				{
				createDhcpFixed(1),
				destroyDhcpFixed(2)
				}
			MAX-ACCESS read-write
			STATUS current
			DESCRIPTION
				"The request of a user command."
			::= { sleV2Dhcp4FixedControl 1 }

		
		-- 1.3.6.1.4.1.6296.102.6.2.2.4.2.2
		sleV2Dhcp4FixedControlStatus OBJECT-TYPE
			SYNTAX SleControlStatusType
			MAX-ACCESS read-only
			STATUS current
			DESCRIPTION
				"The status of a user command."
			::= { sleV2Dhcp4FixedControl 2 }

		
		-- 1.3.6.1.4.1.6296.102.6.2.2.4.2.3
		sleV2Dhcp4FixedControlTimer OBJECT-TYPE
			SYNTAX Gauge32
			MAX-ACCESS read-write
			STATUS current
			DESCRIPTION
				"The maximum wait Time for the manager for a long running user command."
			::= { sleV2Dhcp4FixedControl 3 }

		
		-- 1.3.6.1.4.1.6296.102.6.2.2.4.2.4
		sleV2Dhcp4FixedControlTimeStamp OBJECT-TYPE
			SYNTAX TimeTicks
			MAX-ACCESS read-only
			STATUS current
			DESCRIPTION
				"The Time stamp of the last command (end of command)."
			::= { sleV2Dhcp4FixedControl 4 }

		
		-- 1.3.6.1.4.1.6296.102.6.2.2.4.2.5
		sleV2Dhcp4FixedControlReqResult OBJECT-TYPE
			SYNTAX SleControlRequestResultType
			MAX-ACCESS read-only
			STATUS current
			DESCRIPTION
				"The result of the last user command."
			::= { sleV2Dhcp4FixedControl 5 }

		
		-- 1.3.6.1.4.1.6296.102.6.2.2.4.2.6
		sleV2Dhcp4FixedControlPoolIndex OBJECT-TYPE
			SYNTAX INTEGER (1..255)
			MAX-ACCESS read-write
			STATUS current
			DESCRIPTION
				"Description."
			::= { sleV2Dhcp4FixedControl 6 }

		
		-- 1.3.6.1.4.1.6296.102.6.2.2.4.2.7
		sleV2Dhcp4FixedControlAddress OBJECT-TYPE
			SYNTAX IpAddress
			MAX-ACCESS read-write
			STATUS current
			DESCRIPTION
				"Description."
			::= { sleV2Dhcp4FixedControl 7 }

		
		-- 1.3.6.1.4.1.6296.102.6.2.2.4.2.8
		sleV2Dhcp4FixedControlMac OBJECT-TYPE
			SYNTAX MacAddress
			MAX-ACCESS read-write
			STATUS current
			DESCRIPTION
				"Description."
			::= { sleV2Dhcp4FixedControl 8 }

		
		-- 1.3.6.1.4.1.6296.102.6.2.2.4.3
		sleV2Dhcp4FixedNotification OBJECT IDENTIFIER ::= { sleV2Dhcp4Fixed 3 }

		
		-- 1.3.6.1.4.1.6296.102.6.2.2.4.3.1
		sleV2Dhcp4FixedCreated NOTIFICATION-TYPE
			OBJECTS { sleV2Dhcp4FixedControlRequest, sleV2Dhcp4FixedControlTimeStamp, sleV2Dhcp4FixedControlReqResult, sleV2Dhcp4FixedControlPoolIndex, sleV2Dhcp4FixedControlAddress, 
				sleV2Dhcp4FixedControlMac }
			STATUS current
			DESCRIPTION 
				"Description."
			::= { sleV2Dhcp4FixedNotification 1 }

		
		-- 1.3.6.1.4.1.6296.102.6.2.2.4.3.2
		sleV2Dhcp4FixedDestroyed NOTIFICATION-TYPE
			OBJECTS { sleV2Dhcp4FixedControlRequest, sleV2Dhcp4FixedControlTimeStamp, sleV2Dhcp4FixedControlReqResult, sleV2Dhcp4FixedControlPoolIndex, sleV2Dhcp4FixedControlAddress, 
				sleV2Dhcp4FixedControlMac }
			STATUS current
			DESCRIPTION 
				"Description."
			::= { sleV2Dhcp4FixedNotification 2 }

		
		-- 1.3.6.1.4.1.6296.102.6.2.2.5
		sleV2Dhcp4Dns OBJECT IDENTIFIER ::= { sleV2Dhcp4Pool 5 }

		
		-- 1.3.6.1.4.1.6296.102.6.2.2.5.1
		sleV2Dhcp4DnsTable OBJECT-TYPE
			SYNTAX SEQUENCE OF SleV2Dhcp4DnsEntry
			MAX-ACCESS not-accessible
			STATUS current
			DESCRIPTION
				"Description."
			::= { sleV2Dhcp4Dns 1 }

		
		-- 1.3.6.1.4.1.6296.102.6.2.2.5.1.1
		sleV2Dhcp4DnsEntry OBJECT-TYPE
			SYNTAX SleV2Dhcp4DnsEntry
			MAX-ACCESS not-accessible
			STATUS current
			DESCRIPTION
				"Description."
			INDEX { sleV2Dhcp4PoolIndex, sleV2Dhcp4DnsIndex }
			::= { sleV2Dhcp4DnsTable 1 }

		
		SleV2Dhcp4DnsEntry ::=
			SEQUENCE { 
				sleV2Dhcp4DnsIndex
					INTEGER,
				sleV2Dhcp4DnsAddress
					IpAddress
			 }

		-- 1.3.6.1.4.1.6296.102.6.2.2.5.1.1.1
		sleV2Dhcp4DnsIndex OBJECT-TYPE
			SYNTAX INTEGER (1..8)
			MAX-ACCESS read-only
			STATUS current
			DESCRIPTION
				"Description."
			::= { sleV2Dhcp4DnsEntry 1 }

		
		-- 1.3.6.1.4.1.6296.102.6.2.2.5.1.1.2
		sleV2Dhcp4DnsAddress OBJECT-TYPE
			SYNTAX IpAddress
			MAX-ACCESS read-only
			STATUS current
			DESCRIPTION
				"The Ip address of Dns setting in Dhcp server daemon.
				"
			::= { sleV2Dhcp4DnsEntry 2 }

		
		-- 1.3.6.1.4.1.6296.102.6.2.2.5.2
		sleV2Dhcp4DnsControl OBJECT IDENTIFIER ::= { sleV2Dhcp4Dns 2 }

		
		-- 1.3.6.1.4.1.6296.102.6.2.2.5.2.1
		sleV2Dhcp4DnsControlRequest OBJECT-TYPE
			SYNTAX INTEGER
				{
				createDhcpDns(1),
				destroyDhcpDns(2)
				}
			MAX-ACCESS read-write
			STATUS current
			DESCRIPTION
				"The request of a user command.
				create될때는 항상 insert방식이면 개수가 넘쳐나면
				실패한다.
				destroy할때는 그 번호만을 삭제한다. 없으면 실패.삭제된 후에
				뒤의 index들은 앞으로 당겨진다.
				
				이러한 동작은 gateway나 option에서도 마찬가지이다."
			::= { sleV2Dhcp4DnsControl 1 }

		
		-- 1.3.6.1.4.1.6296.102.6.2.2.5.2.2
		sleV2Dhcp4DnsControlStatus OBJECT-TYPE
			SYNTAX SleControlStatusType
			MAX-ACCESS read-only
			STATUS current
			DESCRIPTION
				"The status of a user command."
			::= { sleV2Dhcp4DnsControl 2 }

		
		-- 1.3.6.1.4.1.6296.102.6.2.2.5.2.3
		sleV2Dhcp4DnsControlTimer OBJECT-TYPE
			SYNTAX Gauge32
			MAX-ACCESS read-write
			STATUS current
			DESCRIPTION
				"The maximum wait Time for the manager for a long running user command."
			::= { sleV2Dhcp4DnsControl 3 }

		
		-- 1.3.6.1.4.1.6296.102.6.2.2.5.2.4
		sleV2Dhcp4DnsControlTimeStamp OBJECT-TYPE
			SYNTAX TimeTicks
			MAX-ACCESS read-only
			STATUS current
			DESCRIPTION
				"The Time stamp of the last command (end of command)."
			::= { sleV2Dhcp4DnsControl 4 }

		
		-- 1.3.6.1.4.1.6296.102.6.2.2.5.2.5
		sleV2Dhcp4DnsControlReqResult OBJECT-TYPE
			SYNTAX SleControlRequestResultType
			MAX-ACCESS read-write
			STATUS current
			DESCRIPTION
				"The result of the last user command."
			::= { sleV2Dhcp4DnsControl 5 }

		
		-- 1.3.6.1.4.1.6296.102.6.2.2.5.2.6
		sleV2Dhcp4DnsControlPoolIndex OBJECT-TYPE
			SYNTAX INTEGER (1..255)
			MAX-ACCESS read-write
			STATUS current
			DESCRIPTION
				"Description."
			::= { sleV2Dhcp4DnsControl 6 }

		
		-- 1.3.6.1.4.1.6296.102.6.2.2.5.2.7
		sleV2Dhcp4DnsControlIndex OBJECT-TYPE
			SYNTAX INTEGER (0 | 1..8)
			MAX-ACCESS read-write
			STATUS current
			DESCRIPTION
				"Description."
			::= { sleV2Dhcp4DnsControl 7 }

		
		-- 1.3.6.1.4.1.6296.102.6.2.2.5.2.8
		sleV2Dhcp4DnsControlAddress OBJECT-TYPE
			SYNTAX IpAddress
			MAX-ACCESS read-write
			STATUS current
			DESCRIPTION
				"Description."
			::= { sleV2Dhcp4DnsControl 8 }

		
		-- 1.3.6.1.4.1.6296.102.6.2.2.5.3
		sleV2Dhcp4DnsNotification OBJECT IDENTIFIER ::= { sleV2Dhcp4Dns 3 }

		
		-- 1.3.6.1.4.1.6296.102.6.2.2.5.3.1
		sleV2Dhcp4DnsCreated NOTIFICATION-TYPE
			OBJECTS { sleV2Dhcp4DnsControlRequest, sleV2Dhcp4DnsControlTimeStamp, sleV2Dhcp4DnsControlReqResult, sleV2Dhcp4DnsAddress }
			STATUS current
			DESCRIPTION 
				"Description."
			::= { sleV2Dhcp4DnsNotification 1 }

		
		-- 1.3.6.1.4.1.6296.102.6.2.2.5.3.2
		sleV2Dhcp4DnsDestroyed NOTIFICATION-TYPE
			OBJECTS { sleV2Dhcp4DnsControlRequest, sleV2Dhcp4DnsControlTimeStamp, sleV2Dhcp4DnsControlReqResult, sleV2Dhcp4DnsControlPoolIndex, sleV2Dhcp4DnsControlIndex
				 }
			STATUS current
			DESCRIPTION 
				"The sleDnsIp is 0.0.0.0 for CLI 
				'no ip dhcp default-config dns-server'"
			::= { sleV2Dhcp4DnsNotification 2 }

		
		-- 1.3.6.1.4.1.6296.102.6.2.2.6
		sleV2Dhcp4DefaultGateway OBJECT IDENTIFIER ::= { sleV2Dhcp4Pool 6 }

		
		-- 1.3.6.1.4.1.6296.102.6.2.2.6.1
		sleV2Dhcp4DefaultGatewayTable OBJECT-TYPE
			SYNTAX SEQUENCE OF SleV2Dhcp4DefaultGatewayEntry
			MAX-ACCESS not-accessible
			STATUS current
			DESCRIPTION
				"Description."
			::= { sleV2Dhcp4DefaultGateway 1 }

		
		-- 1.3.6.1.4.1.6296.102.6.2.2.6.1.1
		sleV2Dhcp4DefaultGatewayEntry OBJECT-TYPE
			SYNTAX SleV2Dhcp4DefaultGatewayEntry
			MAX-ACCESS not-accessible
			STATUS current
			DESCRIPTION
				"Description."
			INDEX { sleV2Dhcp4PoolIndex, sleV2Dhcp4DefaultGatewayIndex }
			::= { sleV2Dhcp4DefaultGatewayTable 1 }

		
		SleV2Dhcp4DefaultGatewayEntry ::=
			SEQUENCE { 
				sleV2Dhcp4DefaultGatewayIndex
					INTEGER,
				sleV2Dhcp4DefaultGatewayAddress
					IpAddress
			 }

		-- 1.3.6.1.4.1.6296.102.6.2.2.6.1.1.1
		sleV2Dhcp4DefaultGatewayIndex OBJECT-TYPE
			SYNTAX INTEGER (1..8)
			MAX-ACCESS read-only
			STATUS current
			DESCRIPTION
				"Description."
			::= { sleV2Dhcp4DefaultGatewayEntry 1 }

		
		-- 1.3.6.1.4.1.6296.102.6.2.2.6.1.1.2
		sleV2Dhcp4DefaultGatewayAddress OBJECT-TYPE
			SYNTAX IpAddress
			MAX-ACCESS read-only
			STATUS current
			DESCRIPTION
				"The Gateway IP assigned to leases of the Subnet."
			::= { sleV2Dhcp4DefaultGatewayEntry 2 }

		
		-- 1.3.6.1.4.1.6296.102.6.2.2.6.2
		sleV2Dhcp4DefaultGatewayControl OBJECT IDENTIFIER ::= { sleV2Dhcp4DefaultGateway 2 }

		
		-- 1.3.6.1.4.1.6296.102.6.2.2.6.2.1
		sleV2Dhcp4DefaultGatewayControlRequest OBJECT-TYPE
			SYNTAX INTEGER
				{
				createDhcpDefaultGateway(1),
				destroyDhcpDefaultGateway(2)
				}
			MAX-ACCESS read-write
			STATUS current
			DESCRIPTION
				"The request of a user command."
			::= { sleV2Dhcp4DefaultGatewayControl 1 }

		
		-- 1.3.6.1.4.1.6296.102.6.2.2.6.2.2
		sleV2Dhcp4DefaultGatewayControlStatus OBJECT-TYPE
			SYNTAX SleControlStatusType
			MAX-ACCESS read-only
			STATUS current
			DESCRIPTION
				"The status of a user command."
			::= { sleV2Dhcp4DefaultGatewayControl 2 }

		
		-- 1.3.6.1.4.1.6296.102.6.2.2.6.2.3
		sleV2Dhcp4DefaultGatewayControlTimer OBJECT-TYPE
			SYNTAX Gauge32
			MAX-ACCESS read-write
			STATUS current
			DESCRIPTION
				"The maximum wait Time for the manager for a long running user command."
			::= { sleV2Dhcp4DefaultGatewayControl 3 }

		
		-- 1.3.6.1.4.1.6296.102.6.2.2.6.2.4
		sleV2Dhcp4DefaultGatewayControlTimeStamp OBJECT-TYPE
			SYNTAX TimeTicks
			MAX-ACCESS read-only
			STATUS current
			DESCRIPTION
				"The Time stamp of the last command (end of command)."
			::= { sleV2Dhcp4DefaultGatewayControl 4 }

		
		-- 1.3.6.1.4.1.6296.102.6.2.2.6.2.5
		sleV2Dhcp4DefaultGatewayControlReqResult OBJECT-TYPE
			SYNTAX SleControlRequestResultType
			MAX-ACCESS read-only
			STATUS current
			DESCRIPTION
				"The result of the last user command."
			::= { sleV2Dhcp4DefaultGatewayControl 5 }

		
		-- 1.3.6.1.4.1.6296.102.6.2.2.6.2.6
		sleV2Dhcp4DefaultGatewayControlPoolIndex OBJECT-TYPE
			SYNTAX INTEGER (1..255)
			MAX-ACCESS read-write
			STATUS current
			DESCRIPTION
				"The Pool name."
			::= { sleV2Dhcp4DefaultGatewayControl 6 }

		
		-- 1.3.6.1.4.1.6296.102.6.2.2.6.2.7
		sleV2Dhcp4DefaultGatewayControlIndex OBJECT-TYPE
			SYNTAX INTEGER (0 | 1..8)
			MAX-ACCESS read-write
			STATUS current
			DESCRIPTION
				"Description."
			::= { sleV2Dhcp4DefaultGatewayControl 7 }

		
		-- 1.3.6.1.4.1.6296.102.6.2.2.6.2.8
		sleV2Dhcp4DefaultGatewayControlAddress OBJECT-TYPE
			SYNTAX IpAddress
			MAX-ACCESS read-write
			STATUS current
			DESCRIPTION
				"The Gateway IP assigned to Subnet."
			::= { sleV2Dhcp4DefaultGatewayControl 8 }

		
		-- 1.3.6.1.4.1.6296.102.6.2.2.6.3
		sleV2Dhcp4DefaultGatewayNotification OBJECT IDENTIFIER ::= { sleV2Dhcp4DefaultGateway 3 }

		
		-- 1.3.6.1.4.1.6296.102.6.2.2.6.3.1
		sleV2Dhcp4DefaultGatewayCreated NOTIFICATION-TYPE
			OBJECTS { sleV2Dhcp4DefaultGatewayControlRequest, sleV2Dhcp4DefaultGatewayControlTimeStamp, sleV2Dhcp4DefaultGatewayControlReqResult, sleV2Dhcp4DefaultGatewayAddress }
			STATUS current
			DESCRIPTION 
				"Description."
			::= { sleV2Dhcp4DefaultGatewayNotification 1 }

		
		-- 1.3.6.1.4.1.6296.102.6.2.2.6.3.2
		sleV2Dhcp4DefaultGatewayDestroyed NOTIFICATION-TYPE
			OBJECTS { sleV2Dhcp4DefaultGatewayControlRequest, sleV2Dhcp4DefaultGatewayControlReqResult, sleV2Dhcp4DefaultGatewayControlTimeStamp, sleV2Dhcp4DefaultGatewayControlPoolIndex, sleV2Dhcp4DefaultGatewayControlIndex
				 }
			STATUS current
			DESCRIPTION 
				"The sleDefaultGatewayIp is 0.0.0.0 for CLI 
				'no default-gateway all'"
			::= { sleV2Dhcp4DefaultGatewayNotification 2 }

		
		-- 1.3.6.1.4.1.6296.102.6.2.2.7
		sleV2Dhcp4Option OBJECT IDENTIFIER ::= { sleV2Dhcp4Pool 7 }

		
		-- 1.3.6.1.4.1.6296.102.6.2.2.7.1
		sleV2Dhcp4OptionTable OBJECT-TYPE
			SYNTAX SEQUENCE OF SleV2Dhcp4OptionEntry
			MAX-ACCESS not-accessible
			STATUS current
			DESCRIPTION
				"Description."
			::= { sleV2Dhcp4Option 1 }

		
		-- 1.3.6.1.4.1.6296.102.6.2.2.7.1.1
		sleV2Dhcp4OptionEntry OBJECT-TYPE
			SYNTAX SleV2Dhcp4OptionEntry
			MAX-ACCESS not-accessible
			STATUS current
			DESCRIPTION
				"Description."
			INDEX { sleV2Dhcp4PoolIndex, sleV2Dhcp4OptionCode, sleV2Dhcp4OptionInstance }
			::= { sleV2Dhcp4OptionTable 1 }

		
		SleV2Dhcp4OptionEntry ::=
			SEQUENCE { 
				sleV2Dhcp4OptionCode
					INTEGER,
				sleV2Dhcp4OptionInstance
					INTEGER,
				sleV2Dhcp4OptionType
					INTEGER,
				sleV2Dhcp4OptionValue
					OCTET STRING
			 }

		-- 1.3.6.1.4.1.6296.102.6.2.2.7.1.1.1
		sleV2Dhcp4OptionCode OBJECT-TYPE
			SYNTAX INTEGER
				{
				subnetMask(1),
				timeOffset(2),
				router(3),
				timeServer(4),
				nameServer(5),
				domainNameServer(6),
				logServer(7),
				cookieServer(8),
				lprServer(9),
				impressServer(10),
				resourceLocationServer(11),
				hostName(12),
				bootFileSize(13),
				meritFile(14),
				domainName(15),
				swapServer(16),
				rootPath(17),
				extensionsPath(18),
				ipForwardState(19),
				nonLocalSourceRoutingState(20),
				policyFilter(21),
				maximumDatagramReassemblySize(22),
				defaultIpTimeToLive(23),
				pathMtuAgingTimeout(24),
				pathMtuPlateauTable(25),
				interfaceMtu(26),
				allSubnetsAreLocal(27),
				broadcastAddress(28),
				performMaskDiscovery(29),
				maskSupplier(30),
				performRouterDiscovery(31),
				routerSolicitationAddress(32),
				staticRoute(33),
				trailerEncapsulation(34),
				arpCacheTimeout(35),
				ethernetEncapsulationOption(36),
				tcpDefaultTtl(37),
				tcpKeepaliveInterval(38),
				tcpKeepaliveGarbage(39),
				nisDomain(40),
				nisServers(41),
				networkTimeProtocolServers(42),
				vendorSpecificInformation(43),
				netbiosOverTcpIpNameServer(44),
				netbiosOverTcpIpDatagramDistributionServer(45),
				netbiosOverTcpIpNodeType(46),
				netbiosOverTcpIpScope(47),
				xWindowSystemFontServer(48),
				xWindowSystemDisplayManager(49),
				requestedIpAddress(50),
				ipAddressLeaseTime(51),
				optionOverload(52),
				dhcpMessageType(53),
				serverIdentifier(54),
				parameterRequestList(55),
				message(56),
				maximumDhcpMessageSize(57),
				renewalTimeValue(58),
				rebindingTimeValue(59),
				vendorClassIdentifier(60),
				clientIdentifier(61),
				nisPlusDomain(64),
				nisPlusServers(65),
				tftpServerName(66),
				bootFileName(67),
				mobileIpHomeAgent(68),
				smtpServer(69),
				pop3Server(70),
				nntpServer(71),
				wwwServer(72),
				defaultFingerServer(73),
				ircServer(74),
				streetTalkServer(75),
				stdaServer(76)
				}
			MAX-ACCESS read-only
			STATUS current
			DESCRIPTION
				"3: default Gateway
				4: DNS Server"
			::= { sleV2Dhcp4OptionEntry 1 }

		
		-- 1.3.6.1.4.1.6296.102.6.2.2.7.1.1.2
		sleV2Dhcp4OptionInstance OBJECT-TYPE
			SYNTAX INTEGER (1..8)
			MAX-ACCESS read-only
			STATUS current
			DESCRIPTION
				"Description."
			::= { sleV2Dhcp4OptionEntry 2 }

		
		-- 1.3.6.1.4.1.6296.102.6.2.2.7.1.1.3
		sleV2Dhcp4OptionType OBJECT-TYPE
			SYNTAX INTEGER
				{
				ipaddress(1),
				hex(2),
				text(3)
				}
			MAX-ACCESS read-only
			STATUS current
			DESCRIPTION
				"Description."
			::= { sleV2Dhcp4OptionEntry 3 }

		
		-- 1.3.6.1.4.1.6296.102.6.2.2.7.1.1.4
		sleV2Dhcp4OptionValue OBJECT-TYPE
			SYNTAX OCTET STRING (SIZE (1..64))
			MAX-ACCESS read-only
			STATUS current
			DESCRIPTION
				"Description."
			::= { sleV2Dhcp4OptionEntry 4 }

		
		-- 1.3.6.1.4.1.6296.102.6.2.2.7.2
		sleV2Dhcp4OptionControl OBJECT IDENTIFIER ::= { sleV2Dhcp4Option 2 }

		
		-- 1.3.6.1.4.1.6296.102.6.2.2.7.2.1
		sleV2Dhcp4OptionControlRequest OBJECT-TYPE
			SYNTAX INTEGER
				{
				createDhcpOption(1),
				destoryDhcpOption(2)
				}
			MAX-ACCESS read-write
			STATUS current
			DESCRIPTION
				"The request of a user command."
			::= { sleV2Dhcp4OptionControl 1 }

		
		-- 1.3.6.1.4.1.6296.102.6.2.2.7.2.2
		sleV2Dhcp4OptionControlStatus OBJECT-TYPE
			SYNTAX SleControlStatusType
			MAX-ACCESS read-only
			STATUS current
			DESCRIPTION
				"The status of a user command."
			::= { sleV2Dhcp4OptionControl 2 }

		
		-- 1.3.6.1.4.1.6296.102.6.2.2.7.2.3
		sleV2Dhcp4OptionControlTimer OBJECT-TYPE
			SYNTAX Gauge32
			MAX-ACCESS read-write
			STATUS current
			DESCRIPTION
				"The maximum wait Time for the manager for a long running user command."
			::= { sleV2Dhcp4OptionControl 3 }

		
		-- 1.3.6.1.4.1.6296.102.6.2.2.7.2.4
		sleV2Dhcp4OptionControlTimeStamp OBJECT-TYPE
			SYNTAX TimeTicks
			MAX-ACCESS read-only
			STATUS current
			DESCRIPTION
				"The Time stamp of the last command (end of command)."
			::= { sleV2Dhcp4OptionControl 4 }

		
		-- 1.3.6.1.4.1.6296.102.6.2.2.7.2.5
		sleV2Dhcp4OptionControlReqResult OBJECT-TYPE
			SYNTAX SleControlRequestResultType
			MAX-ACCESS read-only
			STATUS current
			DESCRIPTION
				"The result of the last user command."
			::= { sleV2Dhcp4OptionControl 5 }

		
		-- 1.3.6.1.4.1.6296.102.6.2.2.7.2.6
		sleV2Dhcp4OptionControlPoolIndex OBJECT-TYPE
			SYNTAX INTEGER (1..255)
			MAX-ACCESS read-write
			STATUS current
			DESCRIPTION
				"Description."
			::= { sleV2Dhcp4OptionControl 6 }

		
		-- 1.3.6.1.4.1.6296.102.6.2.2.7.2.7
		sleV2Dhcp4OptionControlCode OBJECT-TYPE
			SYNTAX INTEGER
				{
				timeOffset(2),
				timeServer(4),
				nameServer(5),
				logServer(7),
				cookieServer(8),
				lprServer(9),
				impressServer(10),
				resourceLocationServer(11),
				swapServer(16),
				rootPath(17),
				ipForwardState(19),
				nonLocalSourceRoutingState(20),
				policyFilter(21),
				maximumDatagramReassemblySize(22),
				defaultIpTimeToLive(23),
				pathMtuAgingTimeout(24),
				interfaceMtu(26),
				allSubnetsAreLocal(27),
				broadcastAddress(28),
				performMaskDiscovery(29),
				maskSupplier(30),
				performRouterDiscovery(31),
				routerSolicitationAddress(32),
				staticRoute(33),
				trailerEncapsulation(34),
				arpCacheTimeout(35),
				ethernetEncapsulationOption(36),
				tcpDefaultTtl(37),
				tcpKeepaliveInterval(38),
				tcpKeepaliveGarbage(39),
				nisDomain(40),
				nisServers(41),
				networkTimeProtocolServers(42),
				xWindowSystemFontServer(48),
				xWindowSystemDisplayManager(49),
				nisPlusDomain(64),
				nisPlusServers(65),
				tftpServerName(66),
				mobileIpHomeAgent(68),
				smtpServer(69),
				pop3Server(70),
				nntpServer(71),
				wwwServer(72),
				defaultFingerServer(73),
				ircServer(74),
				streetTalkServer(75),
				stdaServer(76)
				}
			MAX-ACCESS read-write
			STATUS current
			DESCRIPTION
				"Description."
			::= { sleV2Dhcp4OptionControl 7 }

		
		-- 1.3.6.1.4.1.6296.102.6.2.2.7.2.8
		sleV2Dhcp4OptionControlInstance OBJECT-TYPE
			SYNTAX INTEGER (0 | 1..8)
			MAX-ACCESS read-write
			STATUS current
			DESCRIPTION
				"Description."
			::= { sleV2Dhcp4OptionControl 8 }

		
		-- 1.3.6.1.4.1.6296.102.6.2.2.7.2.9
		sleV2Dhcp4OptionControlType OBJECT-TYPE
			SYNTAX INTEGER
				{
				ipaddress(1),
				hex(2),
				text(3)
				}
			MAX-ACCESS read-write
			STATUS current
			DESCRIPTION
				"Description."
			::= { sleV2Dhcp4OptionControl 9 }

		
		-- 1.3.6.1.4.1.6296.102.6.2.2.7.2.10
		sleV2Dhcp4OptionControlValue OBJECT-TYPE
			SYNTAX OCTET STRING (SIZE (1..64))
			MAX-ACCESS read-write
			STATUS current
			DESCRIPTION
				"Description."
			::= { sleV2Dhcp4OptionControl 10 }

		
		-- 1.3.6.1.4.1.6296.102.6.2.2.7.3
		sleV2Dhcp4OptionNotification OBJECT IDENTIFIER ::= { sleV2Dhcp4Option 3 }

		
		-- 1.3.6.1.4.1.6296.102.6.2.2.7.3.1
		sleV2Dhcp4OptionCreated NOTIFICATION-TYPE
			OBJECTS { sleV2Dhcp4OptionControlRequest, sleV2Dhcp4OptionControlReqResult, sleV2Dhcp4OptionControlTimeStamp, sleV2Dhcp4OptionType, sleV2Dhcp4OptionValue
				 }
			STATUS current
			DESCRIPTION 
				"Description."
			::= { sleV2Dhcp4OptionNotification 1 }

		
		-- 1.3.6.1.4.1.6296.102.6.2.2.7.3.2
		sleV2Dhcp4OptionDestroyed NOTIFICATION-TYPE
			OBJECTS { sleV2Dhcp4OptionControlRequest, sleV2Dhcp4OptionControlTimeStamp, sleV2Dhcp4OptionControlReqResult, sleV2Dhcp4OptionControlPoolIndex, sleV2Dhcp4OptionControlCode, 
				sleV2Dhcp4OptionControlInstance }
			STATUS current
			DESCRIPTION 
				"Description."
			::= { sleV2Dhcp4OptionNotification 2 }

		
		-- 1.3.6.1.4.1.6296.102.6.2.2.8
		sleV2Dhcp4Logs OBJECT IDENTIFIER ::= { sleV2Dhcp4Pool 8 }

		
		-- 1.3.6.1.4.1.6296.102.6.2.2.8.1
		sleV2Dhcp4LogsTable OBJECT-TYPE
			SYNTAX SEQUENCE OF SleV2Dhcp4LogsEntry
			MAX-ACCESS not-accessible
			STATUS current
			DESCRIPTION
				"Description."
			::= { sleV2Dhcp4Logs 1 }

		
		-- 1.3.6.1.4.1.6296.102.6.2.2.8.1.1
		sleV2Dhcp4LogsEntry OBJECT-TYPE
			SYNTAX SleV2Dhcp4LogsEntry
			MAX-ACCESS not-accessible
			STATUS current
			DESCRIPTION
				"Description."
			INDEX { sleV2Dhcp4PoolIndex, sleV2Dhcp4LogsIndex }
			::= { sleV2Dhcp4LogsTable 1 }

		
		SleV2Dhcp4LogsEntry ::=
			SEQUENCE { 
				sleV2Dhcp4LogsIndex
					INTEGER,
				sleV2Dhcp4LogsAddress
					IpAddress
			 }

		-- 1.3.6.1.4.1.6296.102.6.2.2.8.1.1.1
		sleV2Dhcp4LogsIndex OBJECT-TYPE
			SYNTAX INTEGER (1..3)
			MAX-ACCESS read-only
			STATUS current
			DESCRIPTION
				"The index of Log server setting in DHCP server daemon"
			::= { sleV2Dhcp4LogsEntry 1 }

		
		-- 1.3.6.1.4.1.6296.102.6.2.2.8.1.1.2
		sleV2Dhcp4LogsAddress OBJECT-TYPE
			SYNTAX IpAddress
			MAX-ACCESS read-only
			STATUS current
			DESCRIPTION
				"The IP address of Log server setting in DHCP server daemon"
			::= { sleV2Dhcp4LogsEntry 2 }

		
		-- 1.3.6.1.4.1.6296.102.6.2.2.8.2
		sleV2Dhcp4LogsControl OBJECT IDENTIFIER ::= { sleV2Dhcp4Logs 2 }

		
		-- 1.3.6.1.4.1.6296.102.6.2.2.8.2.1
		sleV2Dhcp4LogsControlRequest OBJECT-TYPE
			SYNTAX INTEGER
				{
				createDhcpLogs(1),
				destroyDhcpLogs(2)
				}
			MAX-ACCESS read-write
			STATUS current
			DESCRIPTION
				"Description."
			::= { sleV2Dhcp4LogsControl 1 }

		
		-- 1.3.6.1.4.1.6296.102.6.2.2.8.2.2
		sleV2Dhcp4LogsControlStatus OBJECT-TYPE
			SYNTAX SleControlStatusType
			MAX-ACCESS read-only
			STATUS current
			DESCRIPTION
				"Description."
			::= { sleV2Dhcp4LogsControl 2 }

		
		-- 1.3.6.1.4.1.6296.102.6.2.2.8.2.3
		sleV2Dhcp4LogsControlTimer OBJECT-TYPE
			SYNTAX Gauge32
			MAX-ACCESS read-write
			STATUS current
			DESCRIPTION
				"Description."
			::= { sleV2Dhcp4LogsControl 3 }

		
		-- 1.3.6.1.4.1.6296.102.6.2.2.8.2.4
		sleV2Dhcp4LogsControlTimeStamp OBJECT-TYPE
			SYNTAX TimeTicks
			MAX-ACCESS read-only
			STATUS current
			DESCRIPTION
				"Description."
			::= { sleV2Dhcp4LogsControl 4 }

		
		-- 1.3.6.1.4.1.6296.102.6.2.2.8.2.5
		sleV2Dhcp4LogsControlReqResult OBJECT-TYPE
			SYNTAX SleControlRequestResultType
			MAX-ACCESS read-only
			STATUS current
			DESCRIPTION
				"Description."
			::= { sleV2Dhcp4LogsControl 5 }

		
		-- 1.3.6.1.4.1.6296.102.6.2.2.8.2.6
		sleV2Dhcp4LogsControlPoolIndex OBJECT-TYPE
			SYNTAX INTEGER (1..255)
			MAX-ACCESS read-write
			STATUS current
			DESCRIPTION
				"The index of DCHP pool"
			::= { sleV2Dhcp4LogsControl 6 }

		
		-- 1.3.6.1.4.1.6296.102.6.2.2.8.2.7
		sleV2Dhcp4LogsControlIndex OBJECT-TYPE
			SYNTAX INTEGER (0 | 1..3)
			MAX-ACCESS read-write
			STATUS current
			DESCRIPTION
				"The index of Log server setting in DHCP server daemon"
			::= { sleV2Dhcp4LogsControl 7 }

		
		-- 1.3.6.1.4.1.6296.102.6.2.2.8.2.8
		sleV2Dhcp4LogsControlAddress OBJECT-TYPE
			SYNTAX IpAddress
			MAX-ACCESS read-write
			STATUS current
			DESCRIPTION
				"The IP address of Log server setting in DHCP server daemon"
			::= { sleV2Dhcp4LogsControl 8 }

		
		-- 1.3.6.1.4.1.6296.102.6.2.2.8.3
		sleV2Dhcp4LogsNotification OBJECT IDENTIFIER ::= { sleV2Dhcp4Logs 3 }

		
		-- 1.3.6.1.4.1.6296.102.6.2.2.8.3.1
		sleV2Dhcp4LogsCreated NOTIFICATION-TYPE
			OBJECTS { sleV2Dhcp4LogsControlRequest, sleV2Dhcp4LogsControlTimeStamp, sleV2Dhcp4LogsControlReqResult, sleV2Dhcp4LogsAddress }
			STATUS current
			DESCRIPTION 
				"Description."
			::= { sleV2Dhcp4LogsNotification 1 }

		
		-- 1.3.6.1.4.1.6296.102.6.2.2.8.3.2
		sleV2Dhcp4LogsDestroyed NOTIFICATION-TYPE
			OBJECTS { sleV2Dhcp4LogsControlRequest, sleV2Dhcp4LogsControlTimeStamp, sleV2Dhcp4LogsControlReqResult, sleV2Dhcp4LogsControlIndex }
			STATUS current
			DESCRIPTION 
				"Description."
			::= { sleV2Dhcp4LogsNotification 2 }

		
		-- 1.3.6.1.4.1.6296.102.6.2.2.9
		sleV2Dhcp4Ntp OBJECT IDENTIFIER ::= { sleV2Dhcp4Pool 9 }

		
		-- 1.3.6.1.4.1.6296.102.6.2.2.9.1
		sleV2Dhcp4NtpTable OBJECT-TYPE
			SYNTAX SEQUENCE OF SleV2Dhcp4NtpEntry
			MAX-ACCESS not-accessible
			STATUS current
			DESCRIPTION
				"Description."
			::= { sleV2Dhcp4Ntp 1 }

		
		-- 1.3.6.1.4.1.6296.102.6.2.2.9.1.1
		sleV2Dhcp4NtpEntry OBJECT-TYPE
			SYNTAX SleV2Dhcp4NtpEntry
			MAX-ACCESS not-accessible
			STATUS current
			DESCRIPTION
				"Description."
			INDEX { sleV2Dhcp4PoolIndex, sleV2Dhcp4NtpIndex }
			::= { sleV2Dhcp4NtpTable 1 }

		
		SleV2Dhcp4NtpEntry ::=
			SEQUENCE { 
				sleV2Dhcp4NtpIndex
					INTEGER,
				sleV2Dhcp4NtpAddress
					IpAddress
			 }

		-- 1.3.6.1.4.1.6296.102.6.2.2.9.1.1.1
		sleV2Dhcp4NtpIndex OBJECT-TYPE
			SYNTAX INTEGER (1..3)
			MAX-ACCESS read-only
			STATUS current
			DESCRIPTION
				"The index of Ntp server setting in DHCP server daemon"
			::= { sleV2Dhcp4NtpEntry 1 }

		
		-- 1.3.6.1.4.1.6296.102.6.2.2.9.1.1.2
		sleV2Dhcp4NtpAddress OBJECT-TYPE
			SYNTAX IpAddress
			MAX-ACCESS read-only
			STATUS current
			DESCRIPTION
				"The IP address of Ntp server setting in DHCP server daemon"
			::= { sleV2Dhcp4NtpEntry 2 }

		
		-- 1.3.6.1.4.1.6296.102.6.2.2.9.2
		sleV2Dhcp4NtpControl OBJECT IDENTIFIER ::= { sleV2Dhcp4Ntp 2 }

		
		-- 1.3.6.1.4.1.6296.102.6.2.2.9.2.1
		sleV2Dhcp4NtpControlRequest OBJECT-TYPE
			SYNTAX INTEGER
				{
				createDhcpNtp(1),
				destroyDhcpNtp(2)
				}
			MAX-ACCESS read-write
			STATUS current
			DESCRIPTION
				"Description."
			::= { sleV2Dhcp4NtpControl 1 }

		
		-- 1.3.6.1.4.1.6296.102.6.2.2.9.2.2
		sleV2Dhcp4NtpControlStatus OBJECT-TYPE
			SYNTAX SleControlStatusType
			MAX-ACCESS read-only
			STATUS current
			DESCRIPTION
				"Description."
			::= { sleV2Dhcp4NtpControl 2 }

		
		-- 1.3.6.1.4.1.6296.102.6.2.2.9.2.3
		sleV2Dhcp4NtpControlTimer OBJECT-TYPE
			SYNTAX Gauge32
			MAX-ACCESS read-write
			STATUS current
			DESCRIPTION
				"Description."
			::= { sleV2Dhcp4NtpControl 3 }

		
		-- 1.3.6.1.4.1.6296.102.6.2.2.9.2.4
		sleV2Dhcp4NtpControlTimeStamp OBJECT-TYPE
			SYNTAX TimeTicks
			MAX-ACCESS read-only
			STATUS current
			DESCRIPTION
				"Description."
			::= { sleV2Dhcp4NtpControl 4 }

		
		-- 1.3.6.1.4.1.6296.102.6.2.2.9.2.5
		sleV2Dhcp4NtpControlReqResult OBJECT-TYPE
			SYNTAX SleControlRequestResultType
			MAX-ACCESS read-only
			STATUS current
			DESCRIPTION
				"Description."
			::= { sleV2Dhcp4NtpControl 5 }

		
		-- 1.3.6.1.4.1.6296.102.6.2.2.9.2.6
		sleV2Dhcp4NtpControlPoolIndex OBJECT-TYPE
			SYNTAX INTEGER (1..255)
			MAX-ACCESS read-write
			STATUS current
			DESCRIPTION
				"The index of DCHP pool"
			::= { sleV2Dhcp4NtpControl 6 }

		
		-- 1.3.6.1.4.1.6296.102.6.2.2.9.2.7
		sleV2Dhcp4NtpControlIndex OBJECT-TYPE
			SYNTAX INTEGER (0 | 1..3)
			MAX-ACCESS read-write
			STATUS current
			DESCRIPTION
				"The index of Ntp server setting in DHCP server daemon"
			::= { sleV2Dhcp4NtpControl 7 }

		
		-- 1.3.6.1.4.1.6296.102.6.2.2.9.2.8
		sleV2Dhcp4NtpControlAddress OBJECT-TYPE
			SYNTAX IpAddress
			MAX-ACCESS read-write
			STATUS current
			DESCRIPTION
				"The IP address of Ntp server setting in DHCP server daemon"
			::= { sleV2Dhcp4NtpControl 8 }

		
		-- 1.3.6.1.4.1.6296.102.6.2.2.9.3
		sleV2Dhcp4NtpNotification OBJECT IDENTIFIER ::= { sleV2Dhcp4Ntp 3 }

		
		-- 1.3.6.1.4.1.6296.102.6.2.2.9.3.1
		sleV2Dhcp4NtpCreated NOTIFICATION-TYPE
			OBJECTS { sleV2Dhcp4NtpControlRequest, sleV2Dhcp4NtpControlTimeStamp, sleV2Dhcp4NtpControlReqResult, sleV2Dhcp4NtpAddress }
			STATUS current
			DESCRIPTION 
				"Description."
			::= { sleV2Dhcp4NtpNotification 1 }

		
		-- 1.3.6.1.4.1.6296.102.6.2.2.9.3.2
		sleV2Dhcp4NtpDestroyed NOTIFICATION-TYPE
			OBJECTS { sleV2Dhcp4NtpControlRequest, sleV2Dhcp4NtpControlTimeStamp, sleV2Dhcp4NtpControlReqResult, sleV2Dhcp4NtpControlPoolIndex, sleV2Dhcp4NtpControlIndex
				 }
			STATUS current
			DESCRIPTION 
				"Description."
			::= { sleV2Dhcp4NtpNotification 2 }

		
		-- 1.3.6.1.4.1.6296.102.6.2.2.10
		sleV2Dhcp4PE OBJECT IDENTIFIER ::= { sleV2Dhcp4Pool 10 }

		
		-- 1.3.6.1.4.1.6296.102.6.2.2.10.1
		sleV2Dhcp4PEVendor OBJECT IDENTIFIER ::= { sleV2Dhcp4PE 1 }

		
		-- 1.3.6.1.4.1.6296.102.6.2.2.10.1.1
		sleV2Dhcp4PEVendorTable OBJECT-TYPE
			SYNTAX SEQUENCE OF SleV2Dhcp4PEVendorEntry
			MAX-ACCESS not-accessible
			STATUS current
			DESCRIPTION
				"Description."
			::= { sleV2Dhcp4PEVendor 1 }

		
		-- 1.3.6.1.4.1.6296.102.6.2.2.10.1.1.1
		sleV2Dhcp4PEVendorEntry OBJECT-TYPE
			SYNTAX SleV2Dhcp4PEVendorEntry
			MAX-ACCESS not-accessible
			STATUS current
			DESCRIPTION
				"Description."
			INDEX { sleV2Dhcp4PEVendorPoolIndex, sleV2Dhcp4PEVendorIfIndex, sleV2Dhcp4PEVendorID, sleV2Dhcp4PEVendorStart }
			::= { sleV2Dhcp4PEVendorTable 1 }

		
		SleV2Dhcp4PEVendorEntry ::=
			SEQUENCE { 
				sleV2Dhcp4PEVendorPoolIndex
					INTEGER,
				sleV2Dhcp4PEVendorIfIndex
					INTEGER,
				sleV2Dhcp4PEVendorID
					OCTET STRING,
				sleV2Dhcp4PEVendorStart
					IpAddress,
				sleV2Dhcp4PEVendorEnd
					IpAddress
			 }

		-- 1.3.6.1.4.1.6296.102.6.2.2.10.1.1.1.1
		sleV2Dhcp4PEVendorPoolIndex OBJECT-TYPE
			SYNTAX INTEGER (1..255)
			MAX-ACCESS read-only
			STATUS current
			DESCRIPTION
				"The Pool index"
			::= { sleV2Dhcp4PEVendorEntry 1 }

		
		-- 1.3.6.1.4.1.6296.102.6.2.2.10.1.1.1.2
		sleV2Dhcp4PEVendorIfIndex OBJECT-TYPE
			SYNTAX INTEGER (1..512)
			MAX-ACCESS read-only
			STATUS current
			DESCRIPTION
				"Description."
			::= { sleV2Dhcp4PEVendorEntry 2 }

		
		-- 1.3.6.1.4.1.6296.102.6.2.2.10.1.1.1.3
		sleV2Dhcp4PEVendorID OBJECT-TYPE
			SYNTAX OCTET STRING (SIZE (0..32))
			MAX-ACCESS read-only
			STATUS current
			DESCRIPTION
				"Description."
			::= { sleV2Dhcp4PEVendorEntry 3 }

		
		-- 1.3.6.1.4.1.6296.102.6.2.2.10.1.1.1.4
		sleV2Dhcp4PEVendorStart OBJECT-TYPE
			SYNTAX IpAddress
			MAX-ACCESS read-only
			STATUS current
			DESCRIPTION
				"Description."
			::= { sleV2Dhcp4PEVendorEntry 4 }

		
		-- 1.3.6.1.4.1.6296.102.6.2.2.10.1.1.1.5
		sleV2Dhcp4PEVendorEnd OBJECT-TYPE
			SYNTAX IpAddress
			MAX-ACCESS read-only
			STATUS current
			DESCRIPTION
				"Description."
			::= { sleV2Dhcp4PEVendorEntry 5 }

		
		-- 1.3.6.1.4.1.6296.102.6.2.2.10.1.2
		sleV2Dhcp4PEVendorControl OBJECT IDENTIFIER ::= { sleV2Dhcp4PEVendor 2 }

		
		-- 1.3.6.1.4.1.6296.102.6.2.2.10.1.2.1
		sleV2Dhcp4PEVendorControlRequest OBJECT-TYPE
			SYNTAX INTEGER
				{
				createPEVendorEntry(1),
				destroyPEVendorEntry(2),
				destroyPEVendorEntryAll(3)
				}
			MAX-ACCESS read-write
			STATUS current
			DESCRIPTION
				"Description."
			::= { sleV2Dhcp4PEVendorControl 1 }

		
		-- 1.3.6.1.4.1.6296.102.6.2.2.10.1.2.2
		sleV2Dhcp4PEVendorControlStatus OBJECT-TYPE
			SYNTAX SleControlStatusType
			MAX-ACCESS read-only
			STATUS current
			DESCRIPTION
				"Description."
			::= { sleV2Dhcp4PEVendorControl 2 }

		
		-- 1.3.6.1.4.1.6296.102.6.2.2.10.1.2.3
		sleV2Dhcp4PEVendorControlTimer OBJECT-TYPE
			SYNTAX Gauge32
			MAX-ACCESS read-write
			STATUS current
			DESCRIPTION
				"Description."
			::= { sleV2Dhcp4PEVendorControl 3 }

		
		-- 1.3.6.1.4.1.6296.102.6.2.2.10.1.2.4
		sleV2Dhcp4PEVendorControlTimeStamp OBJECT-TYPE
			SYNTAX TimeTicks
			MAX-ACCESS read-only
			STATUS current
			DESCRIPTION
				"Description."
			::= { sleV2Dhcp4PEVendorControl 4 }

		
		-- 1.3.6.1.4.1.6296.102.6.2.2.10.1.2.5
		sleV2Dhcp4PEVendorControlReqResult OBJECT-TYPE
			SYNTAX SleControlRequestResultType
			MAX-ACCESS read-only
			STATUS current
			DESCRIPTION
				"Description."
			::= { sleV2Dhcp4PEVendorControl 5 }

		
		-- 1.3.6.1.4.1.6296.102.6.2.2.10.1.2.6
		sleV2Dhcp4PEVendorControlPoolIndex OBJECT-TYPE
			SYNTAX INTEGER (1..255)
			MAX-ACCESS read-write
			STATUS current
			DESCRIPTION
				"The Pool index"
			::= { sleV2Dhcp4PEVendorControl 6 }

		
		-- 1.3.6.1.4.1.6296.102.6.2.2.10.1.2.7
		sleV2Dhcp4PEVendorControlIfIndex OBJECT-TYPE
			SYNTAX INTEGER (1..512)
			MAX-ACCESS read-write
			STATUS current
			DESCRIPTION
				"Description."
			::= { sleV2Dhcp4PEVendorControl 7 }

		
		-- 1.3.6.1.4.1.6296.102.6.2.2.10.1.2.8
		sleV2Dhcp4PEVendorControlVendorID OBJECT-TYPE
			SYNTAX OCTET STRING (SIZE (0..32))
			MAX-ACCESS read-write
			STATUS current
			DESCRIPTION
				"Description."
			::= { sleV2Dhcp4PEVendorControl 8 }

		
		-- 1.3.6.1.4.1.6296.102.6.2.2.10.1.2.9
		sleV2Dhcp4PEVendorControlStart OBJECT-TYPE
			SYNTAX IpAddress
			MAX-ACCESS read-write
			STATUS current
			DESCRIPTION
				"Description."
			::= { sleV2Dhcp4PEVendorControl 9 }

		
		-- 1.3.6.1.4.1.6296.102.6.2.2.10.1.2.10
		sleV2Dhcp4PEVendorControlEnd OBJECT-TYPE
			SYNTAX IpAddress
			MAX-ACCESS read-write
			STATUS current
			DESCRIPTION
				"Description."
			::= { sleV2Dhcp4PEVendorControl 10 }

		
		-- 1.3.6.1.4.1.6296.102.6.2.2.10.1.3
		sleV2Dhcp4PEVendorNotification OBJECT IDENTIFIER ::= { sleV2Dhcp4PEVendor 3 }

		
		-- 1.3.6.1.4.1.6296.102.6.2.2.10.1.3.1
		sleV2Dhcp4PEVendorCreated NOTIFICATION-TYPE
			OBJECTS { sleV2Dhcp4PEVendorControlRequest, sleV2Dhcp4PEVendorControlTimeStamp, sleV2Dhcp4PEVendorControlReqResult, sleV2Dhcp4PEVendorControlPoolIndex, sleV2Dhcp4PEVendorControlIfIndex, 
				sleV2Dhcp4PEVendorControlVendorID, sleV2Dhcp4PEVendorControlStart, sleV2Dhcp4PEVendorControlEnd }
			STATUS current
			DESCRIPTION 
				"Description."
			::= { sleV2Dhcp4PEVendorNotification 1 }

		
		-- 1.3.6.1.4.1.6296.102.6.2.2.10.1.3.2
		sleV2Dhcp4PEVendorDestroyed NOTIFICATION-TYPE
			OBJECTS { sleV2Dhcp4PEVendorControlRequest, sleV2Dhcp4PEVendorControlTimeStamp, sleV2Dhcp4PEVendorControlReqResult, sleV2Dhcp4PEVendorControlPoolIndex, sleV2Dhcp4PEVendorControlIfIndex, 
				sleV2Dhcp4PEVendorControlVendorID, sleV2Dhcp4PEVendorControlStart, sleV2Dhcp4PEVendorControlEnd }
			STATUS current
			DESCRIPTION 
				"Description."
			::= { sleV2Dhcp4PEVendorNotification 2 }

		
		-- 1.3.6.1.4.1.6296.102.6.2.2.10.1.3.3
		sleV2Dhcp4PEVendorAllDestroyed NOTIFICATION-TYPE
			OBJECTS { sleV2Dhcp4PEVendorControlRequest, sleV2Dhcp4PEVendorControlTimeStamp, sleV2Dhcp4PEVendorControlReqResult, sleV2Dhcp4PEVendorControlPoolIndex, sleV2Dhcp4PEVendorControlIfIndex
				 }
			STATUS current
			DESCRIPTION 
				"Description."
			::= { sleV2Dhcp4PEVendorNotification 3 }

		
		-- 1.3.6.1.4.1.6296.102.6.2.2.10.2
		sleV2Dhcp4PEAddress OBJECT IDENTIFIER ::= { sleV2Dhcp4PE 2 }

		
		-- 1.3.6.1.4.1.6296.102.6.2.2.10.2.1
		sleV2Dhcp4PEAddressTable OBJECT-TYPE
			SYNTAX SEQUENCE OF SleV2Dhcp4PEAddressEntry
			MAX-ACCESS not-accessible
			STATUS current
			DESCRIPTION
				"Description."
			::= { sleV2Dhcp4PEAddress 1 }

		
		-- 1.3.6.1.4.1.6296.102.6.2.2.10.2.1.1
		sleV2Dhcp4PEAddressEntry OBJECT-TYPE
			SYNTAX SleV2Dhcp4PEAddressEntry
			MAX-ACCESS not-accessible
			STATUS current
			DESCRIPTION
				"Description."
			INDEX { sleV2Dhcp4PEAddressPoolIndex, sleV2Dhcp4PEAddressIfIndex, sleV2Dhcp4PEAddressStart }
			::= { sleV2Dhcp4PEAddressTable 1 }

		
		SleV2Dhcp4PEAddressEntry ::=
			SEQUENCE { 
				sleV2Dhcp4PEAddressPoolIndex
					INTEGER,
				sleV2Dhcp4PEAddressIfIndex
					INTEGER,
				sleV2Dhcp4PEAddressStart
					IpAddress,
				sleV2Dhcp4PEAddressEnd
					IpAddress
			 }

		-- 1.3.6.1.4.1.6296.102.6.2.2.10.2.1.1.1
		sleV2Dhcp4PEAddressPoolIndex OBJECT-TYPE
			SYNTAX INTEGER (1..255)
			MAX-ACCESS read-only
			STATUS current
			DESCRIPTION
				"The Pool index"
			::= { sleV2Dhcp4PEAddressEntry 1 }

		
		-- 1.3.6.1.4.1.6296.102.6.2.2.10.2.1.1.2
		sleV2Dhcp4PEAddressIfIndex OBJECT-TYPE
			SYNTAX INTEGER (1..512)
			MAX-ACCESS read-only
			STATUS current
			DESCRIPTION
				"Description."
			::= { sleV2Dhcp4PEAddressEntry 2 }

		
		-- 1.3.6.1.4.1.6296.102.6.2.2.10.2.1.1.3
		sleV2Dhcp4PEAddressStart OBJECT-TYPE
			SYNTAX IpAddress
			MAX-ACCESS read-only
			STATUS current
			DESCRIPTION
				"Description."
			::= { sleV2Dhcp4PEAddressEntry 3 }

		
		-- 1.3.6.1.4.1.6296.102.6.2.2.10.2.1.1.4
		sleV2Dhcp4PEAddressEnd OBJECT-TYPE
			SYNTAX IpAddress
			MAX-ACCESS read-only
			STATUS current
			DESCRIPTION
				"Description."
			::= { sleV2Dhcp4PEAddressEntry 4 }

		
		-- 1.3.6.1.4.1.6296.102.6.2.2.10.2.2
		sleV2Dhcp4PEAddressControl OBJECT IDENTIFIER ::= { sleV2Dhcp4PEAddress 2 }

		
		-- 1.3.6.1.4.1.6296.102.6.2.2.10.2.2.1
		sleV2Dhcp4PEAddressControlRequest OBJECT-TYPE
			SYNTAX INTEGER
				{
				createPEAddressEntry(1),
				destroyPEAddressEntry(2),
				destroyPEAddressEntryAll(3)
				}
			MAX-ACCESS read-write
			STATUS current
			DESCRIPTION
				"Description."
			::= { sleV2Dhcp4PEAddressControl 1 }

		
		-- 1.3.6.1.4.1.6296.102.6.2.2.10.2.2.2
		sleV2Dhcp4PEAddressControlStatus OBJECT-TYPE
			SYNTAX SleControlStatusType
			MAX-ACCESS read-only
			STATUS current
			DESCRIPTION
				"Description."
			::= { sleV2Dhcp4PEAddressControl 2 }

		
		-- 1.3.6.1.4.1.6296.102.6.2.2.10.2.2.3
		sleV2Dhcp4PEAddressControlTimer OBJECT-TYPE
			SYNTAX Gauge32
			MAX-ACCESS read-write
			STATUS current
			DESCRIPTION
				"Description."
			::= { sleV2Dhcp4PEAddressControl 3 }

		
		-- 1.3.6.1.4.1.6296.102.6.2.2.10.2.2.4
		sleV2Dhcp4PEAddressControlTimeStamp OBJECT-TYPE
			SYNTAX TimeTicks
			MAX-ACCESS read-only
			STATUS current
			DESCRIPTION
				"Description."
			::= { sleV2Dhcp4PEAddressControl 4 }

		
		-- 1.3.6.1.4.1.6296.102.6.2.2.10.2.2.5
		sleV2Dhcp4PEAddressControlReqResult OBJECT-TYPE
			SYNTAX SleControlRequestResultType
			MAX-ACCESS read-only
			STATUS current
			DESCRIPTION
				"Description."
			::= { sleV2Dhcp4PEAddressControl 5 }

		
		-- 1.3.6.1.4.1.6296.102.6.2.2.10.2.2.6
		sleV2Dhcp4PEAddressControlPoolIndex OBJECT-TYPE
			SYNTAX INTEGER (1..255)
			MAX-ACCESS read-write
			STATUS current
			DESCRIPTION
				"The Pool index"
			::= { sleV2Dhcp4PEAddressControl 6 }

		
		-- 1.3.6.1.4.1.6296.102.6.2.2.10.2.2.7
		sleV2Dhcp4PEAddressControlIfIndex OBJECT-TYPE
			SYNTAX INTEGER (1..512)
			MAX-ACCESS read-write
			STATUS current
			DESCRIPTION
				"Description"
			::= { sleV2Dhcp4PEAddressControl 7 }

		
		-- 1.3.6.1.4.1.6296.102.6.2.2.10.2.2.8
		sleV2Dhcp4PEAddressControlStart OBJECT-TYPE
			SYNTAX IpAddress
			MAX-ACCESS read-write
			STATUS current
			DESCRIPTION
				"Description."
			::= { sleV2Dhcp4PEAddressControl 8 }

		
		-- 1.3.6.1.4.1.6296.102.6.2.2.10.2.2.9
		sleV2Dhcp4PEAddressControlEnd OBJECT-TYPE
			SYNTAX IpAddress
			MAX-ACCESS read-write
			STATUS current
			DESCRIPTION
				"Description."
			::= { sleV2Dhcp4PEAddressControl 9 }

		
		-- 1.3.6.1.4.1.6296.102.6.2.2.10.2.3
		sleV2Dhcp4PEAddressNotification OBJECT IDENTIFIER ::= { sleV2Dhcp4PEAddress 3 }

		
		-- 1.3.6.1.4.1.6296.102.6.2.2.10.2.3.1
		sleV2Dhcp4PEAddressCreated NOTIFICATION-TYPE
			OBJECTS { sleV2Dhcp4PEAddressControlRequest, sleV2Dhcp4PEAddressControlTimeStamp, sleV2Dhcp4PEAddressControlReqResult, sleV2Dhcp4PEAddressControlPoolIndex, sleV2Dhcp4PEAddressControlIfIndex, 
				sleV2Dhcp4PEAddressControlStart, sleV2Dhcp4PEAddressControlEnd }
			STATUS current
			DESCRIPTION 
				"Description."
			::= { sleV2Dhcp4PEAddressNotification 1 }

		
		-- 1.3.6.1.4.1.6296.102.6.2.2.10.2.3.2
		sleV2Dhcp4PEAddressDestroyed NOTIFICATION-TYPE
			OBJECTS { sleV2Dhcp4PEAddressControlRequest, sleV2Dhcp4PEAddressControlTimeStamp, sleV2Dhcp4PEAddressControlReqResult, sleV2Dhcp4PEAddressControlPoolIndex, sleV2Dhcp4PEAddressControlIfIndex, 
				sleV2Dhcp4PEAddressControlStart, sleV2Dhcp4PEAddressControlEnd }
			STATUS current
			DESCRIPTION 
				"Description."
			::= { sleV2Dhcp4PEAddressNotification 2 }

		
		-- 1.3.6.1.4.1.6296.102.6.2.2.10.2.3.3
		sleV2Dhcp4PEAddressAllDestroyed NOTIFICATION-TYPE
			OBJECTS { sleV2Dhcp4PEAddressControlRequest, sleV2Dhcp4PEAddressControlTimeStamp, sleV2Dhcp4PEAddressControlReqResult, sleV2Dhcp4PEAddressControlPoolIndex, sleV2Dhcp4PEAddressControlIfIndex
				 }
			STATUS current
			DESCRIPTION 
				"Description."
			::= { sleV2Dhcp4PEAddressNotification 3 }

		
		-- 1.3.6.1.4.1.6296.102.6.2.2.10.3
		sleV2Dhcp4PENonPE OBJECT IDENTIFIER ::= { sleV2Dhcp4PE 3 }

		
		-- 1.3.6.1.4.1.6296.102.6.2.2.10.3.1
		sleV2Dhcp4PENonPETable OBJECT-TYPE
			SYNTAX SEQUENCE OF SleV2Dhcp4PENonPEEntry
			MAX-ACCESS not-accessible
			STATUS current
			DESCRIPTION
				"Description."
			::= { sleV2Dhcp4PENonPE 1 }

		
		-- 1.3.6.1.4.1.6296.102.6.2.2.10.3.1.1
		sleV2Dhcp4PENonPEEntry OBJECT-TYPE
			SYNTAX SleV2Dhcp4PENonPEEntry
			MAX-ACCESS not-accessible
			STATUS current
			DESCRIPTION
				"Description."
			INDEX { sleV2Dhcp4PENonPEPoolIndex }
			::= { sleV2Dhcp4PENonPETable 1 }

		
		SleV2Dhcp4PENonPEEntry ::=
			SEQUENCE { 
				sleV2Dhcp4PENonPEPoolIndex
					INTEGER,
				sleV2Dhcp4PENonPEStart
					IpAddress,
				sleV2Dhcp4PENonPEEnd
					IpAddress
			 }

		-- 1.3.6.1.4.1.6296.102.6.2.2.10.3.1.1.1
		sleV2Dhcp4PENonPEPoolIndex OBJECT-TYPE
			SYNTAX INTEGER (1..255)
			MAX-ACCESS read-only
			STATUS current
			DESCRIPTION
				"The Pool index"
			::= { sleV2Dhcp4PENonPEEntry 1 }

		
		-- 1.3.6.1.4.1.6296.102.6.2.2.10.3.1.1.2
		sleV2Dhcp4PENonPEStart OBJECT-TYPE
			SYNTAX IpAddress
			MAX-ACCESS read-only
			STATUS current
			DESCRIPTION
				"Description."
			::= { sleV2Dhcp4PENonPEEntry 2 }

		
		-- 1.3.6.1.4.1.6296.102.6.2.2.10.3.1.1.3
		sleV2Dhcp4PENonPEEnd OBJECT-TYPE
			SYNTAX IpAddress
			MAX-ACCESS read-only
			STATUS current
			DESCRIPTION
				"Description."
			::= { sleV2Dhcp4PENonPEEntry 3 }

		
		-- 1.3.6.1.4.1.6296.102.6.2.2.10.3.2
		sleV2Dhcp4PENonPEControl OBJECT IDENTIFIER ::= { sleV2Dhcp4PENonPE 2 }

		
		-- 1.3.6.1.4.1.6296.102.6.2.2.10.3.2.1
		sleV2Dhcp4PENonPEControlRequest OBJECT-TYPE
			SYNTAX INTEGER
				{
				createPENonPEEntry(1),
				destroyPENonPEEntry(2)
				}
			MAX-ACCESS read-write
			STATUS current
			DESCRIPTION
				"Description."
			::= { sleV2Dhcp4PENonPEControl 1 }

		
		-- 1.3.6.1.4.1.6296.102.6.2.2.10.3.2.2
		sleV2Dhcp4PENonPEControlStatus OBJECT-TYPE
			SYNTAX SleControlStatusType
			MAX-ACCESS read-only
			STATUS current
			DESCRIPTION
				"Description."
			::= { sleV2Dhcp4PENonPEControl 2 }

		
		-- 1.3.6.1.4.1.6296.102.6.2.2.10.3.2.3
		sleV2Dhcp4PENonPEControlTimer OBJECT-TYPE
			SYNTAX Gauge32
			MAX-ACCESS read-write
			STATUS current
			DESCRIPTION
				"Description."
			::= { sleV2Dhcp4PENonPEControl 3 }

		
		-- 1.3.6.1.4.1.6296.102.6.2.2.10.3.2.4
		sleV2Dhcp4PENonPEControlTimeStamp OBJECT-TYPE
			SYNTAX TimeTicks
			MAX-ACCESS read-only
			STATUS current
			DESCRIPTION
				"Description."
			::= { sleV2Dhcp4PENonPEControl 4 }

		
		-- 1.3.6.1.4.1.6296.102.6.2.2.10.3.2.5
		sleV2Dhcp4PENonPEControlReqResult OBJECT-TYPE
			SYNTAX SleControlRequestResultType
			MAX-ACCESS read-only
			STATUS current
			DESCRIPTION
				"Description."
			::= { sleV2Dhcp4PENonPEControl 5 }

		
		-- 1.3.6.1.4.1.6296.102.6.2.2.10.3.2.6
		sleV2Dhcp4PENonPEControlPoolIndex OBJECT-TYPE
			SYNTAX INTEGER (1..255)
			MAX-ACCESS read-write
			STATUS current
			DESCRIPTION
				"The Pool index"
			::= { sleV2Dhcp4PENonPEControl 6 }

		
		-- 1.3.6.1.4.1.6296.102.6.2.2.10.3.2.7
		sleV2Dhcp4PENonPEControlStart OBJECT-TYPE
			SYNTAX IpAddress
			MAX-ACCESS read-write
			STATUS current
			DESCRIPTION
				"Description."
			::= { sleV2Dhcp4PENonPEControl 7 }

		
		-- 1.3.6.1.4.1.6296.102.6.2.2.10.3.2.8
		sleV2Dhcp4PENonPEControlEnd OBJECT-TYPE
			SYNTAX IpAddress
			MAX-ACCESS read-write
			STATUS current
			DESCRIPTION
				"Description."
			::= { sleV2Dhcp4PENonPEControl 8 }

		
		-- 1.3.6.1.4.1.6296.102.6.2.2.10.3.3
		sleV2Dhcp4PENonPENotification OBJECT IDENTIFIER ::= { sleV2Dhcp4PENonPE 3 }

		
		-- 1.3.6.1.4.1.6296.102.6.2.2.10.3.3.1
		sleV2Dhcp4PENonPECreated NOTIFICATION-TYPE
			OBJECTS { sleV2Dhcp4PENonPEControlRequest, sleV2Dhcp4PENonPEControlTimeStamp, sleV2Dhcp4PENonPEControlReqResult, sleV2Dhcp4PENonPEControlPoolIndex, sleV2Dhcp4PENonPEControlStart, 
				sleV2Dhcp4PENonPEControlEnd }
			STATUS current
			DESCRIPTION 
				"Description."
			::= { sleV2Dhcp4PENonPENotification 1 }

		
		-- 1.3.6.1.4.1.6296.102.6.2.2.10.3.3.2
		sleV2Dhcp4PENonPEDestroyed NOTIFICATION-TYPE
			OBJECTS { sleV2Dhcp4PENonPEControlRequest, sleV2Dhcp4PENonPEControlTimeStamp, sleV2Dhcp4PENonPEControlReqResult, sleV2Dhcp4PENonPEControlPoolIndex, sleV2Dhcp4PENonPEControlStart, 
				sleV2Dhcp4PENonPEControlEnd }
			STATUS current
			DESCRIPTION 
				"Description."
			::= { sleV2Dhcp4PENonPENotification 2 }

		
		-- 1.3.6.1.4.1.6296.102.6.2.3
		sleV2Dhcp4Option82 OBJECT IDENTIFIER ::= { sleV2Dhcp4 3 }

		
		-- 1.3.6.1.4.1.6296.102.6.2.3.1
		sleV2Dhcp4Option82Port OBJECT IDENTIFIER ::= { sleV2Dhcp4Option82 1 }

		
		-- 1.3.6.1.4.1.6296.102.6.2.3.1.1
		sleV2Dhcp4Option82PortTable OBJECT-TYPE
			SYNTAX SEQUENCE OF SleV2Dhcp4Option82PortEntry
			MAX-ACCESS not-accessible
			STATUS current
			DESCRIPTION
				"Description."
			::= { sleV2Dhcp4Option82Port 1 }

		
		-- 1.3.6.1.4.1.6296.102.6.2.3.1.1.1
		sleV2Dhcp4Option82PortEntry OBJECT-TYPE
			SYNTAX SleV2Dhcp4Option82PortEntry
			MAX-ACCESS not-accessible
			STATUS current
			DESCRIPTION
				"Description."
			INDEX { sleV2Dhcp4Option82PortIndex }
			::= { sleV2Dhcp4Option82PortTable 1 }

		
		SleV2Dhcp4Option82PortEntry ::=
			SEQUENCE { 
				sleV2Dhcp4Option82PortIndex
					INTEGER,
				sleV2Dhcp4Option82PortCircuitType
					INTEGER,
				sleV2Dhcp4Option82PortCircuitId
					OCTET STRING,
				sleV2Dhcp4Option82PortTrustState
					INTEGER,
				sleV2Dhcp4Option82PortPolicy
					INTEGER,
				sleV2Dhcp4Option82PortPolicyDrop
					INTEGER
			 }

		-- 1.3.6.1.4.1.6296.102.6.2.3.1.1.1.1
		sleV2Dhcp4Option82PortIndex OBJECT-TYPE
			SYNTAX INTEGER (1..255)
			MAX-ACCESS read-only
			STATUS current
			DESCRIPTION
				"Description."
			::= { sleV2Dhcp4Option82PortEntry 1 }

		
		-- 1.3.6.1.4.1.6296.102.6.2.3.1.1.1.2
		sleV2Dhcp4Option82PortCircuitType OBJECT-TYPE
			SYNTAX INTEGER
				{
				undefined(0),
				index(1),
				hex(2),
				text(3),
				option(4)
				}
			MAX-ACCESS read-only
			STATUS current
			DESCRIPTION
				"Description."
			::= { sleV2Dhcp4Option82PortEntry 2 }

		
		-- 1.3.6.1.4.1.6296.102.6.2.3.1.1.1.3
		sleV2Dhcp4Option82PortCircuitId OBJECT-TYPE
			SYNTAX OCTET STRING (SIZE (0 | 1..32))
			MAX-ACCESS read-only
			STATUS current
			DESCRIPTION
				"Description."
			::= { sleV2Dhcp4Option82PortEntry 3 }

		
		-- 1.3.6.1.4.1.6296.102.6.2.3.1.1.1.4
		sleV2Dhcp4Option82PortTrustState OBJECT-TYPE
			SYNTAX INTEGER
				{
				none(0),
				normal(1),
				option82(2),
				all(3)
				}
			MAX-ACCESS read-only
			STATUS current
			DESCRIPTION
				"."
			DEFVAL { disable }
			::= { sleV2Dhcp4Option82PortEntry 4 }

		
		-- 1.3.6.1.4.1.6296.102.6.2.3.1.1.1.5
		sleV2Dhcp4Option82PortPolicy OBJECT-TYPE
			SYNTAX INTEGER
				{
				none(0),
				keep(1),
				replace(2)
				}
			MAX-ACCESS read-only
			STATUS current
			DESCRIPTION
				"The option82 port policy."
			::= { sleV2Dhcp4Option82PortEntry 5 }

		
		-- 1.3.6.1.4.1.6296.102.6.2.3.1.1.1.6
		sleV2Dhcp4Option82PortPolicyDrop OBJECT-TYPE
			SYNTAX INTEGER
				{
				none(0),
				normal(1),
				option82(2)
				}
			MAX-ACCESS read-only
			STATUS current
			DESCRIPTION
				"The option82 port drop policy."
			::= { sleV2Dhcp4Option82PortEntry 6 }

		
		-- 1.3.6.1.4.1.6296.102.6.2.3.1.2
		sleV2Dhcp4Option82PortControl OBJECT IDENTIFIER ::= { sleV2Dhcp4Option82Port 2 }

		
		-- 1.3.6.1.4.1.6296.102.6.2.3.1.2.1
		sleV2Dhcp4Option82PortControlRequest OBJECT-TYPE
			SYNTAX INTEGER
				{
				setDhcpOption82PortCircuitId(1),
				setDhcpOption82PortTrustState(2),
				clearDhcpOption82PortCircuitId(3),
				setDhcpOption82PortPolicy(4)
				}
			MAX-ACCESS read-write
			STATUS current
			DESCRIPTION
				"The request of a user command."
			::= { sleV2Dhcp4Option82PortControl 1 }

		
		-- 1.3.6.1.4.1.6296.102.6.2.3.1.2.2
		sleV2Dhcp4Option82PortControlStatus OBJECT-TYPE
			SYNTAX SleControlStatusType
			MAX-ACCESS read-only
			STATUS current
			DESCRIPTION
				"The status of a user command."
			::= { sleV2Dhcp4Option82PortControl 2 }

		
		-- 1.3.6.1.4.1.6296.102.6.2.3.1.2.3
		sleV2Dhcp4Option82PortControlTimer OBJECT-TYPE
			SYNTAX Gauge32
			MAX-ACCESS read-write
			STATUS current
			DESCRIPTION
				"The maximum wait Time for the manager for a long running user command."
			::= { sleV2Dhcp4Option82PortControl 3 }

		
		-- 1.3.6.1.4.1.6296.102.6.2.3.1.2.4
		sleV2Dhcp4Option82PortControlTimeStamp OBJECT-TYPE
			SYNTAX TimeTicks
			MAX-ACCESS read-write
			STATUS current
			DESCRIPTION
				"The Time stamp of the last command (end of command)."
			::= { sleV2Dhcp4Option82PortControl 4 }

		
		-- 1.3.6.1.4.1.6296.102.6.2.3.1.2.5
		sleV2Dhcp4Option82PortControlReqResult OBJECT-TYPE
			SYNTAX SleControlRequestResultType
			MAX-ACCESS read-write
			STATUS current
			DESCRIPTION
				"The result of the last user command."
			::= { sleV2Dhcp4Option82PortControl 5 }

		
		-- 1.3.6.1.4.1.6296.102.6.2.3.1.2.6
		sleV2Dhcp4Option82PortControlIndex OBJECT-TYPE
			SYNTAX INTEGER (1..255)
			MAX-ACCESS read-write
			STATUS current
			DESCRIPTION
				"Description."
			::= { sleV2Dhcp4Option82PortControl 6 }

		
		-- 1.3.6.1.4.1.6296.102.6.2.3.1.2.7
		sleV2Dhcp4Option82PortControlCircuitType OBJECT-TYPE
			SYNTAX INTEGER
				{
				undefined(0),
				index(1),
				hex(2),
				text(3),
				option(4)
				}
			MAX-ACCESS read-write
			STATUS current
			DESCRIPTION
				"Description."
			::= { sleV2Dhcp4Option82PortControl 7 }

		
		-- 1.3.6.1.4.1.6296.102.6.2.3.1.2.8
		sleV2Dhcp4Option82PortControlCircuitId OBJECT-TYPE
			SYNTAX OCTET STRING (SIZE (0 | 1..32))
			MAX-ACCESS read-write
			STATUS current
			DESCRIPTION
				"Description."
			::= { sleV2Dhcp4Option82PortControl 8 }

		
		-- 1.3.6.1.4.1.6296.102.6.2.3.1.2.9
		sleV2Dhcp4Option82PortControlTrustState OBJECT-TYPE
			SYNTAX INTEGER
				{
				none(0),
				normal(1),
				option82(2),
				all(3)
				}
			MAX-ACCESS read-write
			STATUS current
			DESCRIPTION
				"The result of the last user command."
			::= { sleV2Dhcp4Option82PortControl 9 }

		
		-- 1.3.6.1.4.1.6296.102.6.2.3.1.2.10
		sleV2Dhcp4Option82PortControlPolicy OBJECT-TYPE
			SYNTAX INTEGER
				{
				none(0),
				keep(1),
				replace(2)
				}
			MAX-ACCESS read-write
			STATUS current
			DESCRIPTION
				"The option82 port policy."
			::= { sleV2Dhcp4Option82PortControl 10 }

		
		-- 1.3.6.1.4.1.6296.102.6.2.3.1.2.11
		sleV2Dhcp4Option82PortControlPolicyDrop OBJECT-TYPE
			SYNTAX INTEGER
				{
				none(0),
				normal(1),
				option82(2)
				}
			MAX-ACCESS read-write
			STATUS current
			DESCRIPTION
				"Description."
			::= { sleV2Dhcp4Option82PortControl 11 }

		
		-- 1.3.6.1.4.1.6296.102.6.2.3.1.3
		sleV2Dhcp4Option82PortNotification OBJECT IDENTIFIER ::= { sleV2Dhcp4Option82Port 3 }

		
		-- 1.3.6.1.4.1.6296.102.6.2.3.1.3.1
		sleV2Dhcp4Option82PortCircuitIdChanged NOTIFICATION-TYPE
			OBJECTS { sleV2Dhcp4Option82PortControlRequest, sleV2Dhcp4Option82PortControlTimeStamp, sleV2Dhcp4Option82PortIndex, sleV2Dhcp4Option82PortControlReqResult, sleV2Dhcp4Option82PortCircuitType, 
				sleV2Dhcp4Option82PortCircuitId }
			STATUS current
			DESCRIPTION 
				"Description."
			::= { sleV2Dhcp4Option82PortNotification 1 }

		
		-- 1.3.6.1.4.1.6296.102.6.2.3.1.3.2
		sleV2Dhcp4Option82PortTrustStateChanged NOTIFICATION-TYPE
			OBJECTS { sleV2Dhcp4Option82PortControlRequest, sleV2Dhcp4Option82PortControlTimeStamp, sleV2Dhcp4Option82PortControlReqResult, sleV2Dhcp4Option82PortTrustState }
			STATUS current
			DESCRIPTION 
				"Description."
			::= { sleV2Dhcp4Option82PortNotification 2 }

		
		-- 1.3.6.1.4.1.6296.102.6.2.3.1.3.3
		sleV2Dhcp4Option82PortCircuitIdCleared NOTIFICATION-TYPE
			OBJECTS { sleV2Dhcp4Option82PortControlRequest, sleV2Dhcp4Option82PortControlTimeStamp, sleV2Dhcp4Option82PortControlReqResult, sleV2Dhcp4Option82PortIndex, sleV2Dhcp4Option82PortCircuitType
				 }
			STATUS current
			DESCRIPTION 
				"Description."
			::= { sleV2Dhcp4Option82PortNotification 3 }

		
		-- 1.3.6.1.4.1.6296.102.6.2.3.1.3.4
		sleV2Dhcp4Option82PortPolicyChanged NOTIFICATION-TYPE
			OBJECTS { sleV2Dhcp4Option82PortControlRequest, sleV2Dhcp4Option82PortControlTimeStamp, sleV2Dhcp4Option82PortControlReqResult, sleV2Dhcp4Option82PortIndex, sleV2Dhcp4Option82PortPolicy, 
				sleV2Dhcp4Option82PortPolicyDrop }
			STATUS current
			DESCRIPTION 
				"Description."
			::= { sleV2Dhcp4Option82PortNotification 4 }

		
		-- 1.3.6.1.4.1.6296.102.6.2.3.2
		sleV2Dhcp4RelayInfo OBJECT IDENTIFIER ::= { sleV2Dhcp4Option82 2 }

		
		-- 1.3.6.1.4.1.6296.102.6.2.3.2.1
		sleV2Dhcp4Remote OBJECT IDENTIFIER ::= { sleV2Dhcp4RelayInfo 1 }

		
		-- 1.3.6.1.4.1.6296.102.6.2.3.2.1.1
		sleV2Dhcp4RemoteTable OBJECT-TYPE
			SYNTAX SEQUENCE OF SleV2Dhcp4RemoteEntry
			MAX-ACCESS not-accessible
			STATUS current
			DESCRIPTION
				"Description."
			::= { sleV2Dhcp4Remote 1 }

		
		-- 1.3.6.1.4.1.6296.102.6.2.3.2.1.1.1
		sleV2Dhcp4RemoteEntry OBJECT-TYPE
			SYNTAX SleV2Dhcp4RemoteEntry
			MAX-ACCESS not-accessible
			STATUS current
			DESCRIPTION
				"Description."
			INDEX { sleV2Dhcp4RemoteId }
			::= { sleV2Dhcp4RemoteTable 1 }

		
		SleV2Dhcp4RemoteEntry ::=
			SEQUENCE { 
				sleV2Dhcp4RemoteId
					OCTET STRING,
				sleV2Dhcp4RemoteType
					INTEGER,
				sleV2Dhcp4RemoteClass
					OCTET STRING,
				sleV2Dhcp4RemoteTrust
					Boolean,
				sleV2Dhcp4RemoteLeaseLimit
					INTEGER,
				sleV2Dhcp4RemoteLeaseCnt
					INTEGER
			 }

		-- 1.3.6.1.4.1.6296.102.6.2.3.2.1.1.1.1
		sleV2Dhcp4RemoteId OBJECT-TYPE
			SYNTAX OCTET STRING (SIZE (1..64))
			MAX-ACCESS read-only
			STATUS current
			DESCRIPTION
				"Description."
			::= { sleV2Dhcp4RemoteEntry 1 }

		
		-- 1.3.6.1.4.1.6296.102.6.2.3.2.1.1.1.2
		sleV2Dhcp4RemoteType OBJECT-TYPE
			SYNTAX INTEGER
				{
				ipaddress(1),
				hex(2),
				text(3),
				index(5)
				}
			MAX-ACCESS read-only
			STATUS current
			DESCRIPTION
				"Description."
			::= { sleV2Dhcp4RemoteEntry 2 }

		
		-- 1.3.6.1.4.1.6296.102.6.2.3.2.1.1.1.3
		sleV2Dhcp4RemoteClass OBJECT-TYPE
			SYNTAX OCTET STRING (SIZE (0 | 1..32))
			MAX-ACCESS read-only
			STATUS current
			DESCRIPTION
				"Description."
			::= { sleV2Dhcp4RemoteEntry 3 }

		
		-- 1.3.6.1.4.1.6296.102.6.2.3.2.1.1.1.4
		sleV2Dhcp4RemoteTrust OBJECT-TYPE
			SYNTAX Boolean
			MAX-ACCESS read-only
			STATUS current
			DESCRIPTION
				"The Information that is whether this remote is trusted or not."
			::= { sleV2Dhcp4RemoteEntry 4 }

		
		-- 1.3.6.1.4.1.6296.102.6.2.3.2.1.1.1.5
		sleV2Dhcp4RemoteLeaseLimit OBJECT-TYPE
			SYNTAX INTEGER (1..2147483637)
			MAX-ACCESS read-only
			STATUS current
			DESCRIPTION
				"Description."
			::= { sleV2Dhcp4RemoteEntry 5 }

		
		-- 1.3.6.1.4.1.6296.102.6.2.3.2.1.1.1.6
		sleV2Dhcp4RemoteLeaseCnt OBJECT-TYPE
			SYNTAX INTEGER (1..2147483637)
			MAX-ACCESS read-only
			STATUS current
			DESCRIPTION
				"Description."
			::= { sleV2Dhcp4RemoteEntry 6 }

		
		-- 1.3.6.1.4.1.6296.102.6.2.3.2.1.2
		sleV2Dhcp4RemoteControl OBJECT IDENTIFIER ::= { sleV2Dhcp4Remote 2 }

		
		-- 1.3.6.1.4.1.6296.102.6.2.3.2.1.2.1
		sleV2Dhcp4RemoteControlRequest OBJECT-TYPE
			SYNTAX INTEGER
				{
				createDhcpRemote(1),
				destroyDhcpRemote(2),
				setDhcpRemote(3),
				clearDhcpRemotes(4)
				}
			MAX-ACCESS read-write
			STATUS current
			DESCRIPTION
				"The request of a user command."
			::= { sleV2Dhcp4RemoteControl 1 }

		
		-- 1.3.6.1.4.1.6296.102.6.2.3.2.1.2.2
		sleV2Dhcp4RemoteControlStatus OBJECT-TYPE
			SYNTAX SleControlStatusType
			MAX-ACCESS read-only
			STATUS current
			DESCRIPTION
				"The status of a user command."
			::= { sleV2Dhcp4RemoteControl 2 }

		
		-- 1.3.6.1.4.1.6296.102.6.2.3.2.1.2.3
		sleV2Dhcp4RemoteControlTimer OBJECT-TYPE
			SYNTAX Gauge32
			MAX-ACCESS read-write
			STATUS current
			DESCRIPTION
				"The maximum wait Time for the manager for a long running user command."
			::= { sleV2Dhcp4RemoteControl 3 }

		
		-- 1.3.6.1.4.1.6296.102.6.2.3.2.1.2.4
		sleV2Dhcp4RemoteControlTimeStamp OBJECT-TYPE
			SYNTAX TimeTicks
			MAX-ACCESS read-only
			STATUS current
			DESCRIPTION
				"The Time stamp of the last command (end of command)."
			::= { sleV2Dhcp4RemoteControl 4 }

		
		-- 1.3.6.1.4.1.6296.102.6.2.3.2.1.2.5
		sleV2Dhcp4RemoteControlReqResult OBJECT-TYPE
			SYNTAX SleControlRequestResultType
			MAX-ACCESS read-only
			STATUS current
			DESCRIPTION
				"The result of the last user command."
			::= { sleV2Dhcp4RemoteControl 5 }

		
		-- 1.3.6.1.4.1.6296.102.6.2.3.2.1.2.6
		sleV2Dhcp4RemoteControlId OBJECT-TYPE
			SYNTAX OCTET STRING (SIZE (1..64))
			MAX-ACCESS read-write
			STATUS current
			DESCRIPTION
				"Description."
			::= { sleV2Dhcp4RemoteControl 6 }

		
		-- 1.3.6.1.4.1.6296.102.6.2.3.2.1.2.7
		sleV2Dhcp4RemoteControlType OBJECT-TYPE
			SYNTAX INTEGER
				{
				ipaddress(1),
				hex(2),
				text(3),
				index(5)
				}
			MAX-ACCESS read-write
			STATUS current
			DESCRIPTION
				"Description."
			::= { sleV2Dhcp4RemoteControl 7 }

		
		-- 1.3.6.1.4.1.6296.102.6.2.3.2.1.2.8
		sleV2Dhcp4RemoteControlClass OBJECT-TYPE
			SYNTAX OCTET STRING (SIZE (0 | 1..32))
			MAX-ACCESS read-write
			STATUS current
			DESCRIPTION
				"Description."
			::= { sleV2Dhcp4RemoteControl 8 }

		
		-- 1.3.6.1.4.1.6296.102.6.2.3.2.1.2.9
		sleV2Dhcp4RemoteControlTrust OBJECT-TYPE
			SYNTAX Boolean
			MAX-ACCESS read-write
			STATUS current
			DESCRIPTION
				"Description."
			::= { sleV2Dhcp4RemoteControl 9 }

		
		-- 1.3.6.1.4.1.6296.102.6.2.3.2.1.2.10
		sleV4Dhcp4RemoteControlLeaseLimit OBJECT-TYPE
			SYNTAX INTEGER (1..2147483637)
			MAX-ACCESS read-write
			STATUS current
			DESCRIPTION
				"Description."
			::= { sleV2Dhcp4RemoteControl 10 }

		
		-- 1.3.6.1.4.1.6296.102.6.2.3.2.1.3
		sleV2Dhcp4RemoteNotification OBJECT IDENTIFIER ::= { sleV2Dhcp4Remote 3 }

		
		-- 1.3.6.1.4.1.6296.102.6.2.3.2.1.3.1
		sleV2Dhcp4RemoteCreated NOTIFICATION-TYPE
			OBJECTS { sleV2Dhcp4RemoteControlRequest, sleV2Dhcp4RemoteControlTimeStamp, sleV4Dhcp4RemoteControlLeaseLimit, sleV2Dhcp4RemoteControlReqResult, sleV2Dhcp4RemoteType, 
				sleV2Dhcp4RemoteClass, sleV2Dhcp4RemoteTrust }
			STATUS current
			DESCRIPTION 
				"Description."
			::= { sleV2Dhcp4RemoteNotification 1 }

		
		-- 1.3.6.1.4.1.6296.102.6.2.3.2.1.3.2
		sleV2Dhcp4RemoteDestroyed NOTIFICATION-TYPE
			OBJECTS { sleV2Dhcp4RemoteControlRequest, sleV2Dhcp4RemoteControlTimeStamp, sleV2Dhcp4RemoteControlReqResult, sleV2Dhcp4RemoteControlId }
			STATUS current
			DESCRIPTION 
				"Description."
			::= { sleV2Dhcp4RemoteNotification 2 }

		
		-- 1.3.6.1.4.1.6296.102.6.2.3.2.1.3.3
		sleV2Dhcp4RemoteChanged NOTIFICATION-TYPE
			OBJECTS { sleV2Dhcp4RemoteControlRequest, sleV2Dhcp4RemoteControlTimeStamp, sleV4Dhcp4RemoteControlLeaseLimit, sleV2Dhcp4RemoteControlReqResult, sleV2Dhcp4RemoteClass, 
				sleV2Dhcp4RemoteTrust }
			STATUS current
			DESCRIPTION 
				"Description."
			::= { sleV2Dhcp4RemoteNotification 3 }

		
		-- 1.3.6.1.4.1.6296.102.6.2.3.2.1.3.4
		sleV2Dhcp4RemoteCleared NOTIFICATION-TYPE
			OBJECTS { sleV2Dhcp4RemoteControlRequest, sleV2Dhcp4RemoteControlTimeStamp, sleV2Dhcp4RemoteControlReqResult }
			STATUS current
			DESCRIPTION 
				"Description."
			::= { sleV2Dhcp4RemoteNotification 4 }

		
		-- 1.3.6.1.4.1.6296.102.6.2.3.2.2
		sleV2Dhcp4RCircuit OBJECT IDENTIFIER ::= { sleV2Dhcp4RelayInfo 2 }

		
		-- 1.3.6.1.4.1.6296.102.6.2.3.2.2.1
		sleV2Dhcp4RCircuitTable OBJECT-TYPE
			SYNTAX SEQUENCE OF SleV2Dhcp4RCircuitEntry
			MAX-ACCESS not-accessible
			STATUS current
			DESCRIPTION
				"Description."
			::= { sleV2Dhcp4RCircuit 1 }

		
		-- 1.3.6.1.4.1.6296.102.6.2.3.2.2.1.1
		sleV2Dhcp4RCircuitEntry OBJECT-TYPE
			SYNTAX SleV2Dhcp4RCircuitEntry
			MAX-ACCESS not-accessible
			STATUS current
			DESCRIPTION
				"Description."
			INDEX { sleV2Dhcp4RemoteId, sleV2Dhcp4RCircuitId }
			::= { sleV2Dhcp4RCircuitTable 1 }

		
		SleV2Dhcp4RCircuitEntry ::=
			SEQUENCE { 
				sleV2Dhcp4RCircuitId
					OCTET STRING,
				sleV2Dhcp4RCircuitType
					INTEGER,
				sleV2Dhcp4RCircuitClass
					OCTET STRING,
				sleV2Dhcp4RCircuitLeaseLimit
					INTEGER,
				sleV2Dhcp4RCircuitLeaseCnt
					INTEGER
			 }

		-- 1.3.6.1.4.1.6296.102.6.2.3.2.2.1.1.1
		sleV2Dhcp4RCircuitId OBJECT-TYPE
			SYNTAX OCTET STRING (SIZE (1..32))
			MAX-ACCESS read-only
			STATUS current
			DESCRIPTION
				"Description."
			::= { sleV2Dhcp4RCircuitEntry 1 }

		
		-- 1.3.6.1.4.1.6296.102.6.2.3.2.2.1.1.2
		sleV2Dhcp4RCircuitType OBJECT-TYPE
			SYNTAX INTEGER
				{
				index(1),
				hex(2),
				text(3)
				}
			MAX-ACCESS read-only
			STATUS current
			DESCRIPTION
				"Description."
			::= { sleV2Dhcp4RCircuitEntry 2 }

		
		-- 1.3.6.1.4.1.6296.102.6.2.3.2.2.1.1.3
		sleV2Dhcp4RCircuitClass OBJECT-TYPE
			SYNTAX OCTET STRING (SIZE (1..32))
			MAX-ACCESS read-only
			STATUS current
			DESCRIPTION
				"Description."
			::= { sleV2Dhcp4RCircuitEntry 3 }

		
		-- 1.3.6.1.4.1.6296.102.6.2.3.2.2.1.1.4
		sleV2Dhcp4RCircuitLeaseLimit OBJECT-TYPE
			SYNTAX INTEGER (1..2147483637)
			MAX-ACCESS read-only
			STATUS current
			DESCRIPTION
				"Description."
			::= { sleV2Dhcp4RCircuitEntry 4 }

		
		-- 1.3.6.1.4.1.6296.102.6.2.3.2.2.1.1.5
		sleV2Dhcp4RCircuitLeaseCnt OBJECT-TYPE
			SYNTAX INTEGER (1..2147483637)
			MAX-ACCESS read-only
			STATUS current
			DESCRIPTION
				"Description."
			::= { sleV2Dhcp4RCircuitEntry 5 }

		
		-- 1.3.6.1.4.1.6296.102.6.2.3.2.2.2
		sleV2Dhcp4RCircuitControl OBJECT IDENTIFIER ::= { sleV2Dhcp4RCircuit 2 }

		
		-- 1.3.6.1.4.1.6296.102.6.2.3.2.2.2.1
		sleV2Dhcp4RCircuitControlRequest OBJECT-TYPE
			SYNTAX INTEGER
				{
				createDhcpRemoteCircuit(1),
				destroyDhcpRemoteCircuit(2),
				clearDhcpRemoteCircuits(3),
				setDhcpRemoteCircuit(4)
				}
			MAX-ACCESS read-write
			STATUS current
			DESCRIPTION
				"The request of a user command."
			::= { sleV2Dhcp4RCircuitControl 1 }

		
		-- 1.3.6.1.4.1.6296.102.6.2.3.2.2.2.2
		sleV2Dhcp4RCircuitControlStatus OBJECT-TYPE
			SYNTAX SleControlStatusType
			MAX-ACCESS read-only
			STATUS current
			DESCRIPTION
				"The status of a user command."
			::= { sleV2Dhcp4RCircuitControl 2 }

		
		-- 1.3.6.1.4.1.6296.102.6.2.3.2.2.2.3
		sleV2Dhcp4RCircuitControlTimer OBJECT-TYPE
			SYNTAX Gauge32
			MAX-ACCESS read-write
			STATUS current
			DESCRIPTION
				"The maximum wait Time for the manager for a long running user command."
			::= { sleV2Dhcp4RCircuitControl 3 }

		
		-- 1.3.6.1.4.1.6296.102.6.2.3.2.2.2.4
		sleV2Dhcp4RCircuitControlTimeStamp OBJECT-TYPE
			SYNTAX TimeTicks
			MAX-ACCESS read-only
			STATUS current
			DESCRIPTION
				"The Time stamp of the last command (end of command)."
			::= { sleV2Dhcp4RCircuitControl 4 }

		
		-- 1.3.6.1.4.1.6296.102.6.2.3.2.2.2.5
		sleV2Dhcp4RCircuitControlReqResult OBJECT-TYPE
			SYNTAX SleControlRequestResultType
			MAX-ACCESS read-only
			STATUS current
			DESCRIPTION
				"The result of the last user command."
			::= { sleV2Dhcp4RCircuitControl 5 }

		
		-- 1.3.6.1.4.1.6296.102.6.2.3.2.2.2.6
		sleV2Dhcp4RCircuitControlRemote OBJECT-TYPE
			SYNTAX OCTET STRING (SIZE (1..32))
			MAX-ACCESS read-write
			STATUS current
			DESCRIPTION
				"Description."
			::= { sleV2Dhcp4RCircuitControl 6 }

		
		-- 1.3.6.1.4.1.6296.102.6.2.3.2.2.2.7
		sleV2Dhcp4RCircuitControlId OBJECT-TYPE
			SYNTAX OCTET STRING (SIZE (1..32))
			MAX-ACCESS read-write
			STATUS current
			DESCRIPTION
				"Description."
			::= { sleV2Dhcp4RCircuitControl 7 }

		
		-- 1.3.6.1.4.1.6296.102.6.2.3.2.2.2.8
		sleV2Dhcp4RCircuitControlType OBJECT-TYPE
			SYNTAX INTEGER
				{
				index(1),
				hex(2),
				text(3)
				}
			MAX-ACCESS read-write
			STATUS current
			DESCRIPTION
				"Description."
			::= { sleV2Dhcp4RCircuitControl 8 }

		
		-- 1.3.6.1.4.1.6296.102.6.2.3.2.2.2.9
		sleV2Dhcp4RCircuitControlClass OBJECT-TYPE
			SYNTAX OCTET STRING (SIZE (1..32))
			MAX-ACCESS read-write
			STATUS current
			DESCRIPTION
				"Description."
			::= { sleV2Dhcp4RCircuitControl 9 }

		
		-- 1.3.6.1.4.1.6296.102.6.2.3.2.2.2.10
		sleV2Dhcp4RCircuitControlLeaseLimit OBJECT-TYPE
			SYNTAX INTEGER (1..2147483637)
			MAX-ACCESS read-write
			STATUS current
			DESCRIPTION
				"Description."
			::= { sleV2Dhcp4RCircuitControl 10 }

		
		-- 1.3.6.1.4.1.6296.102.6.2.3.2.2.3
		sleV2Dhcp4RCircuitNotification OBJECT IDENTIFIER ::= { sleV2Dhcp4RCircuit 3 }

		
		-- 1.3.6.1.4.1.6296.102.6.2.3.2.2.3.1
		sleV2Dhcp4RCircuitCreated NOTIFICATION-TYPE
			OBJECTS { sleV2Dhcp4RCircuitControlRequest, sleV2Dhcp4RCircuitControlTimeStamp, sleV2Dhcp4RCircuitLeaseLimit, sleV2Dhcp4RCircuitControlReqResult, sleV2Dhcp4RCircuitType, 
				sleV2Dhcp4RCircuitClass }
			STATUS current
			DESCRIPTION 
				"Description."
			::= { sleV2Dhcp4RCircuitNotification 1 }

		
		-- 1.3.6.1.4.1.6296.102.6.2.3.2.2.3.2
		sleV2Dhcp4RCircuitDestroyed NOTIFICATION-TYPE
			OBJECTS { sleV2Dhcp4RCircuitControlRequest, sleV2Dhcp4RCircuitControlTimeStamp, sleV2Dhcp4RCircuitControlReqResult, sleV2Dhcp4RCircuitControlRemote, sleV2Dhcp4RCircuitControlId
				 }
			STATUS current
			DESCRIPTION 
				"Description."
			::= { sleV2Dhcp4RCircuitNotification 2 }

		
		-- 1.3.6.1.4.1.6296.102.6.2.3.2.2.3.3
		sleV2Dhcp4RCircuitCleared NOTIFICATION-TYPE
			OBJECTS { sleV2Dhcp4RCircuitControlRequest, sleV2Dhcp4RCircuitControlTimeStamp, sleV2Dhcp4RCircuitControlReqResult, sleV2Dhcp4RCircuitControlRemote }
			STATUS current
			DESCRIPTION 
				"Description."
			::= { sleV2Dhcp4RCircuitNotification 3 }

		
		-- 1.3.6.1.4.1.6296.102.6.2.3.2.2.3.4
		sleV2Dhcp4RCircuitChanged NOTIFICATION-TYPE
			OBJECTS { sleV2Dhcp4RCircuitControlRequest, sleV2Dhcp4RCircuitControlTimeStamp, sleV2Dhcp4RCircuitControlReqResult, sleV2Dhcp4RCircuitControlRemote, sleV2Dhcp4RCircuitLeaseLimit
				 }
			STATUS current
			DESCRIPTION 
				"Description."
			::= { sleV2Dhcp4RCircuitNotification 4 }

		
		-- 1.3.6.1.4.1.6296.102.6.2.3.3
		sleV2Dhcp4Class OBJECT IDENTIFIER ::= { sleV2Dhcp4Option82 3 }

		
		-- 1.3.6.1.4.1.6296.102.6.2.3.3.1
		sleV2Dhcp4ClassBase OBJECT IDENTIFIER ::= { sleV2Dhcp4Class 1 }

		
		-- 1.3.6.1.4.1.6296.102.6.2.3.3.1.1
		sleV2Dhcp4ClassTable OBJECT-TYPE
			SYNTAX SEQUENCE OF SleV2Dhcp4ClassEntry
			MAX-ACCESS not-accessible
			STATUS current
			DESCRIPTION
				"Description."
			::= { sleV2Dhcp4ClassBase 1 }

		
		-- 1.3.6.1.4.1.6296.102.6.2.3.3.1.1.1
		sleV2Dhcp4ClassEntry OBJECT-TYPE
			SYNTAX SleV2Dhcp4ClassEntry
			MAX-ACCESS not-accessible
			STATUS current
			DESCRIPTION
				"Description."
			INDEX { sleV2Dhcp4ClassName }
			::= { sleV2Dhcp4ClassTable 1 }

		
		SleV2Dhcp4ClassEntry ::=
			SEQUENCE { 
				sleV2Dhcp4ClassName
					OCTET STRING
			 }

		-- 1.3.6.1.4.1.6296.102.6.2.3.3.1.1.1.1
		sleV2Dhcp4ClassName OBJECT-TYPE
			SYNTAX OCTET STRING (SIZE (1..32))
			MAX-ACCESS read-only
			STATUS current
			DESCRIPTION
				"Description."
			::= { sleV2Dhcp4ClassEntry 1 }

		
		-- 1.3.6.1.4.1.6296.102.6.2.3.3.1.2
		sleV2Dhcp4ClassControl OBJECT IDENTIFIER ::= { sleV2Dhcp4ClassBase 2 }

		
		-- 1.3.6.1.4.1.6296.102.6.2.3.3.1.2.1
		sleV2Dhcp4ClassControlRequest OBJECT-TYPE
			SYNTAX INTEGER
				{
				createDhcpClass(1),
				destroyDhcpClass(2)
				}
			MAX-ACCESS read-write
			STATUS current
			DESCRIPTION
				"Description."
			::= { sleV2Dhcp4ClassControl 1 }

		
		-- 1.3.6.1.4.1.6296.102.6.2.3.3.1.2.2
		sleV2Dhcp4ClassControlStatus OBJECT-TYPE
			SYNTAX SleControlStatusType
			MAX-ACCESS read-only
			STATUS current
			DESCRIPTION
				"Description."
			::= { sleV2Dhcp4ClassControl 2 }

		
		-- 1.3.6.1.4.1.6296.102.6.2.3.3.1.2.3
		sleV2Dhcp4ClassControlTimer OBJECT-TYPE
			SYNTAX Gauge32
			MAX-ACCESS read-write
			STATUS current
			DESCRIPTION
				"Description."
			::= { sleV2Dhcp4ClassControl 3 }

		
		-- 1.3.6.1.4.1.6296.102.6.2.3.3.1.2.4
		sleV2Dhcp4ClassControlTimeStamp OBJECT-TYPE
			SYNTAX TimeTicks
			MAX-ACCESS read-only
			STATUS current
			DESCRIPTION
				"Description."
			::= { sleV2Dhcp4ClassControl 4 }

		
		-- 1.3.6.1.4.1.6296.102.6.2.3.3.1.2.5
		sleV2Dhcp4ClassControlReqResult OBJECT-TYPE
			SYNTAX SleControlRequestResultType
			MAX-ACCESS read-only
			STATUS current
			DESCRIPTION
				"Description."
			::= { sleV2Dhcp4ClassControl 5 }

		
		-- 1.3.6.1.4.1.6296.102.6.2.3.3.1.2.6
		sleV2Dhcp4ClassControlName OBJECT-TYPE
			SYNTAX OCTET STRING (SIZE (1..32))
			MAX-ACCESS read-write
			STATUS current
			DESCRIPTION
				"Description."
			::= { sleV2Dhcp4ClassControl 6 }

		
		-- 1.3.6.1.4.1.6296.102.6.2.3.3.1.3
		sleV2Dhcp4ClassNotification OBJECT IDENTIFIER ::= { sleV2Dhcp4ClassBase 3 }

		
		-- 1.3.6.1.4.1.6296.102.6.2.3.3.1.3.1
		sleV2Dhcp4ClassCreated NOTIFICATION-TYPE
			OBJECTS { sleV2Dhcp4ClassControlRequest, sleV2Dhcp4ClassControlTimeStamp, sleV2Dhcp4ClassControlReqResult, sleV2Dhcp4ClassControlName }
			STATUS current
			DESCRIPTION 
				"Description."
			::= { sleV2Dhcp4ClassNotification 1 }

		
		-- 1.3.6.1.4.1.6296.102.6.2.3.3.1.3.2
		sleV2Dhcp4ClassDestroyed NOTIFICATION-TYPE
			OBJECTS { sleV2Dhcp4ClassControlRequest, sleV2Dhcp4ClassControlTimeStamp, sleV2Dhcp4ClassControlReqResult, sleV2Dhcp4ClassControlName }
			STATUS current
			DESCRIPTION 
				"Description."
			::= { sleV2Dhcp4ClassNotification 2 }

		
		-- 1.3.6.1.4.1.6296.102.6.2.3.3.2
		sleV2Dhcp4CRCMap OBJECT IDENTIFIER ::= { sleV2Dhcp4Class 2 }

		
		-- 1.3.6.1.4.1.6296.102.6.2.3.3.2.1
		sleV2Dhcp4CRCMapTable OBJECT-TYPE
			SYNTAX SEQUENCE OF SleV2Dhcp4CRCMapEntry
			MAX-ACCESS not-accessible
			STATUS current
			DESCRIPTION
				"Description."
			::= { sleV2Dhcp4CRCMap 1 }

		
		-- 1.3.6.1.4.1.6296.102.6.2.3.3.2.1.1
		sleV2Dhcp4CRCMapEntry OBJECT-TYPE
			SYNTAX SleV2Dhcp4CRCMapEntry
			MAX-ACCESS not-accessible
			STATUS current
			DESCRIPTION
				"Description."
			INDEX { sleV2Dhcp4CRCMapClass, sleV2Dhcp4CRCMapRemote, sleV2Dhcp4CRCMapCircuit }
			::= { sleV2Dhcp4CRCMapTable 1 }

		
		SleV2Dhcp4CRCMapEntry ::=
			SEQUENCE { 
				sleV2Dhcp4CRCMapClass
					OCTET STRING,
				sleV2Dhcp4CRCMapRemote
					OCTET STRING,
				sleV2Dhcp4CRCMapCircuit
					OCTET STRING
			 }

		-- 1.3.6.1.4.1.6296.102.6.2.3.3.2.1.1.1
		sleV2Dhcp4CRCMapClass OBJECT-TYPE
			SYNTAX OCTET STRING (SIZE (1..32))
			MAX-ACCESS read-only
			STATUS current
			DESCRIPTION
				"Description."
			::= { sleV2Dhcp4CRCMapEntry 1 }

		
		-- 1.3.6.1.4.1.6296.102.6.2.3.3.2.1.1.2
		sleV2Dhcp4CRCMapRemote OBJECT-TYPE
			SYNTAX OCTET STRING (SIZE (1..64))
			MAX-ACCESS read-only
			STATUS current
			DESCRIPTION
				"Description."
			::= { sleV2Dhcp4CRCMapEntry 2 }

		
		-- 1.3.6.1.4.1.6296.102.6.2.3.3.2.1.1.3
		sleV2Dhcp4CRCMapCircuit OBJECT-TYPE
			SYNTAX OCTET STRING (SIZE (0 | 1..32))
			MAX-ACCESS read-only
			STATUS current
			DESCRIPTION
				"Description."
			::= { sleV2Dhcp4CRCMapEntry 3 }

		
		-- 1.3.6.1.4.1.6296.102.6.2.3.3.2.2
		sleV2Dhcp4CRCMapControl OBJECT IDENTIFIER ::= { sleV2Dhcp4CRCMap 2 }

		
		-- 1.3.6.1.4.1.6296.102.6.2.3.3.2.2.1
		sleV2Dhcp4CRCMapControlRequest OBJECT-TYPE
			SYNTAX INTEGER
				{
				clearDhcpClassMapCircuits(1),
				clearDhcpClassMapRemotes(2)
				}
			MAX-ACCESS read-write
			STATUS current
			DESCRIPTION
				"The request of a user command."
			::= { sleV2Dhcp4CRCMapControl 1 }

		
		-- 1.3.6.1.4.1.6296.102.6.2.3.3.2.2.2
		sleV2Dhcp4CRCMapControlStatus OBJECT-TYPE
			SYNTAX SleControlStatusType
			MAX-ACCESS read-only
			STATUS current
			DESCRIPTION
				"The status of a user command."
			::= { sleV2Dhcp4CRCMapControl 2 }

		
		-- 1.3.6.1.4.1.6296.102.6.2.3.3.2.2.3
		sleV2Dhcp4CRCMapControlTimer OBJECT-TYPE
			SYNTAX Gauge32
			MAX-ACCESS read-write
			STATUS current
			DESCRIPTION
				"The maximum wait Time for the manager for a long running user command."
			::= { sleV2Dhcp4CRCMapControl 3 }

		
		-- 1.3.6.1.4.1.6296.102.6.2.3.3.2.2.4
		sleV2Dhcp4CRCMapControlTimeStamp OBJECT-TYPE
			SYNTAX TimeTicks
			MAX-ACCESS read-only
			STATUS current
			DESCRIPTION
				"The Time stamp of the last command (end of command)."
			::= { sleV2Dhcp4CRCMapControl 4 }

		
		-- 1.3.6.1.4.1.6296.102.6.2.3.3.2.2.5
		sleV2Dhcp4CRCMapControlReqResult OBJECT-TYPE
			SYNTAX SleControlRequestResultType
			MAX-ACCESS read-only
			STATUS current
			DESCRIPTION
				"The result of the last user command."
			::= { sleV2Dhcp4CRCMapControl 5 }

		
		-- 1.3.6.1.4.1.6296.102.6.2.3.3.2.2.6
		sleV2Dhcp4CRCMapControlClass OBJECT-TYPE
			SYNTAX OCTET STRING (SIZE (1..32))
			MAX-ACCESS read-write
			STATUS current
			DESCRIPTION
				"Description."
			::= { sleV2Dhcp4CRCMapControl 6 }

		
		-- 1.3.6.1.4.1.6296.102.6.2.3.3.2.2.7
		sleV2Dhcp4CRCMapControlRemote OBJECT-TYPE
			SYNTAX OCTET STRING (SIZE (1..32))
			MAX-ACCESS read-write
			STATUS current
			DESCRIPTION
				"Description."
			::= { sleV2Dhcp4CRCMapControl 7 }

		
		-- 1.3.6.1.4.1.6296.102.6.2.3.3.2.3
		sleV2Dhcp4CRCMapNotification OBJECT IDENTIFIER ::= { sleV2Dhcp4CRCMap 3 }

		
		-- 1.3.6.1.4.1.6296.102.6.2.3.3.2.3.1
		sleV2Dhcp4CRCMapCircuitCleared NOTIFICATION-TYPE
			OBJECTS { sleV2Dhcp4CRCMapControlRequest, sleV2Dhcp4CRCMapControlTimeStamp, sleV2Dhcp4CRCMapControlReqResult, sleV2Dhcp4CRCMapControlClass, sleV2Dhcp4CRCMapControlRemote
				 }
			STATUS current
			DESCRIPTION 
				"Description."
			::= { sleV2Dhcp4CRCMapNotification 1 }

		
		-- 1.3.6.1.4.1.6296.102.6.2.3.3.2.3.2
		sleV2Dhcp4CRCMapRemoteCleared NOTIFICATION-TYPE
			OBJECTS { sleV2Dhcp4CRCMapControlRequest, sleV2Dhcp4CRCMapControlTimeStamp, sleV2Dhcp4CRCMapControlReqResult, sleV2Dhcp4CRCMapControlClass }
			STATUS current
			DESCRIPTION 
				"Description."
			::= { sleV2Dhcp4CRCMapNotification 2 }

		
		-- 1.3.6.1.4.1.6296.102.6.2.3.3.3
		sleV2Dhcp4ClassRange OBJECT IDENTIFIER ::= { sleV2Dhcp4Class 3 }

		
		-- 1.3.6.1.4.1.6296.102.6.2.3.3.3.1
		sleV2Dhcp4ClassRangeTable OBJECT-TYPE
			SYNTAX SEQUENCE OF SleV2Dhcp4ClassRangeEntry
			MAX-ACCESS not-accessible
			STATUS current
			DESCRIPTION
				"Description."
			::= { sleV2Dhcp4ClassRange 1 }

		
		-- 1.3.6.1.4.1.6296.102.6.2.3.3.3.1.1
		sleV2Dhcp4ClassRangeEntry OBJECT-TYPE
			SYNTAX SleV2Dhcp4ClassRangeEntry
			MAX-ACCESS not-accessible
			STATUS current
			DESCRIPTION
				"Description."
			INDEX { sleV2Dhcp4PoolIndex, sleV2Dhcp4ClassName, sleV2Dhcp4ClassRangeStart, sleV2Dhcp4ClassRangeEnd }
			::= { sleV2Dhcp4ClassRangeTable 1 }

		
		SleV2Dhcp4ClassRangeEntry ::=
			SEQUENCE { 
				sleV2Dhcp4ClassRangeStart
					IpAddress,
				sleV2Dhcp4ClassRangeEnd
					IpAddress
			 }

		-- 1.3.6.1.4.1.6296.102.6.2.3.3.3.1.1.1
		sleV2Dhcp4ClassRangeStart OBJECT-TYPE
			SYNTAX IpAddress
			MAX-ACCESS read-only
			STATUS current
			DESCRIPTION
				"Description."
			::= { sleV2Dhcp4ClassRangeEntry 1 }

		
		-- 1.3.6.1.4.1.6296.102.6.2.3.3.3.1.1.2
		sleV2Dhcp4ClassRangeEnd OBJECT-TYPE
			SYNTAX IpAddress
			MAX-ACCESS read-only
			STATUS current
			DESCRIPTION
				"Description."
			::= { sleV2Dhcp4ClassRangeEntry 2 }

		
		-- 1.3.6.1.4.1.6296.102.6.2.3.3.3.2
		sleV2Dhcp4ClassRangeControl OBJECT IDENTIFIER ::= { sleV2Dhcp4ClassRange 2 }

		
		-- 1.3.6.1.4.1.6296.102.6.2.3.3.3.2.1
		sleV2Dhcp4ClassRangeControlRequest OBJECT-TYPE
			SYNTAX INTEGER
				{
				createDhcpClassRange(1),
				destoryDhcpClassRange(2)
				}
			MAX-ACCESS read-write
			STATUS current
			DESCRIPTION
				"The request of a user command."
			::= { sleV2Dhcp4ClassRangeControl 1 }

		
		-- 1.3.6.1.4.1.6296.102.6.2.3.3.3.2.2
		sleV2Dhcp4ClassRangeControlStatus OBJECT-TYPE
			SYNTAX SleControlStatusType
			MAX-ACCESS read-only
			STATUS current
			DESCRIPTION
				"The status of a user command."
			::= { sleV2Dhcp4ClassRangeControl 2 }

		
		-- 1.3.6.1.4.1.6296.102.6.2.3.3.3.2.3
		sleV2Dhcp4ClassRangeControlTimer OBJECT-TYPE
			SYNTAX Gauge32
			MAX-ACCESS read-write
			STATUS current
			DESCRIPTION
				"The maximum wait Time for the manager for a long running user command."
			::= { sleV2Dhcp4ClassRangeControl 3 }

		
		-- 1.3.6.1.4.1.6296.102.6.2.3.3.3.2.4
		sleV2Dhcp4ClassRangeControlTimeStamp OBJECT-TYPE
			SYNTAX TimeTicks
			MAX-ACCESS read-only
			STATUS current
			DESCRIPTION
				"The Time stamp of the last command (end of command)."
			::= { sleV2Dhcp4ClassRangeControl 4 }

		
		-- 1.3.6.1.4.1.6296.102.6.2.3.3.3.2.5
		sleV2Dhcp4ClassRangeControlReqResult OBJECT-TYPE
			SYNTAX SleControlRequestResultType
			MAX-ACCESS read-only
			STATUS current
			DESCRIPTION
				"The result of the last user command."
			::= { sleV2Dhcp4ClassRangeControl 5 }

		
		-- 1.3.6.1.4.1.6296.102.6.2.3.3.3.2.6
		sleV2Dhcp4ClassRangeControlPoolIndex OBJECT-TYPE
			SYNTAX INTEGER (1..255)
			MAX-ACCESS read-write
			STATUS current
			DESCRIPTION
				"Description."
			::= { sleV2Dhcp4ClassRangeControl 6 }

		
		-- 1.3.6.1.4.1.6296.102.6.2.3.3.3.2.7
		sleV2Dhcp4ClassRangeControlName OBJECT-TYPE
			SYNTAX OCTET STRING (SIZE (1..32))
			MAX-ACCESS read-write
			STATUS current
			DESCRIPTION
				"Description."
			::= { sleV2Dhcp4ClassRangeControl 7 }

		
		-- 1.3.6.1.4.1.6296.102.6.2.3.3.3.2.8
		sleV2Dhcp4ClassRangeControlStart OBJECT-TYPE
			SYNTAX IpAddress
			MAX-ACCESS read-write
			STATUS current
			DESCRIPTION
				"Description."
			::= { sleV2Dhcp4ClassRangeControl 8 }

		
		-- 1.3.6.1.4.1.6296.102.6.2.3.3.3.2.9
		sleV2Dhcp4ClassRangeControlEnd OBJECT-TYPE
			SYNTAX IpAddress
			MAX-ACCESS read-write
			STATUS current
			DESCRIPTION
				"Description."
			::= { sleV2Dhcp4ClassRangeControl 9 }

		
		-- 1.3.6.1.4.1.6296.102.6.2.3.3.3.3
		sleV2Dhcp4ClassRangeNotification OBJECT IDENTIFIER ::= { sleV2Dhcp4ClassRange 3 }

		
		-- 1.3.6.1.4.1.6296.102.6.2.3.3.3.3.1
		sleV2Dhcp4ClassRangeCreated NOTIFICATION-TYPE
			OBJECTS { sleV2Dhcp4ClassRangeControlRequest, sleV2Dhcp4ClassRangeControlTimeStamp, sleV2Dhcp4ClassRangeControlReqResult, sleV2Dhcp4ClassRangeControlPoolIndex, sleV2Dhcp4ClassRangeControlName, 
				sleV2Dhcp4ClassRangeControlStart, sleV2Dhcp4ClassRangeControlEnd }
			STATUS current
			DESCRIPTION 
				"Description."
			::= { sleV2Dhcp4ClassRangeNotification 1 }

		
		-- 1.3.6.1.4.1.6296.102.6.2.3.3.3.3.2
		sleV2Dhcp4ClassRangeDestroyed NOTIFICATION-TYPE
			OBJECTS { sleV2Dhcp4ClassRangeControlRequest, sleV2Dhcp4ClassRangeControlTimeStamp, sleV2Dhcp4ClassRangeControlReqResult, sleV2Dhcp4ClassRangeControlPoolIndex, sleV2Dhcp4ClassRangeControlName, 
				sleV2Dhcp4ClassRangeControlStart, sleV2Dhcp4ClassRangeControlEnd }
			STATUS current
			DESCRIPTION 
				"Description."
			::= { sleV2Dhcp4ClassRangeNotification 2 }

		
		-- 1.3.6.1.4.1.6296.102.6.2.3.4
		sleV2Dhcp4OptionFormat OBJECT IDENTIFIER ::= { sleV2Dhcp4Option82 4 }

		
		-- 1.3.6.1.4.1.6296.102.6.2.3.4.1
		sleV2Dhcp4OptionFormatBase OBJECT IDENTIFIER ::= { sleV2Dhcp4OptionFormat 1 }

		
		-- 1.3.6.1.4.1.6296.102.6.2.3.4.1.1
		sleV2Dhcp4OptionFormatTable OBJECT-TYPE
			SYNTAX SEQUENCE OF SleV2Dhcp4OptionFormatEntry
			MAX-ACCESS not-accessible
			STATUS current
			DESCRIPTION
				"Description."
			::= { sleV2Dhcp4OptionFormatBase 1 }

		
		-- 1.3.6.1.4.1.6296.102.6.2.3.4.1.1.1
		sleV2Dhcp4OptionFormatEntry OBJECT-TYPE
			SYNTAX SleV2Dhcp4OptionFormatEntry
			MAX-ACCESS not-accessible
			STATUS current
			DESCRIPTION
				"Description."
			INDEX { sleV2Dhcp4OptionFormatName }
			::= { sleV2Dhcp4OptionFormatTable 1 }

		
		SleV2Dhcp4OptionFormatEntry ::=
			SEQUENCE { 
				sleV2Dhcp4OptionFormatName
					OCTET STRING
			 }

		-- 1.3.6.1.4.1.6296.102.6.2.3.4.1.1.1.1
		sleV2Dhcp4OptionFormatName OBJECT-TYPE
			SYNTAX OCTET STRING (SIZE (1..16))
			MAX-ACCESS read-only
			STATUS current
			DESCRIPTION
				"The name of Option Format"
			::= { sleV2Dhcp4OptionFormatEntry 1 }

		
		-- 1.3.6.1.4.1.6296.102.6.2.3.4.1.2
		sleV2Dhcp4OptionFormatControl OBJECT IDENTIFIER ::= { sleV2Dhcp4OptionFormatBase 2 }

		
		-- 1.3.6.1.4.1.6296.102.6.2.3.4.1.2.1
		sleV2Dhcp4OptionFormatControlRequest OBJECT-TYPE
			SYNTAX INTEGER
				{
				createOptionFormat(1),
				destroyOptionFormat(2)
				}
			MAX-ACCESS read-write
			STATUS current
			DESCRIPTION
				"The request of a user command"
			::= { sleV2Dhcp4OptionFormatControl 1 }
-- The request of a user command
		
		-- 1.3.6.1.4.1.6296.102.6.2.3.4.1.2.2
		sleV2Dhcp4OptionFormatControlStatus OBJECT-TYPE
			SYNTAX SleControlStatusType
			MAX-ACCESS read-only
			STATUS current
			DESCRIPTION
				"The status of user command"
			::= { sleV2Dhcp4OptionFormatControl 2 }

		
		-- 1.3.6.1.4.1.6296.102.6.2.3.4.1.2.3
		sleV2Dhcp4OptionFormatControlTimer OBJECT-TYPE
			SYNTAX Gauge32
			MAX-ACCESS read-write
			STATUS current
			DESCRIPTION
				"The maximum time for the manager for a long running user command"
			::= { sleV2Dhcp4OptionFormatControl 3 }

		
		-- 1.3.6.1.4.1.6296.102.6.2.3.4.1.2.4
		sleV2Dhcp4OptionFormatControlTimeStamp OBJECT-TYPE
			SYNTAX TimeTicks
			MAX-ACCESS read-only
			STATUS current
			DESCRIPTION
				"The time stamp of the last command(end of command)"
			::= { sleV2Dhcp4OptionFormatControl 4 }

		
		-- 1.3.6.1.4.1.6296.102.6.2.3.4.1.2.5
		sleV2Dhcp4OptionFormatControlReqResult OBJECT-TYPE
			SYNTAX SleControlRequestResultType
			MAX-ACCESS read-only
			STATUS current
			DESCRIPTION
				"The result of the last user command"
			::= { sleV2Dhcp4OptionFormatControl 5 }

		
		-- 1.3.6.1.4.1.6296.102.6.2.3.4.1.2.6
		sleV2Dhcp4OptionFormatControlName OBJECT-TYPE
			SYNTAX OCTET STRING (SIZE (1..32))
			MAX-ACCESS read-write
			STATUS current
			DESCRIPTION
				"The name of Option Format"
			::= { sleV2Dhcp4OptionFormatControl 6 }

		
		-- 1.3.6.1.4.1.6296.102.6.2.3.4.1.3
		sleV2Dhcp4OptionFormatNotification OBJECT IDENTIFIER ::= { sleV2Dhcp4OptionFormatBase 3 }

		
		-- 1.3.6.1.4.1.6296.102.6.2.3.4.1.3.1
		sleV2Dhcp4OptionFormatCreated NOTIFICATION-TYPE
			OBJECTS { sleV2Dhcp4OptionFormatControlRequest, sleV2Dhcp4OptionFormatControlName, sleV2Dhcp4OptionFormatControlTimeStamp, sleV2Dhcp4OptionFormatControlReqResult }
			STATUS current
			DESCRIPTION 
				"Description."
			::= { sleV2Dhcp4OptionFormatNotification 1 }

		
		-- 1.3.6.1.4.1.6296.102.6.2.3.4.1.3.2
		sleV2Dhcp4OptionFormatDestroyed NOTIFICATION-TYPE
			OBJECTS { sleV2Dhcp4OptionFormatControlRequest, sleV2Dhcp4OptionFormatControlName, sleV2Dhcp4OptionFormatControlReqResult, sleV2Dhcp4OptionFormatControlTimeStamp }
			STATUS current
			DESCRIPTION 
				"Description."
			::= { sleV2Dhcp4OptionFormatNotification 2 }

		
		-- 1.3.6.1.4.1.6296.102.6.2.3.4.2
		sleV2Dhcp4OptionFormatAttribute OBJECT IDENTIFIER ::= { sleV2Dhcp4OptionFormat 2 }

		
		-- 1.3.6.1.4.1.6296.102.6.2.3.4.2.1
		sleV2Dhcp4OptionFormatAttrTable OBJECT-TYPE
			SYNTAX SEQUENCE OF SleV2Dhcp4OptionFormatAttrEntry
			MAX-ACCESS not-accessible
			STATUS current
			DESCRIPTION
				"Description."
			::= { sleV2Dhcp4OptionFormatAttribute 1 }

		
		-- 1.3.6.1.4.1.6296.102.6.2.3.4.2.1.1
		sleV2Dhcp4OptionFormatAttrEntry OBJECT-TYPE
			SYNTAX SleV2Dhcp4OptionFormatAttrEntry
			MAX-ACCESS not-accessible
			STATUS current
			DESCRIPTION
				"Description."
			INDEX { sleV2Dhcp4OptionFormatName, sleV2Dhcp4OptionFormatAttrID }
			::= { sleV2Dhcp4OptionFormatAttrTable 1 }

		
		SleV2Dhcp4OptionFormatAttrEntry ::=
			SEQUENCE { 
				sleV2Dhcp4OptionFormatAttrID
					INTEGER,
				sleV2Dhcp4OptionFormatAttrLength
					INTEGER,
				sleV2Dhcp4OptionFormatAttrHiddenLength
					INTEGER,
				sleV2Dhcp4OptionFormatAttrType
					INTEGER,
				sleV2Dhcp4OptionFormatAttrVarType
					INTEGER,
				sleV2Dhcp4OptionFormatAttrVarValue
					OCTET STRING
			 }

		-- 1.3.6.1.4.1.6296.102.6.2.3.4.2.1.1.1
		sleV2Dhcp4OptionFormatAttrID OBJECT-TYPE
			SYNTAX INTEGER (1..32)
			MAX-ACCESS read-only
			STATUS current
			DESCRIPTION
				"The ID of Option Format Attr"
			::= { sleV2Dhcp4OptionFormatAttrEntry 1 }

		
		-- 1.3.6.1.4.1.6296.102.6.2.3.4.2.1.1.2
		sleV2Dhcp4OptionFormatAttrLength OBJECT-TYPE
			SYNTAX INTEGER (-1..64)
			MAX-ACCESS read-write
			STATUS current
			DESCRIPTION
				"The Length Field of Option Format Attr.
				The -1 of value means this field is not defined.
				The Zero of value means this field is variable.
				"
			::= { sleV2Dhcp4OptionFormatAttrEntry 2 }

		
		-- 1.3.6.1.4.1.6296.102.6.2.3.4.2.1.1.3
		sleV2Dhcp4OptionFormatAttrHiddenLength OBJECT-TYPE
			SYNTAX INTEGER (-1..64)
			MAX-ACCESS read-write
			STATUS current
			DESCRIPTION
				"The Hidden Length Field of Option Format Attr.
				The -1 of value means this field is not defined.
				The Zero of value means this field is variable.
				
				"
			::= { sleV2Dhcp4OptionFormatAttrEntry 3 }

		
		-- 1.3.6.1.4.1.6296.102.6.2.3.4.2.1.1.4
		sleV2Dhcp4OptionFormatAttrType OBJECT-TYPE
			SYNTAX INTEGER (-1..255)
			MAX-ACCESS read-write
			STATUS current
			DESCRIPTION
				"The Hidden Length Field of Option Format Attr.
				The -1 of value means this field is not defined.
				"
			::= { sleV2Dhcp4OptionFormatAttrEntry 4 }

		
		-- 1.3.6.1.4.1.6296.102.6.2.3.4.2.1.1.5
		sleV2Dhcp4OptionFormatAttrVarType OBJECT-TYPE
			SYNTAX INTEGER
				{
				hex(1),
				ifIp(2),
				index(3),
				ip(4),
				string(5)
				}
			MAX-ACCESS read-only
			STATUS current
			DESCRIPTION
				"The Variable Type Field of Option Format Attr."
			::= { sleV2Dhcp4OptionFormatAttrEntry 5 }

		
		-- 1.3.6.1.4.1.6296.102.6.2.3.4.2.1.1.6
		sleV2Dhcp4OptionFormatAttrVarValue OBJECT-TYPE
			SYNTAX OCTET STRING (SIZE (1..255))
			MAX-ACCESS read-write
			STATUS current
			DESCRIPTION
				"The Variable Value Field of Option Format Attr.
				"
			::= { sleV2Dhcp4OptionFormatAttrEntry 6 }

		
		-- 1.3.6.1.4.1.6296.102.6.2.3.4.2.2
		sleV2Dhcp4OptionFormatAttrControl OBJECT IDENTIFIER ::= { sleV2Dhcp4OptionFormatAttribute 2 }

		
		-- 1.3.6.1.4.1.6296.102.6.2.3.4.2.2.1
		sleV2Dhcp4OptionFormatAttrControlRequest OBJECT-TYPE
			SYNTAX INTEGER
				{
				addOptionFormatAttr(1),
				deleteOptionFormatAttr(2),
				modifyOptionFormatAttr(3)
				}
			MAX-ACCESS read-write
			STATUS current
			DESCRIPTION
				"The request of a user command."
			::= { sleV2Dhcp4OptionFormatAttrControl 1 }

		
		-- 1.3.6.1.4.1.6296.102.6.2.3.4.2.2.2
		sleV2Dhcp4OptionFormatAttrControlStatus OBJECT-TYPE
			SYNTAX SleControlStatusType
			MAX-ACCESS read-only
			STATUS current
			DESCRIPTION
				"The status of user command."
			::= { sleV2Dhcp4OptionFormatAttrControl 2 }

		
		-- 1.3.6.1.4.1.6296.102.6.2.3.4.2.2.3
		sleV2Dhcp4OptionFormatAttrControlTimer OBJECT-TYPE
			SYNTAX Gauge32
			MAX-ACCESS read-write
			STATUS current
			DESCRIPTION
				"The maximum time for the manager for a long running user command."
			::= { sleV2Dhcp4OptionFormatAttrControl 3 }

		
		-- 1.3.6.1.4.1.6296.102.6.2.3.4.2.2.4
		sleV2Dhcp4OptionFormatAttrControlTimeStamp OBJECT-TYPE
			SYNTAX TimeTicks
			MAX-ACCESS read-only
			STATUS current
			DESCRIPTION
				"The time stamp of the last command(end of command)."
			::= { sleV2Dhcp4OptionFormatAttrControl 4 }

		
		-- 1.3.6.1.4.1.6296.102.6.2.3.4.2.2.5
		sleV2Dhcp4OptionFormatAttrControlReqResult OBJECT-TYPE
			SYNTAX SleControlRequestResultType
			MAX-ACCESS read-only
			STATUS current
			DESCRIPTION
				"The result of the last user command."
			::= { sleV2Dhcp4OptionFormatAttrControl 5 }

		
		-- 1.3.6.1.4.1.6296.102.6.2.3.4.2.2.6
		sleV2Dhcp4OptionFormatAttrControlName OBJECT-TYPE
			SYNTAX OCTET STRING (SIZE (1..16))
			MAX-ACCESS read-write
			STATUS current
			DESCRIPTION
				"The name of Option Format."
			::= { sleV2Dhcp4OptionFormatAttrControl 6 }

		
		-- 1.3.6.1.4.1.6296.102.6.2.3.4.2.2.7
		sleV2Dhcp4OptionFormatAttrControlID OBJECT-TYPE
			SYNTAX INTEGER (1..64)
			MAX-ACCESS read-write
			STATUS current
			DESCRIPTION
				"The ID of Option Format Attr."
			::= { sleV2Dhcp4OptionFormatAttrControl 7 }

		
		-- 1.3.6.1.4.1.6296.102.6.2.3.4.2.2.8
		sleV2Dhcp4OptionFormatAttrControlLength OBJECT-TYPE
			SYNTAX INTEGER (-1..64)
			MAX-ACCESS read-write
			STATUS current
			DESCRIPTION
				"The Length Field of Option Format Attr.
				The -1 of value means this field is not defined.
				The Zero of value means this field is variable
				"
			::= { sleV2Dhcp4OptionFormatAttrControl 8 }

		
		-- 1.3.6.1.4.1.6296.102.6.2.3.4.2.2.9
		sleV2Dhcp4OptionFormatAttrControlHiddenLength OBJECT-TYPE
			SYNTAX INTEGER (-1..64)
			MAX-ACCESS read-write
			STATUS current
			DESCRIPTION
				"The Hidden Length Field of Option Format Attr.
				The -1 of value means this field is not defined.
				The Zero of value means this field is variable"
			::= { sleV2Dhcp4OptionFormatAttrControl 9 }
-- 
-- 
		
		-- 1.3.6.1.4.1.6296.102.6.2.3.4.2.2.10
		sleV2Dhcp4OptionFormatAttrControlType OBJECT-TYPE
			SYNTAX INTEGER (-1..255)
			MAX-ACCESS read-write
			STATUS current
			DESCRIPTION
				"The Type Field of Option Format Attr.
				The -1 of value means this field not defined."
			::= { sleV2Dhcp4OptionFormatAttrControl 10 }
-- 
-- 
		
		-- 1.3.6.1.4.1.6296.102.6.2.3.4.2.2.11
		sleV2Dhcp4OptionFormatAttrControlVarType OBJECT-TYPE
			SYNTAX INTEGER
				{
				hex(1),
				ifIp(2),
				index(3),
				ip(4),
				string(5)
				}
			MAX-ACCESS read-only
			STATUS current
			DESCRIPTION
				"The Variable Type Field of Option Format Attr."
			::= { sleV2Dhcp4OptionFormatAttrControl 11 }

		
		-- 1.3.6.1.4.1.6296.102.6.2.3.4.2.2.12
		sleV2Dhcp4OptionFormatAttrControlVarValue OBJECT-TYPE
			SYNTAX OCTET STRING (SIZE (1..255))
			MAX-ACCESS read-write
			STATUS current
			DESCRIPTION
				"The Variable Value Field of Option Format Attr."
			::= { sleV2Dhcp4OptionFormatAttrControl 12 }

		
		-- 1.3.6.1.4.1.6296.102.6.2.3.4.2.3
		sleV2Dhcp4OptionFormatAttrNotification OBJECT IDENTIFIER ::= { sleV2Dhcp4OptionFormatAttribute 3 }

		
		-- 1.3.6.1.4.1.6296.102.6.2.3.4.2.3.1
		sleV2Dhcp4OptionFormatAttrAdded NOTIFICATION-TYPE
			OBJECTS { sleV2Dhcp4OptionFormatAttrControlRequest, sleV2Dhcp4OptionFormatAttrControlVarValue, sleV2Dhcp4OptionFormatAttrControlVarType, sleV2Dhcp4OptionFormatAttrControlType, sleV2Dhcp4OptionFormatAttrControlHiddenLength, 
				sleV2Dhcp4OptionFormatAttrControlLength, sleV2Dhcp4OptionFormatAttrControlReqResult, sleV2Dhcp4OptionFormatAttrControlTimeStamp, sleV2Dhcp4OptionFormatAttrControlName, sleV2Dhcp4OptionFormatAttrControlID
				 }
			STATUS current
			DESCRIPTION 
				"addOptionFormatAttr."
			::= { sleV2Dhcp4OptionFormatAttrNotification 1 }

		
		-- 1.3.6.1.4.1.6296.102.6.2.3.4.2.3.2
		sleV2Dhcp4OptionFormatAttrDeleted NOTIFICATION-TYPE
			OBJECTS { sleV2Dhcp4OptionFormatAttrControlRequest, sleV2Dhcp4OptionFormatAttrControlID, sleV2Dhcp4OptionFormatAttrControlName, sleV2Dhcp4OptionFormatControlTimeStamp, sleV2Dhcp4OptionFormatControlReqResult
				 }
			STATUS current
			DESCRIPTION 
				"deleteOptionFormatAttr."
			::= { sleV2Dhcp4OptionFormatAttrNotification 2 }

		
		-- 1.3.6.1.4.1.6296.102.6.2.3.4.2.3.3
		sleV2Dhcp4OptionFormatAttrModified NOTIFICATION-TYPE
			OBJECTS { sleV2Dhcp4OptionFormatAttrControlRequest, sleV2Dhcp4OptionFormatAttrControlReqResult, sleV2Dhcp4OptionFormatAttrControlTimeStamp, sleV2Dhcp4OptionFormatAttrControlName, sleV2Dhcp4OptionFormatAttrControlID, 
				sleV2Dhcp4OptionFormatAttrControlLength, sleV2Dhcp4OptionFormatAttrControlHiddenLength, sleV2Dhcp4OptionFormatAttrControlType, sleV2Dhcp4OptionFormatAttrControlVarType, sleV2Dhcp4OptionFormatAttrControlVarValue
				 }
			STATUS current
			DESCRIPTION 
				"modifyOptionFormatAttr."
			::= { sleV2Dhcp4OptionFormatAttrNotification 3 }

		
		-- 1.3.6.1.4.1.6296.102.6.2.4
		sleV2Dhcp4Filter OBJECT IDENTIFIER ::= { sleV2Dhcp4 4 }

		
		-- 1.3.6.1.4.1.6296.102.6.2.4.1
		sleV2Dhcp4FilterPort OBJECT IDENTIFIER ::= { sleV2Dhcp4Filter 1 }

		
		-- 1.3.6.1.4.1.6296.102.6.2.4.1.1
		sleV2Dhcp4FilterPortTable OBJECT-TYPE
			SYNTAX SEQUENCE OF SleV2Dhcp4FilterPortEntry
			MAX-ACCESS not-accessible
			STATUS current
			DESCRIPTION
				"Description."
			::= { sleV2Dhcp4FilterPort 1 }

		
		-- 1.3.6.1.4.1.6296.102.6.2.4.1.1.1
		sleV2Dhcp4FilterPortEntry OBJECT-TYPE
			SYNTAX SleV2Dhcp4FilterPortEntry
			MAX-ACCESS not-accessible
			STATUS current
			DESCRIPTION
				"Description."
			INDEX { sleV2Dhcp4FilterPortIndex }
			::= { sleV2Dhcp4FilterPortTable 1 }

		
		SleV2Dhcp4FilterPortEntry ::=
			SEQUENCE { 
				sleV2Dhcp4FilterPortIndex
					INTEGER,
				sleV2Dhcp4FilterPortState
					INTEGER
			 }

		-- 1.3.6.1.4.1.6296.102.6.2.4.1.1.1.1
		sleV2Dhcp4FilterPortIndex OBJECT-TYPE
			SYNTAX INTEGER (1..255)
			MAX-ACCESS read-only
			STATUS current
			DESCRIPTION
				"Description."
			::= { sleV2Dhcp4FilterPortEntry 1 }

		
		-- 1.3.6.1.4.1.6296.102.6.2.4.1.1.1.2
		sleV2Dhcp4FilterPortState OBJECT-TYPE
			SYNTAX INTEGER
				{
				disable(0),
				enable(1)
				}
			MAX-ACCESS read-only
			STATUS current
			DESCRIPTION
				"Description."
			::= { sleV2Dhcp4FilterPortEntry 2 }

		
		-- 1.3.6.1.4.1.6296.102.6.2.4.1.2
		sleV2Dhcp4FilterPortControl OBJECT IDENTIFIER ::= { sleV2Dhcp4FilterPort 2 }

		
		-- 1.3.6.1.4.1.6296.102.6.2.4.1.2.1
		sleV2Dhcp4FilterPortControlRequest OBJECT-TYPE
			SYNTAX INTEGER { setDhcpFilterPortMode(1) }
			MAX-ACCESS read-write
			STATUS current
			DESCRIPTION
				"The request of a user command."
			::= { sleV2Dhcp4FilterPortControl 1 }

		
		-- 1.3.6.1.4.1.6296.102.6.2.4.1.2.2
		sleV2Dhcp4FilterPortControlStatus OBJECT-TYPE
			SYNTAX SleControlStatusType
			MAX-ACCESS read-only
			STATUS current
			DESCRIPTION
				"The status of a user command."
			::= { sleV2Dhcp4FilterPortControl 2 }

		
		-- 1.3.6.1.4.1.6296.102.6.2.4.1.2.3
		sleV2Dhcp4FilterPortControlTimer OBJECT-TYPE
			SYNTAX Gauge32
			MAX-ACCESS read-write
			STATUS current
			DESCRIPTION
				"The maximum wait Time for the manager for a long running user command."
			::= { sleV2Dhcp4FilterPortControl 3 }

		
		-- 1.3.6.1.4.1.6296.102.6.2.4.1.2.4
		sleV2Dhcp4FilterPortControlTimeStamp OBJECT-TYPE
			SYNTAX TimeTicks
			MAX-ACCESS read-only
			STATUS current
			DESCRIPTION
				"The Time stamp of the last command (end of command)."
			::= { sleV2Dhcp4FilterPortControl 4 }

		
		-- 1.3.6.1.4.1.6296.102.6.2.4.1.2.5
		sleV2Dhcp4FilterPortControlReqResult OBJECT-TYPE
			SYNTAX SleControlRequestResultType
			MAX-ACCESS read-only
			STATUS current
			DESCRIPTION
				"The result of the last user command."
			::= { sleV2Dhcp4FilterPortControl 5 }

		
		-- 1.3.6.1.4.1.6296.102.6.2.4.1.2.6
		sleV2Dhcp4FilterPortControlIndex OBJECT-TYPE
			SYNTAX INTEGER (1..255)
			MAX-ACCESS read-write
			STATUS current
			DESCRIPTION
				"Description."
			::= { sleV2Dhcp4FilterPortControl 6 }

		
		-- 1.3.6.1.4.1.6296.102.6.2.4.1.2.7
		sleV2Dhcp4FilterPortControlState OBJECT-TYPE
			SYNTAX INTEGER
				{
				disable(0),
				enable(1)
				}
			MAX-ACCESS read-write
			STATUS current
			DESCRIPTION
				"Description."
			::= { sleV2Dhcp4FilterPortControl 7 }

		
		-- 1.3.6.1.4.1.6296.102.6.2.4.1.3
		sleV2Dhcp4FilterPortNotification OBJECT IDENTIFIER ::= { sleV2Dhcp4FilterPort 3 }

		
		-- 1.3.6.1.4.1.6296.102.6.2.4.1.3.1
		sleV2Dhcp4FilterPortStateChanged NOTIFICATION-TYPE
			OBJECTS { sleV2Dhcp4FilterPortControlRequest, sleV2Dhcp4FilterPortControlTimeStamp, sleV2Dhcp4FilterPortControlReqResult, sleV2Dhcp4FilterPortState }
			STATUS current
			DESCRIPTION 
				"Description."
			::= { sleV2Dhcp4FilterPortNotification 1 }

		
		-- 1.3.6.1.4.1.6296.102.6.2.4.2
		sleV2Dhcp4FilterAddress OBJECT IDENTIFIER ::= { sleV2Dhcp4Filter 2 }

		
		-- 1.3.6.1.4.1.6296.102.6.2.4.2.1
		sleV2Dhcp4FilterAddressTable OBJECT-TYPE
			SYNTAX SEQUENCE OF SleV2Dhcp4FilterAddressEntry
			MAX-ACCESS not-accessible
			STATUS current
			DESCRIPTION
				"Description."
			::= { sleV2Dhcp4FilterAddress 1 }

		
		-- 1.3.6.1.4.1.6296.102.6.2.4.2.1.1
		sleV2Dhcp4FilterAddressEntry OBJECT-TYPE
			SYNTAX SleV2Dhcp4FilterAddressEntry
			MAX-ACCESS not-accessible
			STATUS current
			DESCRIPTION
				"Description."
			INDEX { sleV2Dhcp4FilterAddressMac }
			::= { sleV2Dhcp4FilterAddressTable 1 }

		
		SleV2Dhcp4FilterAddressEntry ::=
			SEQUENCE { 
				sleV2Dhcp4FilterAddressMac
					MacAddress,
				sleV2Dhcp4FilterAddressType
					BITS
			 }

		-- 1.3.6.1.4.1.6296.102.6.2.4.2.1.1.1
		sleV2Dhcp4FilterAddressMac OBJECT-TYPE
			SYNTAX MacAddress
			MAX-ACCESS read-only
			STATUS current
			DESCRIPTION
				"The mac address for the filtering.
				MAC address which IP address is not assigned"
			::= { sleV2Dhcp4FilterAddressEntry 1 }

		
		-- 1.3.6.1.4.1.6296.102.6.2.4.2.1.1.2
		sleV2Dhcp4FilterAddressType OBJECT-TYPE
			SYNTAX BITS
				{
				discover(0),
				offer(1),
				request(2),
				decline(3),
				ack(4),
				nak(5),
				release(6),
				inform(7)
				}
			MAX-ACCESS read-only
			STATUS current
			DESCRIPTION
				"The type can be assigned as a DHCP PACKET
				  ack       packet type - DHCPACK
				  decline   packet type - DHCPDECLINE
				  discover  packet type - DHCPDISCOVER
				  inform    packet type - DHCPINFORM
				  nak       packet type - DHCPNAK
				  offer     packet type - DHCPOFFER
				  release   packet type - DHCPRELEASE
				  request   packet type - DHCPREQUEST"
			::= { sleV2Dhcp4FilterAddressEntry 2 }

		
		-- 1.3.6.1.4.1.6296.102.6.2.4.2.2
		sleV2Dhcp4FilterAddressControl OBJECT IDENTIFIER ::= { sleV2Dhcp4FilterAddress 2 }

		
		-- 1.3.6.1.4.1.6296.102.6.2.4.2.2.1
		sleV2Dhcp4FilterAddressControlRequest OBJECT-TYPE
			SYNTAX INTEGER
				{
				createDhcpFilterAddress(1),
				destroyDhcpFilterAddress(2)
				}
			MAX-ACCESS read-write
			STATUS current
			DESCRIPTION
				"The request of a user command."
			::= { sleV2Dhcp4FilterAddressControl 1 }

		
		-- 1.3.6.1.4.1.6296.102.6.2.4.2.2.2
		sleV2Dhcp4FilterAddressControlStatus OBJECT-TYPE
			SYNTAX SleControlStatusType
			MAX-ACCESS read-only
			STATUS current
			DESCRIPTION
				"The status of a user command."
			::= { sleV2Dhcp4FilterAddressControl 2 }

		
		-- 1.3.6.1.4.1.6296.102.6.2.4.2.2.3
		sleV2Dhcp4FilterAddressControlTimer OBJECT-TYPE
			SYNTAX Gauge32
			MAX-ACCESS read-write
			STATUS current
			DESCRIPTION
				"The maximum wait Time for the manager for a long running user command."
			::= { sleV2Dhcp4FilterAddressControl 3 }

		
		-- 1.3.6.1.4.1.6296.102.6.2.4.2.2.4
		sleV2Dhcp4FilterAddressControlTimeStamp OBJECT-TYPE
			SYNTAX TimeTicks
			MAX-ACCESS read-only
			STATUS current
			DESCRIPTION
				"The Time stamp of the last command (end of command)."
			::= { sleV2Dhcp4FilterAddressControl 4 }

		
		-- 1.3.6.1.4.1.6296.102.6.2.4.2.2.5
		sleV2Dhcp4FilterAddressControlReqResult OBJECT-TYPE
			SYNTAX SleControlRequestResultType
			MAX-ACCESS read-only
			STATUS current
			DESCRIPTION
				"The result of the last user command."
			::= { sleV2Dhcp4FilterAddressControl 5 }

		
		-- 1.3.6.1.4.1.6296.102.6.2.4.2.2.6
		sleV2Dhcp4FilterAddressControlMac OBJECT-TYPE
			SYNTAX MacAddress
			MAX-ACCESS read-write
			STATUS current
			DESCRIPTION
				"The mac address for the filtering.
				MAC address which IP address is not assigned"
			::= { sleV2Dhcp4FilterAddressControl 6 }

		
		-- 1.3.6.1.4.1.6296.102.6.2.4.2.2.7
		sleV2Dhcp4FilterAddressControlType OBJECT-TYPE
			SYNTAX BITS
				{
				discover(0),
				offer(1),
				request(2),
				decline(3),
				ack(4),
				nak(5),
				release(6),
				inform(7)
				}
			MAX-ACCESS read-write
			STATUS current
			DESCRIPTION
				"The type can be assigned as a DHCP PACKET
				  ack       packet type - DHCPACK
				  decline   packet type - DHCPDECLINE
				  discover  packet type - DHCPDISCOVER
				  inform    packet type - DHCPINFORM
				  nak       packet type - DHCPNAK
				  offer     packet type - DHCPOFFER
				  release   packet type - DHCPRELEASE
				  request   packet type - DHCPREQUEST"
			::= { sleV2Dhcp4FilterAddressControl 7 }

		
		-- 1.3.6.1.4.1.6296.102.6.2.4.2.3
		sleV2Dhcp4FilterAddressNotification OBJECT IDENTIFIER ::= { sleV2Dhcp4FilterAddress 3 }

		
		-- 1.3.6.1.4.1.6296.102.6.2.4.2.3.1
		sleV2Dhcp4FilterAddressCreated NOTIFICATION-TYPE
			OBJECTS { sleV2Dhcp4FilterAddressControlRequest, sleV2Dhcp4FilterAddressControlTimeStamp, sleV2Dhcp4FilterAddressControlReqResult, sleV2Dhcp4FilterAddressControlMac, sleV2Dhcp4FilterAddressControlType
				 }
			STATUS current
			DESCRIPTION 
				"Description."
			::= { sleV2Dhcp4FilterAddressNotification 1 }

		
		-- 1.3.6.1.4.1.6296.102.6.2.4.2.3.2
		sleV2Dhcp4FilterAddressDestroyed NOTIFICATION-TYPE
			OBJECTS { sleV2Dhcp4FilterAddressControlRequest, sleV2Dhcp4FilterAddressControlTimeStamp, sleV2Dhcp4FilterAddressControlReqResult, sleV2Dhcp4FilterAddressControlMac, sleV2Dhcp4FilterAddressControlType
				 }
			STATUS current
			DESCRIPTION 
				"Description."
			::= { sleV2Dhcp4FilterAddressNotification 2 }

		
		-- 1.3.6.1.4.1.6296.102.6.2.4.3
		sleV2Dhcp4Illegal OBJECT IDENTIFIER ::= { sleV2Dhcp4Filter 3 }

		
		-- 1.3.6.1.4.1.6296.102.6.2.4.3.1
		sleV2Dhcp4IllegalTable OBJECT-TYPE
			SYNTAX SEQUENCE OF SleV2Dhcp4IllegalEntry
			MAX-ACCESS not-accessible
			STATUS current
			DESCRIPTION
				"Description."
			::= { sleV2Dhcp4Illegal 1 }

		
		-- 1.3.6.1.4.1.6296.102.6.2.4.3.1.1
		sleV2Dhcp4IllegalEntry OBJECT-TYPE
			SYNTAX SleV2Dhcp4IllegalEntry
			MAX-ACCESS not-accessible
			STATUS current
			DESCRIPTION
				"Description."
			INDEX { sleV2Dhcp4IllegalAddress, sleV2Dhcp4IllegalMac }
			::= { sleV2Dhcp4IllegalTable 1 }

		
		SleV2Dhcp4IllegalEntry ::=
			SEQUENCE { 
				sleV2Dhcp4IllegalAddress
					IpAddress,
				sleV2Dhcp4IllegalMac
					MacAddress,
				sleV2Dhcp4IllegalTime
					Unsigned32
			 }

		-- 1.3.6.1.4.1.6296.102.6.2.4.3.1.1.1
		sleV2Dhcp4IllegalAddress OBJECT-TYPE
			SYNTAX IpAddress
			MAX-ACCESS read-only
			STATUS current
			DESCRIPTION
				"The illegal IP address."
			::= { sleV2Dhcp4IllegalEntry 1 }

		
		-- 1.3.6.1.4.1.6296.102.6.2.4.3.1.1.2
		sleV2Dhcp4IllegalMac OBJECT-TYPE
			SYNTAX MacAddress
			MAX-ACCESS read-only
			STATUS current
			DESCRIPTION
				"The MAC Address of this illegal address."
			::= { sleV2Dhcp4IllegalEntry 2 }

		
		-- 1.3.6.1.4.1.6296.102.6.2.4.3.1.1.3
		sleV2Dhcp4IllegalTime OBJECT-TYPE
			SYNTAX Unsigned32
			MAX-ACCESS read-only
			STATUS current
			DESCRIPTION
				"단위는 1970.1.1일 0시 0분 0초부터 계산한 초"
			::= { sleV2Dhcp4IllegalEntry 3 }

		
		-- 1.3.6.1.4.1.6296.102.6.2.4.3.2
		sleV2Dhcp4IllegalControl OBJECT IDENTIFIER ::= { sleV2Dhcp4Illegal 2 }

		
		-- 1.3.6.1.4.1.6296.102.6.2.4.3.2.1
		sleV2Dhcp4IllegalControlRequest OBJECT-TYPE
			SYNTAX INTEGER { clearIllegal(1) }
			MAX-ACCESS read-write
			STATUS current
			DESCRIPTION
				"The request of a user command."
			::= { sleV2Dhcp4IllegalControl 1 }

		
		-- 1.3.6.1.4.1.6296.102.6.2.4.3.2.2
		sleV2Dhcp4IllegalControlStatus OBJECT-TYPE
			SYNTAX SleControlStatusType
			MAX-ACCESS read-only
			STATUS current
			DESCRIPTION
				"The status of a user command."
			::= { sleV2Dhcp4IllegalControl 2 }

		
		-- 1.3.6.1.4.1.6296.102.6.2.4.3.2.3
		sleV2Dhcp4IllegalControlTimer OBJECT-TYPE
			SYNTAX Gauge32
			MAX-ACCESS read-write
			STATUS current
			DESCRIPTION
				"The maximum wait Time for the manager for a long running user command."
			::= { sleV2Dhcp4IllegalControl 3 }

		
		-- 1.3.6.1.4.1.6296.102.6.2.4.3.2.4
		sleV2Dhcp4IllegalControlTimeStamp OBJECT-TYPE
			SYNTAX TimeTicks
			MAX-ACCESS read-only
			STATUS current
			DESCRIPTION
				"The Time stamp of the last command (end of command)."
			::= { sleV2Dhcp4IllegalControl 4 }

		
		-- 1.3.6.1.4.1.6296.102.6.2.4.3.2.5
		sleV2Dhcp4IllegalControlReqResult OBJECT-TYPE
			SYNTAX SleControlRequestResultType
			MAX-ACCESS read-only
			STATUS current
			DESCRIPTION
				"The result of the last user command."
			::= { sleV2Dhcp4IllegalControl 5 }

		
		-- 1.3.6.1.4.1.6296.102.6.2.4.3.3
		sleV2Dhcp4IllegalNotification OBJECT IDENTIFIER ::= { sleV2Dhcp4Illegal 3 }

		
		-- 1.3.6.1.4.1.6296.102.6.2.4.3.3.1
		sleV2Dhcp4IllegalCleared NOTIFICATION-TYPE
			OBJECTS { sleV2Dhcp4IllegalControlRequest, sleV2Dhcp4IllegalControlTimeStamp, sleV2Dhcp4IllegalControlReqResult }
			STATUS current
			DESCRIPTION 
				"Description."
			::= { sleV2Dhcp4IllegalNotification 1 }

		
		-- 1.3.6.1.4.1.6296.102.6.2.5
		sleV2Dhcp4Stats OBJECT IDENTIFIER ::= { sleV2Dhcp4 5 }

		
		-- 1.3.6.1.4.1.6296.102.6.2.5.1
		sleV2Dhcp4PacketStats OBJECT IDENTIFIER ::= { sleV2Dhcp4Stats 1 }

		
		-- 1.3.6.1.4.1.6296.102.6.2.5.1.1
		sleV2Dhcp4PacketStatsInfo OBJECT IDENTIFIER ::= { sleV2Dhcp4PacketStats 1 }

		
		-- 1.3.6.1.4.1.6296.102.6.2.5.1.1.1
		sleV2Dhcp4PacketStatsReceived OBJECT-TYPE
			SYNTAX Unsigned32
			MAX-ACCESS read-only
			STATUS current
			DESCRIPTION
				"The number of received DHCP packets."
			::= { sleV2Dhcp4PacketStatsInfo 1 }

		
		-- 1.3.6.1.4.1.6296.102.6.2.5.1.1.2
		sleV2Dhcp4PacketStatsSent OBJECT-TYPE
			SYNTAX Unsigned32
			MAX-ACCESS read-only
			STATUS current
			DESCRIPTION
				"The number of sent DHCP packets."
			::= { sleV2Dhcp4PacketStatsInfo 2 }

		
		-- 1.3.6.1.4.1.6296.102.6.2.5.1.1.3
		sleV2Dhcp4PacketStatsReceivedErrors OBJECT-TYPE
			SYNTAX Unsigned32
			MAX-ACCESS read-only
			STATUS current
			DESCRIPTION
				"The number of received DHCP Error packets."
			::= { sleV2Dhcp4PacketStatsInfo 3 }

		
		-- 1.3.6.1.4.1.6296.102.6.2.5.1.1.4
		sleV2Dhcp4PacketStatsSentErrors OBJECT-TYPE
			SYNTAX Unsigned32
			MAX-ACCESS read-only
			STATUS current
			DESCRIPTION
				"The number of sent DHCP Error packets."
			::= { sleV2Dhcp4PacketStatsInfo 4 }

		
		-- 1.3.6.1.4.1.6296.102.6.2.5.1.1.5
		sleV2Dhcp4PacketStatsBootpReceivedRequests OBJECT-TYPE
			SYNTAX Unsigned32
			MAX-ACCESS read-only
			STATUS current
			DESCRIPTION
				"The number of received DHCP Bootp Request packets."
			::= { sleV2Dhcp4PacketStatsInfo 5 }

		
		-- 1.3.6.1.4.1.6296.102.6.2.5.1.1.6
		sleV2Dhcp4PacketStatsBootpReceivedReplies OBJECT-TYPE
			SYNTAX Unsigned32
			MAX-ACCESS read-only
			STATUS current
			DESCRIPTION
				"The number of received DHCP Bootp Reply packets."
			::= { sleV2Dhcp4PacketStatsInfo 6 }

		
		-- 1.3.6.1.4.1.6296.102.6.2.5.1.1.7
		sleV2Dhcp4PacketStatsBootpSentRequests OBJECT-TYPE
			SYNTAX Unsigned32
			MAX-ACCESS read-only
			STATUS current
			DESCRIPTION
				"The number of sent DHCP Bootp Request packets."
			::= { sleV2Dhcp4PacketStatsInfo 7 }

		
		-- 1.3.6.1.4.1.6296.102.6.2.5.1.1.8
		sleV2Dhcp4PacketStatsBootpSentReplies OBJECT-TYPE
			SYNTAX Unsigned32
			MAX-ACCESS read-only
			STATUS current
			DESCRIPTION
				"The number of sent DHCP Bootp Reply packets."
			::= { sleV2Dhcp4PacketStatsInfo 8 }

		
		-- 1.3.6.1.4.1.6296.102.6.2.5.1.1.9
		sleV2Dhcp4PacketStatsReceivedDiscover OBJECT-TYPE
			SYNTAX Unsigned32
			MAX-ACCESS read-only
			STATUS current
			DESCRIPTION
				"The number of received Discover packets."
			::= { sleV2Dhcp4PacketStatsInfo 9 }

		
		-- 1.3.6.1.4.1.6296.102.6.2.5.1.1.10
		sleV2Dhcp4PacketStatsReceivedRequest OBJECT-TYPE
			SYNTAX Unsigned32
			MAX-ACCESS read-only
			STATUS current
			DESCRIPTION
				"The number of received DHCP Request packets."
			::= { sleV2Dhcp4PacketStatsInfo 10 }

		
		-- 1.3.6.1.4.1.6296.102.6.2.5.1.1.11
		sleV2Dhcp4PacketStatsReceivedRelease OBJECT-TYPE
			SYNTAX Unsigned32
			MAX-ACCESS read-only
			STATUS current
			DESCRIPTION
				"The number of received DHCP Release packets."
			::= { sleV2Dhcp4PacketStatsInfo 11 }

		
		-- 1.3.6.1.4.1.6296.102.6.2.5.1.1.12
		sleV2Dhcp4PacketStatscReceivedInform OBJECT-TYPE
			SYNTAX Unsigned32
			MAX-ACCESS read-only
			STATUS current
			DESCRIPTION
				"The number of received DHCP Inform packets."
			::= { sleV2Dhcp4PacketStatsInfo 12 }

		
		-- 1.3.6.1.4.1.6296.102.6.2.5.1.1.13
		sleV2Dhcp4PacketStatsReceivedDecline OBJECT-TYPE
			SYNTAX Unsigned32
			MAX-ACCESS read-only
			STATUS current
			DESCRIPTION
				"The number of received DHCP Decline packets."
			::= { sleV2Dhcp4PacketStatsInfo 13 }

		
		-- 1.3.6.1.4.1.6296.102.6.2.5.1.1.14
		sleV2Dhcp4PacketStatsSentOffer OBJECT-TYPE
			SYNTAX Unsigned32
			MAX-ACCESS read-only
			STATUS current
			DESCRIPTION
				"The number of sent DHCP Offer packets."
			::= { sleV2Dhcp4PacketStatsInfo 14 }

		
		-- 1.3.6.1.4.1.6296.102.6.2.5.1.1.15
		sleV2Dhcp4PacketStatsSentAck OBJECT-TYPE
			SYNTAX Unsigned32
			MAX-ACCESS read-only
			STATUS current
			DESCRIPTION
				"The number of sent DHCP Ack packets."
			::= { sleV2Dhcp4PacketStatsInfo 15 }

		
		-- 1.3.6.1.4.1.6296.102.6.2.5.1.1.16
		sleV2Dhcp4PacketStatsSentNak OBJECT-TYPE
			SYNTAX Unsigned32
			MAX-ACCESS read-only
			STATUS current
			DESCRIPTION
				"The number of sent DHCP Nak packets."
			::= { sleV2Dhcp4PacketStatsInfo 16 }

		
		-- 1.3.6.1.4.1.6296.102.6.2.5.1.1.17
		sleV2Dhcp4SummaryPoolCnt OBJECT-TYPE
			SYNTAX Unsigned32
			MAX-ACCESS read-only
			STATUS current
			DESCRIPTION
				"The number of Pools.to be set."
			::= { sleV2Dhcp4PacketStatsInfo 17 }

		
		-- 1.3.6.1.4.1.6296.102.6.2.5.1.1.18
		sleV2Dhcp4SummaryTotal OBJECT-TYPE
			SYNTAX Unsigned32
			MAX-ACCESS read-only
			STATUS current
			DESCRIPTION
				"The number of Total leases to be set."
			::= { sleV2Dhcp4PacketStatsInfo 18 }

		
		-- 1.3.6.1.4.1.6296.102.6.2.5.1.1.19
		sleV2Dhcp4SummaryAvailable OBJECT-TYPE
			SYNTAX Unsigned32
			MAX-ACCESS read-only
			STATUS current
			DESCRIPTION
				"The number of Available leases to be set."
			::= { sleV2Dhcp4PacketStatsInfo 19 }

		
		-- 1.3.6.1.4.1.6296.102.6.2.5.1.1.20
		sleV2Dhcp4SummaryAbandon OBJECT-TYPE
			SYNTAX Unsigned32
			MAX-ACCESS read-only
			STATUS current
			DESCRIPTION
				"The number of Abandon leases to be set."
			::= { sleV2Dhcp4PacketStatsInfo 20 }

		
		-- 1.3.6.1.4.1.6296.102.6.2.5.1.1.21
		sleV2Dhcp4SummaryBound OBJECT-TYPE
			SYNTAX Unsigned32
			MAX-ACCESS read-only
			STATUS current
			DESCRIPTION
				"The number of Bound leases to be set."
			::= { sleV2Dhcp4PacketStatsInfo 21 }

		
		-- 1.3.6.1.4.1.6296.102.6.2.5.1.1.22
		sleV2Dhcp4SummaryOffered OBJECT-TYPE
			SYNTAX Unsigned32
			MAX-ACCESS read-only
			STATUS current
			DESCRIPTION
				"The number of Offered leases to be set."
			::= { sleV2Dhcp4PacketStatsInfo 22 }

		
		-- 1.3.6.1.4.1.6296.102.6.2.5.1.1.23
		sleV2Dhcp4SummaryFixed OBJECT-TYPE
			SYNTAX Unsigned32
			MAX-ACCESS read-only
			STATUS current
			DESCRIPTION
				"The number of Fixed leases to be set."
			::= { sleV2Dhcp4PacketStatsInfo 23 }

		
		-- 1.3.6.1.4.1.6296.102.6.2.5.1.1.24
		sleV2Dhcp4SummaryAllocated OBJECT-TYPE
			SYNTAX Unsigned32
			MAX-ACCESS read-only
			STATUS current
			DESCRIPTION
				"Description."
			::= { sleV2Dhcp4PacketStatsInfo 24 }

		
		-- 1.3.6.1.4.1.6296.102.6.2.5.1.2
		sleV2Dhcp4PacketStatsControl OBJECT IDENTIFIER ::= { sleV2Dhcp4PacketStats 2 }

		
		-- 1.3.6.1.4.1.6296.102.6.2.5.1.2.1
		sleV2Dhcp4PacketStatsControlRequest OBJECT-TYPE
			SYNTAX INTEGER { clearDhcpPacketStats(1) }
			MAX-ACCESS read-write
			STATUS current
			DESCRIPTION
				"The request of a user command."
			::= { sleV2Dhcp4PacketStatsControl 1 }

		
		-- 1.3.6.1.4.1.6296.102.6.2.5.1.2.2
		sleV2Dhcp4PacketStatsControlStatus OBJECT-TYPE
			SYNTAX SleControlStatusType
			MAX-ACCESS read-only
			STATUS current
			DESCRIPTION
				"The status of a user command."
			::= { sleV2Dhcp4PacketStatsControl 2 }

		
		-- 1.3.6.1.4.1.6296.102.6.2.5.1.2.3
		sleV2Dhcp4PacketStatsControlTimer OBJECT-TYPE
			SYNTAX Gauge32
			MAX-ACCESS read-write
			STATUS current
			DESCRIPTION
				"The maximum wait Time for the manager for a long running user command."
			::= { sleV2Dhcp4PacketStatsControl 3 }

		
		-- 1.3.6.1.4.1.6296.102.6.2.5.1.2.4
		sleV2Dhcp4PacketStatsControlTimeStamp OBJECT-TYPE
			SYNTAX TimeTicks
			MAX-ACCESS read-only
			STATUS current
			DESCRIPTION
				"The Time stamp of the last command (end of command)."
			::= { sleV2Dhcp4PacketStatsControl 4 }

		
		-- 1.3.6.1.4.1.6296.102.6.2.5.1.2.5
		sleV2Dhcp4PacketStatsControlReqResult OBJECT-TYPE
			SYNTAX SleControlRequestResultType
			MAX-ACCESS read-only
			STATUS current
			DESCRIPTION
				"The result of the last user command."
			::= { sleV2Dhcp4PacketStatsControl 5 }

		
		-- 1.3.6.1.4.1.6296.102.6.2.5.1.3
		sleV2Dhcp4PacketStatsNotification OBJECT IDENTIFIER ::= { sleV2Dhcp4PacketStats 3 }

		
		-- 1.3.6.1.4.1.6296.102.6.2.5.1.3.1
		sleV2Dhcp4PacketStatsCleared NOTIFICATION-TYPE
			OBJECTS { sleV2Dhcp4PacketStatsControlRequest, sleV2Dhcp4PacketStatsControlTimeStamp, sleV2Dhcp4PacketStatsControlReqResult }
			STATUS current
			DESCRIPTION 
				"Description."
			::= { sleV2Dhcp4PacketStatsNotification 1 }

		
		-- 1.3.6.1.4.1.6296.102.6.2.5.2
		sleV2Dhcp4Leased OBJECT IDENTIFIER ::= { sleV2Dhcp4Stats 2 }

		
		-- 1.3.6.1.4.1.6296.102.6.2.5.2.1
		sleV2Dhcp4LeasedTable OBJECT-TYPE
			SYNTAX SEQUENCE OF SleV2Dhcp4LeasedEntry
			MAX-ACCESS not-accessible
			STATUS current
			DESCRIPTION
				"Description."
			::= { sleV2Dhcp4Leased 1 }

		
		-- 1.3.6.1.4.1.6296.102.6.2.5.2.1.1
		sleV2Dhcp4LeasedEntry OBJECT-TYPE
			SYNTAX SleV2Dhcp4LeasedEntry
			MAX-ACCESS not-accessible
			STATUS current
			DESCRIPTION
				"Description."
			INDEX { sleV2Dhcp4LeasedAddress }
			::= { sleV2Dhcp4LeasedTable 1 }

		
		SleV2Dhcp4LeasedEntry ::=
			SEQUENCE { 
				sleV2Dhcp4LeasedAddress
					IpAddress,
				sleV2Dhcp4LeasedPoolIndex
					INTEGER,
				sleV2Dhcp4LeasedStatus
					INTEGER,
				sleV2Dhcp4LeasedMac
					MacAddress,
				sleV2Dhcp4LeasedHostName
					OCTET STRING,
				sleV2Dhcp4LeasedClientId
					OCTET STRING,
				sleV2Dhcp4LeasedRemoteId
					OCTET STRING,
				sleV2Dhcp4LeasedCircuitId
					OCTET STRING,
				sleV2Dhcp4LeasedStartTime
					Unsigned32,
				sleV2Dhcp4LeasedFinishTime
					Unsigned32
			 }

		-- 1.3.6.1.4.1.6296.102.6.2.5.2.1.1.1
		sleV2Dhcp4LeasedAddress OBJECT-TYPE
			SYNTAX IpAddress
			MAX-ACCESS read-only
			STATUS current
			DESCRIPTION
				"."
			::= { sleV2Dhcp4LeasedEntry 1 }

		
		-- 1.3.6.1.4.1.6296.102.6.2.5.2.1.1.2
		sleV2Dhcp4LeasedPoolIndex OBJECT-TYPE
			SYNTAX INTEGER (1..255)
			MAX-ACCESS read-only
			STATUS current
			DESCRIPTION
				"."
			::= { sleV2Dhcp4LeasedEntry 2 }

		
		-- 1.3.6.1.4.1.6296.102.6.2.5.2.1.1.3
		sleV2Dhcp4LeasedStatus OBJECT-TYPE
			SYNTAX INTEGER
				{
				fixed(1),
				offered(2),
				bound(3),
				abandon(4),
				free(5)
				}
			MAX-ACCESS read-only
			STATUS current
			DESCRIPTION
				"."
			::= { sleV2Dhcp4LeasedEntry 3 }

		
		-- 1.3.6.1.4.1.6296.102.6.2.5.2.1.1.4
		sleV2Dhcp4LeasedMac OBJECT-TYPE
			SYNTAX MacAddress
			MAX-ACCESS read-only
			STATUS current
			DESCRIPTION
				"."
			::= { sleV2Dhcp4LeasedEntry 4 }

		
		-- 1.3.6.1.4.1.6296.102.6.2.5.2.1.1.5
		sleV2Dhcp4LeasedHostName OBJECT-TYPE
			SYNTAX OCTET STRING (SIZE (0 | 1..64))
			MAX-ACCESS read-only
			STATUS current
			DESCRIPTION
				"."
			::= { sleV2Dhcp4LeasedEntry 5 }

		
		-- 1.3.6.1.4.1.6296.102.6.2.5.2.1.1.6
		sleV2Dhcp4LeasedClientId OBJECT-TYPE
			SYNTAX OCTET STRING (SIZE (0 | 1..64))
			MAX-ACCESS read-only
			STATUS current
			DESCRIPTION
				"."
			::= { sleV2Dhcp4LeasedEntry 6 }

		
		-- 1.3.6.1.4.1.6296.102.6.2.5.2.1.1.7
		sleV2Dhcp4LeasedRemoteId OBJECT-TYPE
			SYNTAX OCTET STRING (SIZE (0 | 1..32))
			MAX-ACCESS read-only
			STATUS current
			DESCRIPTION
				"."
			::= { sleV2Dhcp4LeasedEntry 7 }

		
		-- 1.3.6.1.4.1.6296.102.6.2.5.2.1.1.8
		sleV2Dhcp4LeasedCircuitId OBJECT-TYPE
			SYNTAX OCTET STRING (SIZE (0 | 1..32))
			MAX-ACCESS read-only
			STATUS current
			DESCRIPTION
				"."
			::= { sleV2Dhcp4LeasedEntry 8 }

		
		-- 1.3.6.1.4.1.6296.102.6.2.5.2.1.1.9
		sleV2Dhcp4LeasedStartTime OBJECT-TYPE
			SYNTAX Unsigned32
			UNITS "second"
			MAX-ACCESS read-only
			STATUS current
			DESCRIPTION
				"시작시간: 단위는 1970.1.1일 0시 0분 0초부터 계산한 초"
			::= { sleV2Dhcp4LeasedEntry 9 }

		
		-- 1.3.6.1.4.1.6296.102.6.2.5.2.1.1.10
		sleV2Dhcp4LeasedFinishTime OBJECT-TYPE
			SYNTAX Unsigned32
			UNITS "second"
			MAX-ACCESS read-only
			STATUS current
			DESCRIPTION
				"Description."
			::= { sleV2Dhcp4LeasedEntry 10 }

		
		-- 1.3.6.1.4.1.6296.102.6.2.5.2.2
		sleV2Dhcp4LeasedControl OBJECT IDENTIFIER ::= { sleV2Dhcp4Leased 2 }

		
		-- 1.3.6.1.4.1.6296.102.6.2.5.2.2.1
		sleV2Dhcp4LeasedControlRequest OBJECT-TYPE
			SYNTAX INTEGER
				{
				clearDhcpLeasedAddress(1),
				clearDhcpLeaseNetwork(2),
				clearDhcpLeasePool(3),
				clearDhcpLeaseAll(4)
				}
			MAX-ACCESS read-write
			STATUS current
			DESCRIPTION
				"The request of a user command."
			::= { sleV2Dhcp4LeasedControl 1 }

		
		-- 1.3.6.1.4.1.6296.102.6.2.5.2.2.2
		sleV2Dhcp4LeasedControlStatus OBJECT-TYPE
			SYNTAX SleControlStatusType
			MAX-ACCESS read-only
			STATUS current
			DESCRIPTION
				"The status of a user command."
			::= { sleV2Dhcp4LeasedControl 2 }

		
		-- 1.3.6.1.4.1.6296.102.6.2.5.2.2.3
		sleV2Dhcp4LeasedControlTimer OBJECT-TYPE
			SYNTAX Gauge32
			MAX-ACCESS read-write
			STATUS current
			DESCRIPTION
				"The maximum wait Time for the manager for a long running user command."
			::= { sleV2Dhcp4LeasedControl 3 }

		
		-- 1.3.6.1.4.1.6296.102.6.2.5.2.2.4
		sleV2Dhcp4LeasedControlTimeStamp OBJECT-TYPE
			SYNTAX TimeTicks
			MAX-ACCESS read-only
			STATUS current
			DESCRIPTION
				"The Time stamp of the last command (end of command)."
			::= { sleV2Dhcp4LeasedControl 4 }

		
		-- 1.3.6.1.4.1.6296.102.6.2.5.2.2.5
		sleV2Dhcp4LeasedControlReqResult OBJECT-TYPE
			SYNTAX SleControlRequestResultType
			MAX-ACCESS read-only
			STATUS current
			DESCRIPTION
				"The result of the last user command."
			::= { sleV2Dhcp4LeasedControl 5 }

		
		-- 1.3.6.1.4.1.6296.102.6.2.5.2.2.6
		sleV2Dhcp4LeasedControlAddress OBJECT-TYPE
			SYNTAX IpAddress
			MAX-ACCESS read-write
			STATUS current
			DESCRIPTION
				"."
			::= { sleV2Dhcp4LeasedControl 6 }

		
		-- 1.3.6.1.4.1.6296.102.6.2.5.2.2.7
		sleV2Dhcp4LeasedControlMask OBJECT-TYPE
			SYNTAX INTEGER (1..32)
			MAX-ACCESS read-only
			STATUS current
			DESCRIPTION
				"The result of the last user command."
			::= { sleV2Dhcp4LeasedControl 7 }

		
		-- 1.3.6.1.4.1.6296.102.6.2.5.2.2.8
		sleV2Dhcp4LeasedControlPoolIndex OBJECT-TYPE
			SYNTAX INTEGER (1..255)
			MAX-ACCESS read-write
			STATUS current
			DESCRIPTION
				"."
			::= { sleV2Dhcp4LeasedControl 8 }

		
		-- 1.3.6.1.4.1.6296.102.6.2.5.2.3
		sleV2Dhcp4LeasedNotification OBJECT IDENTIFIER ::= { sleV2Dhcp4Leased 3 }

		
		-- 1.3.6.1.4.1.6296.102.6.2.5.2.3.1
		sleV2Dhcp4LeasedAddressCleared NOTIFICATION-TYPE
			OBJECTS { sleV2Dhcp4LeasedControlRequest, sleV2Dhcp4LeasedControlTimeStamp, sleV2Dhcp4LeasedControlReqResult, sleV2Dhcp4LeasedControlAddress }
			STATUS current
			DESCRIPTION 
				"Description."
			::= { sleV2Dhcp4LeasedNotification 1 }

		
		-- 1.3.6.1.4.1.6296.102.6.2.5.2.3.2
		sleV2Dhcp4LeasedNetworkCleared NOTIFICATION-TYPE
			OBJECTS { sleV2Dhcp4LeasedControlRequest, sleV2Dhcp4LeasedControlTimeStamp, sleV2Dhcp4LeasedControlReqResult, sleV2Dhcp4LeasedControlAddress, sleV2Dhcp4LeasedControlMask
				 }
			STATUS current
			DESCRIPTION 
				"Description."
			::= { sleV2Dhcp4LeasedNotification 2 }

		
		-- 1.3.6.1.4.1.6296.102.6.2.5.2.3.3
		sleV2Dhcp4LeasedPoolCleared NOTIFICATION-TYPE
			OBJECTS { sleV2Dhcp4LeasedControlRequest, sleV2Dhcp4LeasedControlTimeStamp, sleV2Dhcp4LeasedControlReqResult, sleV2Dhcp4LeasedControlPoolIndex }
			STATUS current
			DESCRIPTION 
				"Description."
			::= { sleV2Dhcp4LeasedNotification 3 }

		
		-- 1.3.6.1.4.1.6296.102.6.2.5.2.3.4
		sleV2Dhcp4LeasedAllCleared NOTIFICATION-TYPE
			OBJECTS { sleV2Dhcp4LeasedControlRequest, sleV2Dhcp4LeasedControlTimeStamp, sleV2Dhcp4LeasedControlReqResult }
			STATUS current
			DESCRIPTION 
				"Description."
			::= { sleV2Dhcp4LeasedNotification 4 }

		
		-- 1.3.6.1.4.1.6296.102.6.2.5.3
		sleV2Dhcp4PacketStatsPort OBJECT IDENTIFIER ::= { sleV2Dhcp4Stats 3 }

		
		-- 1.3.6.1.4.1.6296.102.6.2.5.3.1
		sleV2Dhcp4PacketStatsPortTable OBJECT-TYPE
			SYNTAX SEQUENCE OF SleV2Dhcp4PacketStatsPortEntry
			MAX-ACCESS not-accessible
			STATUS current
			DESCRIPTION
				"Description."
			::= { sleV2Dhcp4PacketStatsPort 1 }

		
		-- 1.3.6.1.4.1.6296.102.6.2.5.3.1.1
		sleV2Dhcp4PacketStatsPortEntry OBJECT-TYPE
			SYNTAX SleV2Dhcp4PacketStatsPortEntry
			MAX-ACCESS not-accessible
			STATUS current
			DESCRIPTION
				"Description."
			INDEX { sleV2Dhcp4PacketStatsPortIndex }
			::= { sleV2Dhcp4PacketStatsPortTable 1 }

		
		SleV2Dhcp4PacketStatsPortEntry ::=
			SEQUENCE { 
				sleV2Dhcp4PacketStatsPortIndex
					InterfaceIndex,
				sleV2Dhcp4PacketStatsPortReceived
					Counter32,
				sleV2Dhcp4PacketStatsPortSent
					Counter32,
				sleV2Dhcp4PacketStatsPortReceivedError
					Counter32,
				sleV2Dhcp4PacketStatsPortSentError
					Counter32,
				sleV2Dhcp4PacketStatsPortReceivedDiscover
					Counter32,
				sleV2Dhcp4PacketStatsPortReceivedRequest
					Counter32,
				sleV2Dhcp4PacketStatsPortReceivedRelease
					Counter32,
				sleV2Dhcp4PacketStatsPortReceivedInform
					Counter32,
				sleV2Dhcp4PacketStatsPortReceivedDecline
					Counter32,
				sleV2Dhcp4PacketStatsPortSentOffer
					Counter32,
				sleV2Dhcp4PacketStatsPortSentAck
					Counter32,
				sleV2Dhcp4PacketStatsPortSentNak
					Counter32
			 }

		-- 1.3.6.1.4.1.6296.102.6.2.5.3.1.1.1
		sleV2Dhcp4PacketStatsPortIndex OBJECT-TYPE
			SYNTAX InterfaceIndex
			MAX-ACCESS read-only
			STATUS current
			DESCRIPTION
				"Description."
			::= { sleV2Dhcp4PacketStatsPortEntry 1 }

		
		-- 1.3.6.1.4.1.6296.102.6.2.5.3.1.1.2
		sleV2Dhcp4PacketStatsPortReceived OBJECT-TYPE
			SYNTAX Counter32
			MAX-ACCESS read-only
			STATUS current
			DESCRIPTION
				"Description."
			::= { sleV2Dhcp4PacketStatsPortEntry 2 }

		
		-- 1.3.6.1.4.1.6296.102.6.2.5.3.1.1.3
		sleV2Dhcp4PacketStatsPortSent OBJECT-TYPE
			SYNTAX Counter32
			MAX-ACCESS read-only
			STATUS current
			DESCRIPTION
				"Description."
			::= { sleV2Dhcp4PacketStatsPortEntry 3 }

		
		-- 1.3.6.1.4.1.6296.102.6.2.5.3.1.1.4
		sleV2Dhcp4PacketStatsPortReceivedError OBJECT-TYPE
			SYNTAX Counter32
			MAX-ACCESS read-only
			STATUS current
			DESCRIPTION
				"Description."
			::= { sleV2Dhcp4PacketStatsPortEntry 4 }

		
		-- 1.3.6.1.4.1.6296.102.6.2.5.3.1.1.5
		sleV2Dhcp4PacketStatsPortSentError OBJECT-TYPE
			SYNTAX Counter32
			MAX-ACCESS read-only
			STATUS current
			DESCRIPTION
				"Description."
			::= { sleV2Dhcp4PacketStatsPortEntry 5 }

		
		-- 1.3.6.1.4.1.6296.102.6.2.5.3.1.1.6
		sleV2Dhcp4PacketStatsPortReceivedDiscover OBJECT-TYPE
			SYNTAX Counter32
			MAX-ACCESS read-only
			STATUS current
			DESCRIPTION
				"Description."
			::= { sleV2Dhcp4PacketStatsPortEntry 6 }

		
		-- 1.3.6.1.4.1.6296.102.6.2.5.3.1.1.7
		sleV2Dhcp4PacketStatsPortReceivedRequest OBJECT-TYPE
			SYNTAX Counter32
			MAX-ACCESS read-only
			STATUS current
			DESCRIPTION
				"Description."
			::= { sleV2Dhcp4PacketStatsPortEntry 7 }

		
		-- 1.3.6.1.4.1.6296.102.6.2.5.3.1.1.8
		sleV2Dhcp4PacketStatsPortReceivedRelease OBJECT-TYPE
			SYNTAX Counter32
			MAX-ACCESS read-only
			STATUS current
			DESCRIPTION
				"Description."
			::= { sleV2Dhcp4PacketStatsPortEntry 8 }

		
		-- 1.3.6.1.4.1.6296.102.6.2.5.3.1.1.9
		sleV2Dhcp4PacketStatsPortReceivedInform OBJECT-TYPE
			SYNTAX Counter32
			MAX-ACCESS read-only
			STATUS current
			DESCRIPTION
				"Description."
			::= { sleV2Dhcp4PacketStatsPortEntry 9 }

		
		-- 1.3.6.1.4.1.6296.102.6.2.5.3.1.1.10
		sleV2Dhcp4PacketStatsPortReceivedDecline OBJECT-TYPE
			SYNTAX Counter32
			MAX-ACCESS read-only
			STATUS current
			DESCRIPTION
				"Description."
			::= { sleV2Dhcp4PacketStatsPortEntry 10 }

		
		-- 1.3.6.1.4.1.6296.102.6.2.5.3.1.1.11
		sleV2Dhcp4PacketStatsPortSentOffer OBJECT-TYPE
			SYNTAX Counter32
			MAX-ACCESS read-only
			STATUS current
			DESCRIPTION
				"Description."
			::= { sleV2Dhcp4PacketStatsPortEntry 11 }

		
		-- 1.3.6.1.4.1.6296.102.6.2.5.3.1.1.12
		sleV2Dhcp4PacketStatsPortSentAck OBJECT-TYPE
			SYNTAX Counter32
			MAX-ACCESS read-only
			STATUS current
			DESCRIPTION
				"Description."
			::= { sleV2Dhcp4PacketStatsPortEntry 12 }

		
		-- 1.3.6.1.4.1.6296.102.6.2.5.3.1.1.13
		sleV2Dhcp4PacketStatsPortSentNak OBJECT-TYPE
			SYNTAX Counter32
			MAX-ACCESS read-only
			STATUS current
			DESCRIPTION
				"Description."
			::= { sleV2Dhcp4PacketStatsPortEntry 13 }

		
		-- 1.3.6.1.4.1.6296.102.6.2.5.4
		sleV2Dhcp4State OBJECT IDENTIFIER ::= { sleV2Dhcp4Stats 4 }

		
		-- 1.3.6.1.4.1.6296.102.6.2.5.4.1
		sleV2Dhcp4StateTable OBJECT-TYPE
			SYNTAX SEQUENCE OF SleV2Dhcp4StateEntry
			MAX-ACCESS not-accessible
			STATUS current
			DESCRIPTION
				"Description."
			::= { sleV2Dhcp4State 1 }

		
		-- 1.3.6.1.4.1.6296.102.6.2.5.4.1.1
		sleV2Dhcp4StateEntry OBJECT-TYPE
			SYNTAX SleV2Dhcp4StateEntry
			MAX-ACCESS not-accessible
			STATUS current
			DESCRIPTION
				"Description."
			INDEX { sleV2Dhcp4StateIndex }
			::= { sleV2Dhcp4StateTable 1 }

		
		SleV2Dhcp4StateEntry ::=
			SEQUENCE { 
				sleV2Dhcp4StateIndex
					INTEGER,
				sleV2Dhcp4StateTotal
					Unsigned32,
				sleV2Dhcp4StateFixed
					Unsigned32,
				sleV2Dhcp4StateDynamic
					Unsigned32,
				sleV2Dhcp4StatePEntry
					Unsigned32
			 }

		-- 1.3.6.1.4.1.6296.102.6.2.5.4.1.1.1
		sleV2Dhcp4StateIndex OBJECT-TYPE
			SYNTAX INTEGER
				{
				bound(1),
				offer(2),
				abandon(3),
				free(4)
				}
			MAX-ACCESS read-only
			STATUS current
			DESCRIPTION
				"Description."
			::= { sleV2Dhcp4StateEntry 1 }

		
		-- 1.3.6.1.4.1.6296.102.6.2.5.4.1.1.2
		sleV2Dhcp4StateTotal OBJECT-TYPE
			SYNTAX Unsigned32
			MAX-ACCESS read-only
			STATUS current
			DESCRIPTION
				"Description."
			::= { sleV2Dhcp4StateEntry 2 }

		
		-- 1.3.6.1.4.1.6296.102.6.2.5.4.1.1.3
		sleV2Dhcp4StateFixed OBJECT-TYPE
			SYNTAX Unsigned32
			MAX-ACCESS read-only
			STATUS current
			DESCRIPTION
				"Description."
			::= { sleV2Dhcp4StateEntry 3 }

		
		-- 1.3.6.1.4.1.6296.102.6.2.5.4.1.1.4
		sleV2Dhcp4StateDynamic OBJECT-TYPE
			SYNTAX Unsigned32
			MAX-ACCESS read-only
			STATUS current
			DESCRIPTION
				"Description."
			::= { sleV2Dhcp4StateEntry 4 }

		
		-- 1.3.6.1.4.1.6296.102.6.2.5.4.1.1.5
		sleV2Dhcp4StatePEntry OBJECT-TYPE
			SYNTAX Unsigned32
			MAX-ACCESS read-only
			STATUS current
			DESCRIPTION
				"Description."
			::= { sleV2Dhcp4StateEntry 5 }

		
		-- 1.3.6.1.4.1.6296.102.6.2.5.4.2
		sleV2Dhcp4StatePoolTable OBJECT-TYPE
			SYNTAX SEQUENCE OF SleV2Dhcp4StatePoolEntry
			MAX-ACCESS not-accessible
			STATUS current
			DESCRIPTION
				"Description."
			::= { sleV2Dhcp4State 2 }

		
		-- 1.3.6.1.4.1.6296.102.6.2.5.4.2.1
		sleV2Dhcp4StatePoolEntry OBJECT-TYPE
			SYNTAX SleV2Dhcp4StatePoolEntry
			MAX-ACCESS not-accessible
			STATUS current
			DESCRIPTION
				"Description."
			INDEX { sleV2Dhcp4PoolIndex, sleV2Dhcp4StateIndex }
			::= { sleV2Dhcp4StatePoolTable 1 }

		
		SleV2Dhcp4StatePoolEntry ::=
			SEQUENCE { 
				sleV2Dhcp4StatePoolTotal
					Unsigned32,
				sleV2Dhcp4StatePoolFixed
					Unsigned32,
				sleV2Dhcp4StatePoolDynamic
					Unsigned32,
				sleV2Dhcp4StatePoolPEntry
					Unsigned32
			 }

		-- 1.3.6.1.4.1.6296.102.6.2.5.4.2.1.1
		sleV2Dhcp4StatePoolTotal OBJECT-TYPE
			SYNTAX Unsigned32
			MAX-ACCESS read-only
			STATUS current
			DESCRIPTION
				"Description."
			::= { sleV2Dhcp4StatePoolEntry 1 }

		
		-- 1.3.6.1.4.1.6296.102.6.2.5.4.2.1.2
		sleV2Dhcp4StatePoolFixed OBJECT-TYPE
			SYNTAX Unsigned32
			MAX-ACCESS read-only
			STATUS current
			DESCRIPTION
				"Description."
			::= { sleV2Dhcp4StatePoolEntry 2 }

		
		-- 1.3.6.1.4.1.6296.102.6.2.5.4.2.1.3
		sleV2Dhcp4StatePoolDynamic OBJECT-TYPE
			SYNTAX Unsigned32
			MAX-ACCESS read-only
			STATUS current
			DESCRIPTION
				"Description."
			::= { sleV2Dhcp4StatePoolEntry 3 }

		
		-- 1.3.6.1.4.1.6296.102.6.2.5.4.2.1.4
		sleV2Dhcp4StatePoolPEntry OBJECT-TYPE
			SYNTAX Unsigned32
			MAX-ACCESS read-only
			STATUS current
			DESCRIPTION
				"Description."
			::= { sleV2Dhcp4StatePoolEntry 4 }

		
		-- 1.3.6.1.4.1.6296.102.6.2.5.4.3
		sleV2Dhcp4StateBindTable OBJECT-TYPE
			SYNTAX SEQUENCE OF SleV2Dhcp4StateBindEntry
			MAX-ACCESS not-accessible
			STATUS current
			DESCRIPTION
				"Description."
			::= { sleV2Dhcp4State 3 }

		
		-- 1.3.6.1.4.1.6296.102.6.2.5.4.3.1
		sleV2Dhcp4StateBindEntry OBJECT-TYPE
			SYNTAX SleV2Dhcp4StateBindEntry
			MAX-ACCESS not-accessible
			STATUS current
			DESCRIPTION
				"Description."
			INDEX { sleV2Dhcp4StateBindIpAddress }
			::= { sleV2Dhcp4StateBindTable 1 }

		
		SleV2Dhcp4StateBindEntry ::=
			SEQUENCE { 
				sleV2Dhcp4StateBindIpAddress
					IpAddress,
				sleV2Dhcp4StateBindPoolIndex
					Integer32,
				sleV2Dhcp4StateBindMac
					MacAddress,
				sleV2Dhcp4StateBindState
					INTEGER,
				sleV2Dhcp4StateBindType
					INTEGER,
				sleV2Dhcp4StateBindExpiration
					OCTET STRING,
				sleV2Dhcp4StateBindPort
					Integer32
			 }

		-- 1.3.6.1.4.1.6296.102.6.2.5.4.3.1.1
		sleV2Dhcp4StateBindIpAddress OBJECT-TYPE
			SYNTAX IpAddress
			MAX-ACCESS read-only
			STATUS current
			DESCRIPTION
				"Description."
			::= { sleV2Dhcp4StateBindEntry 1 }

		
		-- 1.3.6.1.4.1.6296.102.6.2.5.4.3.1.2
		sleV2Dhcp4StateBindPoolIndex OBJECT-TYPE
			SYNTAX Integer32
			MAX-ACCESS read-write
			STATUS current
			DESCRIPTION
				"Description."
			::= { sleV2Dhcp4StateBindEntry 2 }

		
		-- 1.3.6.1.4.1.6296.102.6.2.5.4.3.1.3
		sleV2Dhcp4StateBindMac OBJECT-TYPE
			SYNTAX MacAddress
			MAX-ACCESS read-only
			STATUS current
			DESCRIPTION
				"Description."
			::= { sleV2Dhcp4StateBindEntry 3 }

		
		-- 1.3.6.1.4.1.6296.102.6.2.5.4.3.1.4
		sleV2Dhcp4StateBindState OBJECT-TYPE
			SYNTAX INTEGER
				{
				bound(1),
				offer(2),
				abandon(3),
				free(4)
				}
			MAX-ACCESS read-only
			STATUS current
			DESCRIPTION
				"Description."
			::= { sleV2Dhcp4StateBindEntry 4 }

		
		-- 1.3.6.1.4.1.6296.102.6.2.5.4.3.1.5
		sleV2Dhcp4StateBindType OBJECT-TYPE
			SYNTAX INTEGER
				{
				fixed(1),
				dynamic(2),
				portentry(3)
				}
			MAX-ACCESS read-only
			STATUS current
			DESCRIPTION
				"Description."
			::= { sleV2Dhcp4StateBindEntry 5 }

		
		-- 1.3.6.1.4.1.6296.102.6.2.5.4.3.1.6
		sleV2Dhcp4StateBindExpiration OBJECT-TYPE
			SYNTAX OCTET STRING
			MAX-ACCESS read-only
			STATUS current
			DESCRIPTION
				"Description."
			::= { sleV2Dhcp4StateBindEntry 6 }

		
		-- 1.3.6.1.4.1.6296.102.6.2.5.4.3.1.7
		sleV2Dhcp4StateBindPort OBJECT-TYPE
			SYNTAX Integer32
			MAX-ACCESS read-only
			STATUS current
			DESCRIPTION
				"Description."
			::= { sleV2Dhcp4StateBindEntry 7 }

		
		-- 1.3.6.1.4.1.6296.102.6.2.6
		sleV2Dhcp4Snooping OBJECT IDENTIFIER ::= { sleV2Dhcp4 6 }

		
		-- 1.3.6.1.4.1.6296.102.6.2.6.1
		sleV2Ds4Base OBJECT IDENTIFIER ::= { sleV2Dhcp4Snooping 1 }

		
		-- 1.3.6.1.4.1.6296.102.6.2.6.1.1
		sleV2Ds4Info OBJECT IDENTIFIER ::= { sleV2Ds4Base 1 }

		
		-- 1.3.6.1.4.1.6296.102.6.2.6.1.1.1
		sleV2Ds4Activity OBJECT-TYPE
			SYNTAX INTEGER
				{
				inactive(0),
				active(1)
				}
			MAX-ACCESS read-only
			STATUS current
			DESCRIPTION
				"This object indicates whether the DHCP Snooping feature is
				enabled at the device level."
			::= { sleV2Ds4Info 1 }

		
		-- 1.3.6.1.4.1.6296.102.6.2.6.1.1.2
		sleV2Ds4VerifyMacState OBJECT-TYPE
			SYNTAX INTEGER
				{
				disable(0),
				enable(1)
				}
			MAX-ACCESS read-only
			STATUS current
			DESCRIPTION
				"This object indicates whether the DHCP Snooping verify mac address of the untrusted port
				is enabled at the device level."
			::= { sleV2Ds4Info 2 }

		
		-- 1.3.6.1.4.1.6296.102.6.2.6.1.1.3
		sleV2Ds4DatabaseURL OBJECT-TYPE
			SYNTAX IpAddress
			MAX-ACCESS read-only
			STATUS current
			DESCRIPTION
				"This object indicates the address of server that snooping database 
				will be stored by TFTP."
			::= { sleV2Ds4Info 3 }

		
		-- 1.3.6.1.4.1.6296.102.6.2.6.1.1.4
		sleV2Ds4DatabaseInterval OBJECT-TYPE
			SYNTAX INTEGER (0 | 1..2147483637)
			MAX-ACCESS read-only
			STATUS current
			DESCRIPTION
				"This object indicates the interval time that snooping database 
				will be stored by TFTP."
			::= { sleV2Ds4Info 4 }

		
		-- 1.3.6.1.4.1.6296.102.6.2.6.1.1.5
		sleV2Ds4ArpInspectionTime OBJECT-TYPE
			SYNTAX Integer32 (0..2147483637)
			UNITS "sec"
			MAX-ACCESS read-only
			STATUS current
			DESCRIPTION
				"Description."
			DEFVAL { 1800 }
			::= { sleV2Ds4Info 5 }

		
		-- 1.3.6.1.4.1.6296.102.6.2.6.1.1.6
		sleV2Ds4LimitRateDiscover OBJECT-TYPE
			SYNTAX Integer32 (0 | 1..32767)
			MAX-ACCESS read-only
			STATUS current
			DESCRIPTION
				"The DHCP snooping limit rate discover."
			::= { sleV2Ds4Info 6 }

		
		-- 1.3.6.1.4.1.6296.102.6.2.6.1.1.7
		sleV2Ds4LimitRateRequest OBJECT-TYPE
			SYNTAX Integer32 (0 | 1..32767)
			MAX-ACCESS read-only
			STATUS current
			DESCRIPTION
				"The DHCP snooping limit rate request."
			::= { sleV2Ds4Info 7 }

		
		-- 1.3.6.1.4.1.6296.102.6.2.6.1.1.8
		sleV2Ds4InformationOption OBJECT-TYPE
			SYNTAX INTEGER
				{
				disable(0),
				enable(1)
				}
			MAX-ACCESS read-only
			STATUS current
			DESCRIPTION
				"The DCHP snooping information option."
			::= { sleV2Ds4Info 8 }

		
		-- 1.3.6.1.4.1.6296.102.6.2.6.1.2
		sleV2Ds4Control OBJECT IDENTIFIER ::= { sleV2Ds4Base 2 }

		
		-- 1.3.6.1.4.1.6296.102.6.2.6.1.2.1
		sleV2Ds4ControlRequest OBJECT-TYPE
			SYNTAX INTEGER
				{
				setDsActivity(1),
				setDsVerifyMacState(2),
				setDsDatabaseProfile(3),
				renewDsDatabase(4),
				setDsArpInspectionTime(5),
				setDsLimitRateDiscover(6),
				setDsLimitRateRequest(7),
				setDsInformationOption(8)
				}
			MAX-ACCESS read-write
			STATUS current
			DESCRIPTION
				"The request of a user command."
			::= { sleV2Ds4Control 1 }

		
		-- 1.3.6.1.4.1.6296.102.6.2.6.1.2.2
		sleV2Ds4ControlStatus OBJECT-TYPE
			SYNTAX SleControlStatusType
			MAX-ACCESS read-only
			STATUS current
			DESCRIPTION
				"The status of a user command."
			::= { sleV2Ds4Control 2 }

		
		-- 1.3.6.1.4.1.6296.102.6.2.6.1.2.3
		sleV2Ds4ControlTimer OBJECT-TYPE
			SYNTAX Gauge32
			MAX-ACCESS read-write
			STATUS current
			DESCRIPTION
				"The maximum wait time for the manager for a long running user command."
			::= { sleV2Ds4Control 3 }

		
		-- 1.3.6.1.4.1.6296.102.6.2.6.1.2.4
		sleV2Ds4ControlTimeStamp OBJECT-TYPE
			SYNTAX TimeTicks
			MAX-ACCESS read-only
			STATUS current
			DESCRIPTION
				"The time stamp of the last command (end of command)."
			::= { sleV2Ds4Control 4 }

		
		-- 1.3.6.1.4.1.6296.102.6.2.6.1.2.5
		sleV2Ds4ControlReqResult OBJECT-TYPE
			SYNTAX SleControlRequestResultType
			MAX-ACCESS read-only
			STATUS current
			DESCRIPTION
				"The result of the last user command."
			::= { sleV2Ds4Control 5 }

		
		-- 1.3.6.1.4.1.6296.102.6.2.6.1.2.6
		sleV2Ds4ControlActivity OBJECT-TYPE
			SYNTAX INTEGER
				{
				inactive(0),
				active(1)
				}
			MAX-ACCESS read-write
			STATUS current
			DESCRIPTION
				"Description."
			::= { sleV2Ds4Control 6 }

		
		-- 1.3.6.1.4.1.6296.102.6.2.6.1.2.7
		sleV2Ds4ControlVerifyMacState OBJECT-TYPE
			SYNTAX INTEGER
				{
				disable(0),
				enable(1)
				}
			MAX-ACCESS read-write
			STATUS current
			DESCRIPTION
				"Description."
			::= { sleV2Ds4Control 7 }

		
		-- 1.3.6.1.4.1.6296.102.6.2.6.1.2.8
		sleV2Ds4ControlDatabaseURL OBJECT-TYPE
			SYNTAX IpAddress
			MAX-ACCESS read-write
			STATUS current
			DESCRIPTION
				"Description."
			::= { sleV2Ds4Control 8 }

		
		-- 1.3.6.1.4.1.6296.102.6.2.6.1.2.9
		sleV2Ds4ControlDatabaseInterval OBJECT-TYPE
			SYNTAX INTEGER (0 | 1..2147483637)
			MAX-ACCESS read-write
			STATUS current
			DESCRIPTION
				"Description."
			::= { sleV2Ds4Control 9 }

		
		-- 1.3.6.1.4.1.6296.102.6.2.6.1.2.10
		sleV2Ds4ControlArpInspectionTime OBJECT-TYPE
			SYNTAX Integer32 (0..2147483637)
			UNITS "sec"
			MAX-ACCESS read-write
			STATUS current
			DESCRIPTION
				"Description."
			DEFVAL { 1800 }
			::= { sleV2Ds4Control 10 }

		
		-- 1.3.6.1.4.1.6296.102.6.2.6.1.2.11
		sleV2Ds4ControlLimitRateDiscover OBJECT-TYPE
			SYNTAX Integer32 (0 | 1..32767)
			MAX-ACCESS read-write
			STATUS current
			DESCRIPTION
				"The DHCP snooping limit rate discover. (0: delete)"
			::= { sleV2Ds4Control 11 }

		
		-- 1.3.6.1.4.1.6296.102.6.2.6.1.2.12
		sleV2Ds4ControlLimitRateRequest OBJECT-TYPE
			SYNTAX Integer32 (0 | 1..32767)
			MAX-ACCESS read-write
			STATUS current
			DESCRIPTION
				"The DHCP snooping limit rate request.  (0: delete)"
			::= { sleV2Ds4Control 12 }

		
		-- 1.3.6.1.4.1.6296.102.6.2.6.1.2.13
		sleV2Ds4ControlInformationOption OBJECT-TYPE
			SYNTAX INTEGER
				{
				disable(0),
				enable(1)
				}
			MAX-ACCESS read-write
			STATUS current
			DESCRIPTION
				"The DCHP snooping information option."
			::= { sleV2Ds4Control 13 }

		
		-- 1.3.6.1.4.1.6296.102.6.2.6.1.3
		sleV2Ds4Notification OBJECT IDENTIFIER ::= { sleV2Ds4Base 3 }

		
		-- 1.3.6.1.4.1.6296.102.6.2.6.1.3.1
		sleV2Ds4ActivityChanged NOTIFICATION-TYPE
			OBJECTS { sleV2Ds4ControlRequest, sleV2Ds4ControlTimeStamp, sleV2Ds4ControlReqResult, sleV2Ds4Activity }
			STATUS current
			DESCRIPTION 
				"Description."
			::= { sleV2Ds4Notification 1 }

		
		-- 1.3.6.1.4.1.6296.102.6.2.6.1.3.2
		sleV2Ds4VerifyMacStateChanged NOTIFICATION-TYPE
			OBJECTS { sleV2Ds4ControlRequest, sleV2Ds4ControlTimeStamp, sleV2Ds4ControlReqResult, sleV2Ds4VerifyMacState }
			STATUS current
			DESCRIPTION 
				"Description."
			::= { sleV2Ds4Notification 2 }

		
		-- 1.3.6.1.4.1.6296.102.6.2.6.1.3.3
		sleV2Ds4DatabaseProfileChanged NOTIFICATION-TYPE
			OBJECTS { sleV2Ds4ControlRequest, sleV2Ds4ControlTimeStamp, sleV2Ds4ControlReqResult, sleV2Ds4DatabaseURL, sleV2Ds4DatabaseInterval
				 }
			STATUS current
			DESCRIPTION 
				"Description."
			::= { sleV2Ds4Notification 3 }

		
		-- 1.3.6.1.4.1.6296.102.6.2.6.1.3.4
		sleV2Ds4DatabaseRenewed NOTIFICATION-TYPE
			OBJECTS { sleV2Ds4ControlRequest, sleV2Ds4ControlTimeStamp, sleV2Ds4ControlReqResult, sleV2Ds4ControlDatabaseURL }
			STATUS current
			DESCRIPTION 
				"Description."
			::= { sleV2Ds4Notification 4 }

		
		-- 1.3.6.1.4.1.6296.102.6.2.6.1.3.5
		sleV2Ds4ArpInspectionTimeChanged NOTIFICATION-TYPE
			OBJECTS { sleV2Ds4ControlRequest, sleV2Ds4ControlTimeStamp, sleV2Ds4ControlReqResult, sleV2Ds4ArpInspectionTime }
			STATUS current
			DESCRIPTION 
				"Description."
			::= { sleV2Ds4Notification 5 }

		
		-- 1.3.6.1.4.1.6296.102.6.2.6.1.3.6
		sleV2Ds4LimitRateDiscoverChanged NOTIFICATION-TYPE
			OBJECTS { sleV2Ds4ControlRequest, sleV2Ds4ControlTimeStamp, sleV2Ds4ControlReqResult, sleV2Ds4ControlLimitRateDiscover }
			STATUS current
			DESCRIPTION 
				"setDsLimitRateDiscover"
			::= { sleV2Ds4Notification 6 }

		
		-- 1.3.6.1.4.1.6296.102.6.2.6.1.3.7
		sleV2Ds4LimitRateRequestChanged NOTIFICATION-TYPE
			OBJECTS { sleV2Ds4ControlRequest, sleV2Ds4ControlTimeStamp, sleV2Ds4ControlReqResult, sleV2Ds4ControlLimitRateRequest }
			STATUS current
			DESCRIPTION 
				"setDsLimitRateRequest"
			::= { sleV2Ds4Notification 7 }

		
		-- 1.3.6.1.4.1.6296.102.6.2.6.1.3.8
		sleV2Ds4InformationOptionChanged NOTIFICATION-TYPE
			OBJECTS { sleV2Ds4ControlRequest, sleV2Ds4ControlTimeStamp, sleV2Ds4ControlReqResult, sleV2Ds4ControlInformationOption }
			STATUS current
			DESCRIPTION 
				"setDsInformationOption"
			::= { sleV2Ds4Notification 8 }

		
		-- 1.3.6.1.4.1.6296.102.6.2.6.2
		sleV2Ds4Vlan OBJECT IDENTIFIER ::= { sleV2Dhcp4Snooping 2 }

		
		-- 1.3.6.1.4.1.6296.102.6.2.6.2.1
		sleV2Ds4VlanTable OBJECT-TYPE
			SYNTAX SEQUENCE OF SleV2Ds4VlanEntry
			MAX-ACCESS not-accessible
			STATUS current
			DESCRIPTION
				"A table provides the mechanism to control DHCP Snooping 
				per VLAN. When a VLAN is created in a device supporting this
				table, a corresponding entry of this table will be added."
			::= { sleV2Ds4Vlan 1 }

		
		-- 1.3.6.1.4.1.6296.102.6.2.6.2.1.1
		sleV2Ds4VlanEntry OBJECT-TYPE
			SYNTAX SleV2Ds4VlanEntry
			MAX-ACCESS not-accessible
			STATUS current
			DESCRIPTION
				"A row instance contains the configuration to enable
				or disable DHCP Snooping at each existing VLAN."
			INDEX { sleV2Ds4VlanIndex }
			::= { sleV2Ds4VlanTable 1 }

		
		SleV2Ds4VlanEntry ::=
			SEQUENCE { 
				sleV2Ds4VlanIndex
					INTEGER,
				sleV2Ds4VlanState
					INTEGER
			 }

		-- 1.3.6.1.4.1.6296.102.6.2.6.2.1.1.1
		sleV2Ds4VlanIndex OBJECT-TYPE
			SYNTAX INTEGER (1..4094)
			MAX-ACCESS read-only
			STATUS current
			DESCRIPTION
				"This object indicates the VLAN number on which DHCP Snooping 
				feature is configured."
			::= { sleV2Ds4VlanEntry 1 }

		
		-- 1.3.6.1.4.1.6296.102.6.2.6.2.1.1.2
		sleV2Ds4VlanState OBJECT-TYPE
			SYNTAX INTEGER
				{
				disable(0),
				enable(1)
				}
			MAX-ACCESS read-only
			STATUS current
			DESCRIPTION
				"This object indicates whether DHCP Snooping is enabled in
				this VLAN. 
				
				If this object is set to 'true', DHCP Snooping is enabled. 
				
				If this object is set to 'false', DHCP Snooping is disabled."
			::= { sleV2Ds4VlanEntry 2 }

		
		-- 1.3.6.1.4.1.6296.102.6.2.6.2.2
		sleV2Ds4VlanControl OBJECT IDENTIFIER ::= { sleV2Ds4Vlan 2 }

		
		-- 1.3.6.1.4.1.6296.102.6.2.6.2.2.1
		sleV2Ds4VlanControlRequest OBJECT-TYPE
			SYNTAX INTEGER { setDsVlanState(1) }
			MAX-ACCESS read-write
			STATUS current
			DESCRIPTION
				"The request of a user command."
			::= { sleV2Ds4VlanControl 1 }

		
		-- 1.3.6.1.4.1.6296.102.6.2.6.2.2.2
		sleV2Ds4VlanControlStatus OBJECT-TYPE
			SYNTAX SleControlStatusType
			MAX-ACCESS read-only
			STATUS current
			DESCRIPTION
				"The status of a user command."
			::= { sleV2Ds4VlanControl 2 }

		
		-- 1.3.6.1.4.1.6296.102.6.2.6.2.2.3
		sleV2Ds4VlanControlTimer OBJECT-TYPE
			SYNTAX Gauge32
			MAX-ACCESS read-write
			STATUS current
			DESCRIPTION
				"The maximum wait time for the manager for a long running user command."
			::= { sleV2Ds4VlanControl 3 }

		
		-- 1.3.6.1.4.1.6296.102.6.2.6.2.2.4
		sleV2Ds4VlanControlTimeStamp OBJECT-TYPE
			SYNTAX TimeTicks
			MAX-ACCESS read-only
			STATUS current
			DESCRIPTION
				"The time stamp of the last command (end of command)."
			::= { sleV2Ds4VlanControl 4 }

		
		-- 1.3.6.1.4.1.6296.102.6.2.6.2.2.5
		sleV2Ds4VlanControlReqResult OBJECT-TYPE
			SYNTAX SleControlRequestResultType
			MAX-ACCESS read-only
			STATUS current
			DESCRIPTION
				"The result of the last user command."
			::= { sleV2Ds4VlanControl 5 }

		
		-- 1.3.6.1.4.1.6296.102.6.2.6.2.2.6
		sleV2Ds4VlanControlIndex OBJECT-TYPE
			SYNTAX INTEGER (1..4094)
			MAX-ACCESS read-write
			STATUS current
			DESCRIPTION
				"The vlan index of dhcp snooping."
			::= { sleV2Ds4VlanControl 6 }

		
		-- 1.3.6.1.4.1.6296.102.6.2.6.2.2.7
		sleV2Ds4VlanControlState OBJECT-TYPE
			SYNTAX INTEGER
				{
				disable(0),
				enable(1)
				}
			MAX-ACCESS read-write
			STATUS current
			DESCRIPTION
				"The Dhcp snooping status of Vlan."
			::= { sleV2Ds4VlanControl 7 }

		
		-- 1.3.6.1.4.1.6296.102.6.2.6.2.3
		sleV2Ds4VlanNotification OBJECT IDENTIFIER ::= { sleV2Ds4Vlan 3 }

		
		-- 1.3.6.1.4.1.6296.102.6.2.6.2.3.1
		sleV2Ds4VlanStateChanged NOTIFICATION-TYPE
			OBJECTS { sleV2Ds4VlanControlRequest, sleV2Ds4VlanControlTimeStamp, sleV2Ds4VlanControlReqResult, sleV2Ds4VlanState }
			STATUS current
			DESCRIPTION 
				"Description."
			::= { sleV2Ds4VlanNotification 1 }

		
		-- 1.3.6.1.4.1.6296.102.6.2.6.3
		sleV2Ds4Port OBJECT IDENTIFIER ::= { sleV2Dhcp4Snooping 3 }

		
		-- 1.3.6.1.4.1.6296.102.6.2.6.3.1
		sleV2Ds4PortTable OBJECT-TYPE
			SYNTAX SEQUENCE OF SleV2Ds4PortEntry
			MAX-ACCESS not-accessible
			STATUS current
			DESCRIPTION
				"Description."
			::= { sleV2Ds4Port 1 }

		
		-- 1.3.6.1.4.1.6296.102.6.2.6.3.1.1
		sleV2Ds4PortEntry OBJECT-TYPE
			SYNTAX SleV2Ds4PortEntry
			MAX-ACCESS not-accessible
			STATUS current
			DESCRIPTION
				"A row instance contains the configuration to enable
				or disable trust state for DHCP Snooping at each physical
				interface capable of this feature."
			INDEX { sleV2Ds4PortIndex }
			::= { sleV2Ds4PortTable 1 }

		
		SleV2Ds4PortEntry ::=
			SEQUENCE { 
				sleV2Ds4PortIndex
					INTEGER,
				sleV2Ds4PortTrustState
					INTEGER,
				sleV2Ds4PortLimitRate
					INTEGER,
				sleV2Ds4PortLimitLease
					INTEGER,
				sleV2Ds4PortSrcGuardState
					INTEGER,
				sleV2Ds4PortTimeout
					INTEGER,
				sleV2Ds4PortStatus
					INTEGER,
				sleV2Ds4PortFilterMode
					INTEGER,
				sleV2Ds4PortFilterDelayTimer
					INTEGER,
				sleV2Ds4PortFilterDelayCounter
					INTEGER
			 }

		-- 1.3.6.1.4.1.6296.102.6.2.6.3.1.1.1
		sleV2Ds4PortIndex OBJECT-TYPE
			SYNTAX INTEGER (1..255)
			MAX-ACCESS read-only
			STATUS current
			DESCRIPTION
				"Description."
			::= { sleV2Ds4PortEntry 1 }

		
		-- 1.3.6.1.4.1.6296.102.6.2.6.3.1.1.2
		sleV2Ds4PortTrustState OBJECT-TYPE
			SYNTAX INTEGER
				{
				disable(0),
				enable(1)
				}
			MAX-ACCESS read-only
			STATUS current
			DESCRIPTION
				"This object indicates whether the interface is trusted for
				DHCP Snooping purpose. 
				
				If this object is set to 'true', the interface is trusted.
				DHCP packets coming to this interface will be forwarded
				without checking.
				
				If this object is set to 'false', the interface is not
				trusted. DHCP packets coming to this interface will be
				subjected to DHCP checks."
			::= { sleV2Ds4PortEntry 2 }

		
		-- 1.3.6.1.4.1.6296.102.6.2.6.3.1.1.3
		sleV2Ds4PortLimitRate OBJECT-TYPE
			SYNTAX INTEGER (0 | 1..255)
			MAX-ACCESS read-only
			STATUS current
			DESCRIPTION
				"."
			::= { sleV2Ds4PortEntry 3 }

		
		-- 1.3.6.1.4.1.6296.102.6.2.6.3.1.1.4
		sleV2Ds4PortLimitLease OBJECT-TYPE
			SYNTAX INTEGER (0 | 1..2147483637)
			MAX-ACCESS read-only
			STATUS current
			DESCRIPTION
				"."
			::= { sleV2Ds4PortEntry 4 }

		
		-- 1.3.6.1.4.1.6296.102.6.2.6.3.1.1.5
		sleV2Ds4PortSrcGuardState OBJECT-TYPE
			SYNTAX INTEGER
				{
				disable(0),
				ipEnable(1),
				ipMacEnable(2)
				}
			MAX-ACCESS read-only
			STATUS current
			DESCRIPTION
				"."
			::= { sleV2Ds4PortEntry 5 }

		
		-- 1.3.6.1.4.1.6296.102.6.2.6.3.1.1.6
		sleV2Ds4PortTimeout OBJECT-TYPE
			SYNTAX INTEGER (0 | 120..2147483637)
			MAX-ACCESS read-only
			STATUS current
			DESCRIPTION
				"DHCP Snooping Timeout"
			::= { sleV2Ds4PortEntry 6 }

		
		-- 1.3.6.1.4.1.6296.102.6.2.6.3.1.1.7
		sleV2Ds4PortStatus OBJECT-TYPE
			SYNTAX INTEGER
				{
				enable(1),
				diable(2)
				}
			MAX-ACCESS read-only
			STATUS current
			DESCRIPTION
				"Description."
			::= { sleV2Ds4PortEntry 7 }

		
		-- 1.3.6.1.4.1.6296.102.6.2.6.3.1.1.8
		sleV2Ds4PortFilterMode OBJECT-TYPE
			SYNTAX INTEGER
				{
				disable(0),
				permit(1),
				bypass(2),
				filter(3)
				}
			MAX-ACCESS read-only
			STATUS current
			DESCRIPTION
				"Description."
			::= { sleV2Ds4PortEntry 8 }

		
		-- 1.3.6.1.4.1.6296.102.6.2.6.3.1.1.9
		sleV2Ds4PortFilterDelayTimer OBJECT-TYPE
			SYNTAX INTEGER (-1 | 1..2147483637)
			MAX-ACCESS read-only
			STATUS current
			DESCRIPTION
				"Description."
			::= { sleV2Ds4PortEntry 9 }

		
		-- 1.3.6.1.4.1.6296.102.6.2.6.3.1.1.10
		sleV2Ds4PortFilterDelayCounter OBJECT-TYPE
			SYNTAX INTEGER (-1 | 1..2147483637)
			MAX-ACCESS read-only
			STATUS current
			DESCRIPTION
				"Description."
			::= { sleV2Ds4PortEntry 10 }

		
		-- 1.3.6.1.4.1.6296.102.6.2.6.3.2
		sleV2Ds4PortControl OBJECT IDENTIFIER ::= { sleV2Ds4Port 2 }

		
		-- 1.3.6.1.4.1.6296.102.6.2.6.3.2.1
		sleV2Ds4PortControlRequest OBJECT-TYPE
			SYNTAX INTEGER
				{
				setDsPortTrustState(1),
				setDsPortLimitProfile(2),
				setDsPortSrcGuardState(3),
				setDsPortTimeout(4),
				setDsPortStatus(5),
				setDsPortFilterMode(6),
				setDsPortFilterDelay(7)
				}
			MAX-ACCESS read-write
			STATUS current
			DESCRIPTION
				"The request of a user command."
			::= { sleV2Ds4PortControl 1 }

		
		-- 1.3.6.1.4.1.6296.102.6.2.6.3.2.2
		sleV2Ds4PortControlStatus OBJECT-TYPE
			SYNTAX SleControlStatusType
			MAX-ACCESS read-only
			STATUS current
			DESCRIPTION
				"The status of a user command."
			::= { sleV2Ds4PortControl 2 }

		
		-- 1.3.6.1.4.1.6296.102.6.2.6.3.2.3
		sleV2Ds4PortControlTimer OBJECT-TYPE
			SYNTAX Gauge32
			MAX-ACCESS read-write
			STATUS current
			DESCRIPTION
				"The maximum wait time for the manager for a long running user command."
			::= { sleV2Ds4PortControl 3 }

		
		-- 1.3.6.1.4.1.6296.102.6.2.6.3.2.4
		sleV2Ds4PortControlTimeStamp OBJECT-TYPE
			SYNTAX TimeTicks
			MAX-ACCESS read-only
			STATUS current
			DESCRIPTION
				"The time stamp of the last command (end of command)."
			::= { sleV2Ds4PortControl 4 }

		
		-- 1.3.6.1.4.1.6296.102.6.2.6.3.2.5
		sleV2Ds4PortControlReqResult OBJECT-TYPE
			SYNTAX SleControlRequestResultType
			MAX-ACCESS read-only
			STATUS current
			DESCRIPTION
				"The result of the last user command."
			::= { sleV2Ds4PortControl 5 }

		
		-- 1.3.6.1.4.1.6296.102.6.2.6.3.2.6
		sleV2Ds4PortControlIndex OBJECT-TYPE
			SYNTAX INTEGER (1..255)
			MAX-ACCESS read-write
			STATUS current
			DESCRIPTION
				"."
			::= { sleV2Ds4PortControl 6 }

		
		-- 1.3.6.1.4.1.6296.102.6.2.6.3.2.7
		sleV2Ds4PortControlTrustState OBJECT-TYPE
			SYNTAX INTEGER
				{
				disable(0),
				enable(1)
				}
			MAX-ACCESS read-write
			STATUS current
			DESCRIPTION
				"."
			::= { sleV2Ds4PortControl 7 }

		
		-- 1.3.6.1.4.1.6296.102.6.2.6.3.2.8
		sleV2Ds4PortControlLimitRate OBJECT-TYPE
			SYNTAX INTEGER (0 | 1..255)
			MAX-ACCESS read-write
			STATUS current
			DESCRIPTION
				"."
			::= { sleV2Ds4PortControl 8 }

		
		-- 1.3.6.1.4.1.6296.102.6.2.6.3.2.9
		sleV2Ds4PortControlLimitLease OBJECT-TYPE
			SYNTAX INTEGER (0 | 1..2147483637)
			MAX-ACCESS read-write
			STATUS current
			DESCRIPTION
				"."
			::= { sleV2Ds4PortControl 9 }

		
		-- 1.3.6.1.4.1.6296.102.6.2.6.3.2.10
		sleV2Ds4PortControlSrcGuardState OBJECT-TYPE
			SYNTAX INTEGER
				{
				disable(0),
				ipEnable(1),
				ipMacEnable(2)
				}
			MAX-ACCESS read-write
			STATUS current
			DESCRIPTION
				"."
			::= { sleV2Ds4PortControl 10 }

		
		-- 1.3.6.1.4.1.6296.102.6.2.6.3.2.11
		sleV2Ds4PortControlTimeout OBJECT-TYPE
			SYNTAX INTEGER (0 | 120..2147483637)
			MAX-ACCESS read-write
			STATUS current
			DESCRIPTION
				"DHCP Snooping Timeout"
			::= { sleV2Ds4PortControl 11 }

		
		-- 1.3.6.1.4.1.6296.102.6.2.6.3.2.12
		sleV2Ds4PortControlPStatus OBJECT-TYPE
			SYNTAX INTEGER
				{
				enable(1),
				disable(2)
				}
			MAX-ACCESS read-write
			STATUS current
			DESCRIPTION
				"Description."
			::= { sleV2Ds4PortControl 12 }

		
		-- 1.3.6.1.4.1.6296.102.6.2.6.3.2.13
		sleV2Ds4PortControlFilterMode OBJECT-TYPE
			SYNTAX INTEGER
				{
				disable(0),
				permit(1),
				bypass(2),
				filter(3)
				}
			MAX-ACCESS read-write
			STATUS current
			DESCRIPTION
				"Description."
			::= { sleV2Ds4PortControl 13 }

		
		-- 1.3.6.1.4.1.6296.102.6.2.6.3.2.14
		sleV2Ds4PortControlFilterDelayTimer OBJECT-TYPE
			SYNTAX INTEGER (-1 | 1..2147483637)
			MAX-ACCESS read-write
			STATUS current
			DESCRIPTION
				"Description."
			::= { sleV2Ds4PortControl 14 }

		
		-- 1.3.6.1.4.1.6296.102.6.2.6.3.2.15
		sleV2Ds4PortControlFilterDelayCounter OBJECT-TYPE
			SYNTAX INTEGER (-1 | 1..2147483637)
			MAX-ACCESS read-write
			STATUS current
			DESCRIPTION
				"Description."
			::= { sleV2Ds4PortControl 15 }

		
		-- 1.3.6.1.4.1.6296.102.6.2.6.3.3
		sleV2Ds4PortNotification OBJECT IDENTIFIER ::= { sleV2Ds4Port 3 }

		
		-- 1.3.6.1.4.1.6296.102.6.2.6.3.3.1
		sleV2Ds4PortTrustStateChanged NOTIFICATION-TYPE
			OBJECTS { sleV2Ds4PortControlRequest, sleV2Ds4PortControlTimeStamp, sleV2Ds4PortControlReqResult, sleV2Ds4PortTrustState }
			STATUS current
			DESCRIPTION 
				"Description."
			::= { sleV2Ds4PortNotification 1 }

		
		-- 1.3.6.1.4.1.6296.102.6.2.6.3.3.2
		sleV2Ds4PortLimitProfileChagned NOTIFICATION-TYPE
			OBJECTS { sleV2Ds4PortControlRequest, sleV2Ds4PortControlTimeStamp, sleV2Ds4PortControlReqResult, sleV2Ds4PortLimitLease, sleV2Ds4PortLimitRate
				 }
			STATUS current
			DESCRIPTION 
				"Description."
			::= { sleV2Ds4PortNotification 2 }

		
		-- 1.3.6.1.4.1.6296.102.6.2.6.3.3.3
		sleV2Ds4PortSrcGuardStateChanged NOTIFICATION-TYPE
			OBJECTS { sleV2Ds4PortControlRequest, sleV2Ds4PortControlTimeStamp, sleV2Ds4PortControlReqResult, sleV2Ds4PortSrcGuardState }
			STATUS current
			DESCRIPTION 
				"Description."
			::= { sleV2Ds4PortNotification 3 }

		
		-- 1.3.6.1.4.1.6296.102.6.2.6.3.3.4
		sleV2Ds4PortTimeoutChanged NOTIFICATION-TYPE
			OBJECTS { sleV2Ds4PortControlRequest, sleV2Ds4PortControlTimeStamp, sleV2Ds4PortControlReqResult, sleV2Ds4PortTimeout }
			STATUS current
			DESCRIPTION 
				"Description."
			::= { sleV2Ds4PortNotification 4 }

		
		-- 1.3.6.1.4.1.6296.102.6.2.6.3.3.5
		sleV2Ds4PortStatusChanged NOTIFICATION-TYPE
			OBJECTS { sleV2Ds4PortControlRequest, sleV2Ds4PortControlTimeStamp, sleV2Ds4PortControlReqResult, sleV2Ds4PortControlPStatus }
			STATUS current
			DESCRIPTION 
				"Description."
			::= { sleV2Ds4PortNotification 5 }

		
		-- 1.3.6.1.4.1.6296.102.6.2.6.3.3.6
		sleV2Ds4PortFilterModeChanged NOTIFICATION-TYPE
			OBJECTS { sleV2Ds4PortControlRequest, sleV2Ds4PortControlTimeStamp, sleV2Ds4PortControlReqResult, sleV2Ds4PortFilterMode }
			STATUS current
			DESCRIPTION 
				"Description."
			::= { sleV2Ds4PortNotification 6 }

		
		-- 1.3.6.1.4.1.6296.102.6.2.6.3.3.7
		sleV2Ds4PortFilterDelayChanged NOTIFICATION-TYPE
			OBJECTS { sleV2Ds4PortControlRequest, sleV2Ds4PortControlTimeStamp, sleV2Ds4PortControlReqResult, sleV2Ds4PortFilterDelayTimer, sleV2Ds4PortFilterDelayCounter
				 }
			STATUS current
			DESCRIPTION 
				"Description."
			::= { sleV2Ds4PortNotification 7 }

		
		-- 1.3.6.1.4.1.6296.102.6.2.6.4
		sleV2Ds4Bindings OBJECT IDENTIFIER ::= { sleV2Dhcp4Snooping 4 }

		
		-- 1.3.6.1.4.1.6296.102.6.2.6.4.1
		sleV2Ds4BindingsTable OBJECT-TYPE
			SYNTAX SEQUENCE OF SleV2Ds4BindingsEntry
			MAX-ACCESS not-accessible
			STATUS current
			DESCRIPTION
				"A table provides the DHCP bindings information learnt by
				the device."
			::= { sleV2Ds4Bindings 1 }

		
		-- 1.3.6.1.4.1.6296.102.6.2.6.4.1.1
		sleV2Ds4BindingsEntry OBJECT-TYPE
			SYNTAX SleV2Ds4BindingsEntry
			MAX-ACCESS not-accessible
			STATUS current
			DESCRIPTION
				"A row instance contains the Mac address, IP address type,
				IP address, VLAN number, interface number, leased time and
				status of this instance."
			INDEX { sleV2Ds4BindingsPortIndex, sleV2Ds4BindingsAddress }
			::= { sleV2Ds4BindingsTable 1 }

		
		SleV2Ds4BindingsEntry ::=
			SEQUENCE { 
				sleV2Ds4BindingsVlanIndex
					INTEGER,
				sleV2Ds4BindingsPortIndex
					INTEGER,
				sleV2Ds4BindingsAddress
					IpAddress,
				sleV2Ds4BindingsMac
					MacAddress,
				sleV2Ds4BindingsType
					BITS,
				sleV2Ds4BindingsState
					INTEGER,
				sleV2Ds4BindingsLeasedTime
					INTEGER,
				sleV2Ds4BindingsMaskLen
					Integer32
			 }

		-- 1.3.6.1.4.1.6296.102.6.2.6.4.1.1.1
		sleV2Ds4BindingsVlanIndex OBJECT-TYPE
			SYNTAX INTEGER (1..4094)
			MAX-ACCESS read-only
			STATUS current
			DESCRIPTION
				"This object indicates the VLAN to which a DHCP client host
				belongs."
			::= { sleV2Ds4BindingsEntry 1 }

		
		-- 1.3.6.1.4.1.6296.102.6.2.6.4.1.1.2
		sleV2Ds4BindingsPortIndex OBJECT-TYPE
			SYNTAX INTEGER (1..255)
			MAX-ACCESS read-only
			STATUS current
			DESCRIPTION
				"This object indicates the interface where a DHCP client
				host connects to."
			::= { sleV2Ds4BindingsEntry 2 }

		
		-- 1.3.6.1.4.1.6296.102.6.2.6.4.1.1.3
		sleV2Ds4BindingsAddress OBJECT-TYPE
			SYNTAX IpAddress
			MAX-ACCESS read-only
			STATUS current
			DESCRIPTION
				"This object indicates the allocated IP address of
				a DHCP client host."
			::= { sleV2Ds4BindingsEntry 3 }

		
		-- 1.3.6.1.4.1.6296.102.6.2.6.4.1.1.4
		sleV2Ds4BindingsMac OBJECT-TYPE
			SYNTAX MacAddress
			MAX-ACCESS read-only
			STATUS current
			DESCRIPTION
				"This object indicates the MAC address of a DHCP client
				host."
			::= { sleV2Ds4BindingsEntry 4 }

		
		-- 1.3.6.1.4.1.6296.102.6.2.6.4.1.1.5
		sleV2Ds4BindingsType OBJECT-TYPE
			SYNTAX BITS
				{
				dhcpDynamic(0),
				srcGuardStatic(1)
				}
			MAX-ACCESS read-only
			STATUS current
			DESCRIPTION
				"."
			::= { sleV2Ds4BindingsEntry 5 }

		
		-- 1.3.6.1.4.1.6296.102.6.2.6.4.1.1.6
		sleV2Ds4BindingsState OBJECT-TYPE
			SYNTAX INTEGER
				{
				disable(0),
				enable(1)
				}
			MAX-ACCESS read-only
			STATUS current
			DESCRIPTION
				"Description."
			::= { sleV2Ds4BindingsEntry 6 }

		
		-- 1.3.6.1.4.1.6296.102.6.2.6.4.1.1.7
		sleV2Ds4BindingsLeasedTime OBJECT-TYPE
			SYNTAX INTEGER (-1 | 0 | 1..2147483637)
			UNITS "second"
			MAX-ACCESS read-only
			STATUS current
			DESCRIPTION
				"This object indicates the leased time of this DHCP
				binding entry.
				"
			::= { sleV2Ds4BindingsEntry 7 }

		
		-- 1.3.6.1.4.1.6296.102.6.2.6.4.1.1.8
		sleV2Ds4BindingsMaskLen OBJECT-TYPE
			SYNTAX Integer32
			MAX-ACCESS read-only
			STATUS current
			DESCRIPTION
				"The network mask of the address field of static binding table for snooping"
			::= { sleV2Ds4BindingsEntry 8 }

		
		-- 1.3.6.1.4.1.6296.102.6.2.6.4.2
		sleV2Ds4BindingsControl OBJECT IDENTIFIER ::= { sleV2Ds4Bindings 2 }

		
		-- 1.3.6.1.4.1.6296.102.6.2.6.4.2.1
		sleV2Ds4BindingsControlRequest OBJECT-TYPE
			SYNTAX INTEGER
				{
				createDsBinding(1),
				destroyDsBinding(2),
				clearDsBinding(3)
				}
			MAX-ACCESS read-write
			STATUS current
			DESCRIPTION
				"The request of a user command."
			::= { sleV2Ds4BindingsControl 1 }

		
		-- 1.3.6.1.4.1.6296.102.6.2.6.4.2.2
		sleV2Ds4BindingsControlStatus OBJECT-TYPE
			SYNTAX SleControlStatusType
			MAX-ACCESS read-only
			STATUS current
			DESCRIPTION
				"The status of a user command."
			::= { sleV2Ds4BindingsControl 2 }

		
		-- 1.3.6.1.4.1.6296.102.6.2.6.4.2.3
		sleV2Ds4BindingsControlTimer OBJECT-TYPE
			SYNTAX Gauge32
			MAX-ACCESS read-write
			STATUS current
			DESCRIPTION
				"The maximum wait time for the manager for a long running user command."
			::= { sleV2Ds4BindingsControl 3 }

		
		-- 1.3.6.1.4.1.6296.102.6.2.6.4.2.4
		sleV2Ds4BindingsControlTimeStamp OBJECT-TYPE
			SYNTAX TimeTicks
			MAX-ACCESS read-only
			STATUS current
			DESCRIPTION
				"The time stamp of the last command (end of command)."
			::= { sleV2Ds4BindingsControl 4 }

		
		-- 1.3.6.1.4.1.6296.102.6.2.6.4.2.5
		sleV2Ds4BindingsControlReqResult OBJECT-TYPE
			SYNTAX SleControlRequestResultType
			MAX-ACCESS read-only
			STATUS current
			DESCRIPTION
				"The result of the last user command."
			::= { sleV2Ds4BindingsControl 5 }

		
		-- 1.3.6.1.4.1.6296.102.6.2.6.4.2.6
		sleV2Ds4BindingsControlVlanIndex OBJECT-TYPE
			SYNTAX INTEGER (1..4094)
			MAX-ACCESS read-write
			STATUS current
			DESCRIPTION
				"."
			::= { sleV2Ds4BindingsControl 6 }

		
		-- 1.3.6.1.4.1.6296.102.6.2.6.4.2.7
		sleV2Ds4BindingsControlPortIndex OBJECT-TYPE
			SYNTAX INTEGER (1..255)
			MAX-ACCESS read-write
			STATUS current
			DESCRIPTION
				"."
			::= { sleV2Ds4BindingsControl 7 }

		
		-- 1.3.6.1.4.1.6296.102.6.2.6.4.2.8
		sleV2Ds4BindingsControlAddress OBJECT-TYPE
			SYNTAX IpAddress
			MAX-ACCESS read-only
			STATUS current
			DESCRIPTION
				"This object indicates the allocated IP address of
				a DHCP client host."
			::= { sleV2Ds4BindingsControl 8 }

		
		-- 1.3.6.1.4.1.6296.102.6.2.6.4.2.9
		sleV2Ds4BindingsControlMac OBJECT-TYPE
			SYNTAX MacAddress
			MAX-ACCESS read-write
			STATUS current
			DESCRIPTION
				"."
			::= { sleV2Ds4BindingsControl 9 }

		
		-- 1.3.6.1.4.1.6296.102.6.2.6.4.2.10
		sleV2Ds4BindingsControlType OBJECT-TYPE
			SYNTAX BITS
				{
				dhcpDynamic(0),
				srcGuardStatic(1)
				}
			MAX-ACCESS read-write
			STATUS current
			DESCRIPTION
				"Description."
			::= { sleV2Ds4BindingsControl 10 }

		
		-- 1.3.6.1.4.1.6296.102.6.2.6.4.2.11
		sleV2Ds4BindingsControlLeasedTime OBJECT-TYPE
			SYNTAX INTEGER (-1 | 0 | 1..2147483637)
			UNITS "second"
			MAX-ACCESS read-write
			STATUS current
			DESCRIPTION
				"."
			::= { sleV2Ds4BindingsControl 11 }

		
		-- 1.3.6.1.4.1.6296.102.6.2.6.4.2.12
		sleV2Ds4BindingsControlMaskLen OBJECT-TYPE
			SYNTAX Integer32
			MAX-ACCESS read-write
			STATUS current
			DESCRIPTION
				"The network mask of the address field of static binding table for snooping"
			::= { sleV2Ds4BindingsControl 12 }

		
		-- 1.3.6.1.4.1.6296.102.6.2.6.4.3
		sleV2Ds4BindingsNotification OBJECT IDENTIFIER ::= { sleV2Ds4Bindings 3 }

		
		-- 1.3.6.1.4.1.6296.102.6.2.6.4.3.1
		sleV2Ds4BindingsCreated NOTIFICATION-TYPE
			OBJECTS { sleV2Ds4BindingsControlRequest, sleV2Ds4BindingsControlTimeStamp, sleV2Ds4BindingsControlReqResult, sleV2Ds4BindingsVlanIndex, sleV2Ds4BindingsType, 
				sleV2Ds4BindingsMac, sleV2Ds4BindingsLeasedTime, sleV2Ds4BindingsMaskLen }
			STATUS current
			DESCRIPTION 
				"Description."
			::= { sleV2Ds4BindingsNotification 1 }

		
		-- 1.3.6.1.4.1.6296.102.6.2.6.4.3.2
		sleV2Ds4BindingsDestroyed NOTIFICATION-TYPE
			OBJECTS { sleV2Ds4BindingsControlRequest, sleV2Ds4BindingsControlTimeStamp, sleV2Ds4BindingsControlReqResult, sleV2Ds4BindingsControlPortIndex, sleV2Ds4BindingsControlAddress, 
				sleV2Ds4BindingsControlType, sleV2Ds4BindingsControlMaskLen }
			STATUS current
			DESCRIPTION 
				"Description."
			::= { sleV2Ds4BindingsNotification 2 }

		
		-- 1.3.6.1.4.1.6296.102.6.2.6.4.3.3
		sleV2Ds4BindingsCleared NOTIFICATION-TYPE
			OBJECTS { sleV2Ds4BindingsControlRequest, sleV2Ds4BindingsControlTimeStamp, sleV2Ds4BindingsControlReqResult, sleV2Ds4BindingsControlPortIndex, sleV2Ds4BindingsControlType
				 }
			STATUS current
			DESCRIPTION 
				"Description."
			::= { sleV2Ds4BindingsNotification 3 }

		
		-- 1.3.6.1.4.1.6296.102.6.2.6.5
		sleV2Ds4VlanInfoOpt OBJECT IDENTIFIER ::= { sleV2Dhcp4Snooping 5 }

		
		-- 1.3.6.1.4.1.6296.102.6.2.6.5.1
		sleV2Ds4VlanInfoOptTable OBJECT-TYPE
			SYNTAX SEQUENCE OF SleV2Ds4VlanInfoOptEntry
			MAX-ACCESS not-accessible
			STATUS current
			DESCRIPTION
				"Description."
			::= { sleV2Ds4VlanInfoOpt 1 }

		
		-- 1.3.6.1.4.1.6296.102.6.2.6.5.1.1
		sleV2Ds4VlanInfoOptEntry OBJECT-TYPE
			SYNTAX SleV2Ds4VlanInfoOptEntry
			MAX-ACCESS not-accessible
			STATUS current
			DESCRIPTION
				"Description."
			INDEX { sleV2Ds4VlanInfoOptIndex }
			::= { sleV2Ds4VlanInfoOptTable 1 }

		
		SleV2Ds4VlanInfoOptEntry ::=
			SEQUENCE { 
				sleV2Ds4VlanInfoOptIndex
					INTEGER,
				sleV2Ds4VlanInfoOptState
					INTEGER
			 }

		-- 1.3.6.1.4.1.6296.102.6.2.6.5.1.1.1
		sleV2Ds4VlanInfoOptIndex OBJECT-TYPE
			SYNTAX INTEGER (1..4094)
			MAX-ACCESS read-only
			STATUS current
			DESCRIPTION
				"Description."
			::= { sleV2Ds4VlanInfoOptEntry 1 }

		
		-- 1.3.6.1.4.1.6296.102.6.2.6.5.1.1.2
		sleV2Ds4VlanInfoOptState OBJECT-TYPE
			SYNTAX INTEGER
				{
				disable(0),
				enable(1)
				}
			MAX-ACCESS read-only
			STATUS current
			DESCRIPTION
				"Description."
			::= { sleV2Ds4VlanInfoOptEntry 2 }

		
		-- 1.3.6.1.4.1.6296.102.6.2.6.5.2
		sleV2Ds4VlanInforOptControl OBJECT IDENTIFIER ::= { sleV2Ds4VlanInfoOpt 2 }

		
		-- 1.3.6.1.4.1.6296.102.6.2.6.5.2.1
		sleV2Ds4VlanInfoOptControlRequest OBJECT-TYPE
			SYNTAX INTEGER { setDsVlanInfoOptState(1) }
			MAX-ACCESS read-write
			STATUS current
			DESCRIPTION
				"Description."
			::= { sleV2Ds4VlanInforOptControl 1 }

		
		-- 1.3.6.1.4.1.6296.102.6.2.6.5.2.2
		sleV2Ds4VlanInfoOptControlStatus OBJECT-TYPE
			SYNTAX SleControlStatusType
			MAX-ACCESS read-write
			STATUS current
			DESCRIPTION
				"Description."
			::= { sleV2Ds4VlanInforOptControl 2 }

		
		-- 1.3.6.1.4.1.6296.102.6.2.6.5.2.3
		sleV2Ds4VlanInfoOptControlTimer OBJECT-TYPE
			SYNTAX Gauge32
			MAX-ACCESS read-write
			STATUS current
			DESCRIPTION
				"Description."
			::= { sleV2Ds4VlanInforOptControl 3 }

		
		-- 1.3.6.1.4.1.6296.102.6.2.6.5.2.4
		sleV2Ds4VlanInfoOptControlTimeStamp OBJECT-TYPE
			SYNTAX TimeTicks
			MAX-ACCESS read-write
			STATUS current
			DESCRIPTION
				"Description."
			::= { sleV2Ds4VlanInforOptControl 4 }

		
		-- 1.3.6.1.4.1.6296.102.6.2.6.5.2.5
		sleV2Ds4VlanInfoOptControlReqResult OBJECT-TYPE
			SYNTAX SleControlRequestResultType
			MAX-ACCESS read-write
			STATUS current
			DESCRIPTION
				"Description."
			::= { sleV2Ds4VlanInforOptControl 5 }

		
		-- 1.3.6.1.4.1.6296.102.6.2.6.5.2.6
		sleV2Ds4VlanInfoOptControlIndex OBJECT-TYPE
			SYNTAX INTEGER (1..4094)
			MAX-ACCESS read-write
			STATUS current
			DESCRIPTION
				"Description."
			::= { sleV2Ds4VlanInforOptControl 6 }

		
		-- 1.3.6.1.4.1.6296.102.6.2.6.5.2.7
		sleV2Ds4VlanInfoOptControlState OBJECT-TYPE
			SYNTAX INTEGER
				{
				disable(0),
				enable(1)
				}
			MAX-ACCESS read-write
			STATUS current
			DESCRIPTION
				"Description."
			::= { sleV2Ds4VlanInforOptControl 7 }

		
		-- 1.3.6.1.4.1.6296.102.6.2.6.5.3
		sleV2Ds4VlanInfoOptNotification OBJECT IDENTIFIER ::= { sleV2Ds4VlanInfoOpt 3 }

		
		-- 1.3.6.1.4.1.6296.102.6.2.6.5.3.1
		sleV2Ds4VlanInfoOptStateChanged NOTIFICATION-TYPE
			OBJECTS { sleV2Ds4VlanInfoOptControlRequest, sleV2Ds4VlanInfoOptControlTimeStamp, sleV2Ds4VlanInfoOptControlReqResult, sleV2Ds4VlanInfoOptState }
			STATUS current
			DESCRIPTION 
				"Description."
			::= { sleV2Ds4VlanInfoOptNotification 1 }

		
		-- 1.3.6.1.4.1.6296.102.6.2.7
		sleV2Dhcp4Relay OBJECT IDENTIFIER ::= { sleV2Dhcp4 7 }

		
		-- 1.3.6.1.4.1.6296.102.6.2.7.1
		sleV2Dhcp4RelayInterface OBJECT IDENTIFIER ::= { sleV2Dhcp4Relay 1 }

		
		-- 1.3.6.1.4.1.6296.102.6.2.7.1.1
		sleV2Dhcp4RelayIfTable OBJECT-TYPE
			SYNTAX SEQUENCE OF SleV2Dhcp4RelayIfEntry
			MAX-ACCESS not-accessible
			STATUS current
			DESCRIPTION
				"Description."
			::= { sleV2Dhcp4RelayInterface 1 }

		
		-- 1.3.6.1.4.1.6296.102.6.2.7.1.1.1
		sleV2Dhcp4RelayIfEntry OBJECT-TYPE
			SYNTAX SleV2Dhcp4RelayIfEntry
			MAX-ACCESS not-accessible
			STATUS current
			DESCRIPTION
				"Description."
			INDEX { sleV2Dhcp4RelayIfIndex }
			::= { sleV2Dhcp4RelayIfTable 1 }

		
		SleV2Dhcp4RelayIfEntry ::=
			SEQUENCE { 
				sleV2Dhcp4RelayIfIndex
					INTEGER,
				sleV2Dhcp4RelayIfSimpleOpt82AdminState
					INTEGER,
				sleV2Dhcp4RelayIfSimpleOpt82OperState
					INTEGER,
				sleV2Dhcp4RelayIfMaxHops
					INTEGER
			 }

		-- 1.3.6.1.4.1.6296.102.6.2.7.1.1.1.1
		sleV2Dhcp4RelayIfIndex OBJECT-TYPE
			SYNTAX INTEGER (1..4094)
			MAX-ACCESS read-only
			STATUS current
			DESCRIPTION
				"Description."
			::= { sleV2Dhcp4RelayIfEntry 1 }

		
		-- 1.3.6.1.4.1.6296.102.6.2.7.1.1.1.2
		sleV2Dhcp4RelayIfSimpleOpt82AdminState OBJECT-TYPE
			SYNTAX INTEGER
				{
				disable(0),
				enable(1)
				}
			MAX-ACCESS read-only
			STATUS current
			DESCRIPTION
				"The status of Simplified option82 of interface."
			DEFVAL { disable }
			::= { sleV2Dhcp4RelayIfEntry 2 }

		
		-- 1.3.6.1.4.1.6296.102.6.2.7.1.1.1.3
		sleV2Dhcp4RelayIfSimpleOpt82OperState OBJECT-TYPE
			SYNTAX INTEGER
				{
				disabled(0),
				enabled(1)
				}
			MAX-ACCESS read-only
			STATUS current
			DESCRIPTION
				"Description."
			DEFVAL { disabled }
			::= { sleV2Dhcp4RelayIfEntry 3 }

		
		-- 1.3.6.1.4.1.6296.102.6.2.7.1.1.1.4
		sleV2Dhcp4RelayIfMaxHops OBJECT-TYPE
			SYNTAX INTEGER (1..15)
			MAX-ACCESS read-only
			STATUS current
			DESCRIPTION
				"Description."
			DEFVAL { 4 }
			::= { sleV2Dhcp4RelayIfEntry 4 }

		
		-- 1.3.6.1.4.1.6296.102.6.2.7.1.2
		sleV2Dhcp4RelayIfControl OBJECT IDENTIFIER ::= { sleV2Dhcp4RelayInterface 2 }

		
		-- 1.3.6.1.4.1.6296.102.6.2.7.1.2.1
		sleV2Dhcp4RelayIfControlRequest OBJECT-TYPE
			SYNTAX INTEGER
				{
				setDhcpSimplifiedOpt82State(1),
				setDhcpRelayMaxHops(2)
				}
			MAX-ACCESS read-write
			STATUS current
			DESCRIPTION
				"The request of a user command."
			::= { sleV2Dhcp4RelayIfControl 1 }

		
		-- 1.3.6.1.4.1.6296.102.6.2.7.1.2.2
		sleV2Dhcp4RelayIfControlStatus OBJECT-TYPE
			SYNTAX SleControlStatusType
			MAX-ACCESS read-only
			STATUS current
			DESCRIPTION
				"The status of a user command."
			::= { sleV2Dhcp4RelayIfControl 2 }

		
		-- 1.3.6.1.4.1.6296.102.6.2.7.1.2.3
		sleV2Dhcp4RelayIfControlTimer OBJECT-TYPE
			SYNTAX Gauge32
			MAX-ACCESS read-write
			STATUS current
			DESCRIPTION
				"The maximum wait time for the manager for a long running user command."
			::= { sleV2Dhcp4RelayIfControl 3 }

		
		-- 1.3.6.1.4.1.6296.102.6.2.7.1.2.4
		sleV2Dhcp4RelayIfControlTimeStamp OBJECT-TYPE
			SYNTAX TimeTicks
			MAX-ACCESS read-only
			STATUS current
			DESCRIPTION
				"The time stamp of the last command (end of command)."
			::= { sleV2Dhcp4RelayIfControl 4 }

		
		-- 1.3.6.1.4.1.6296.102.6.2.7.1.2.5
		sleV2Dhcp4RelayIfControllReqResult OBJECT-TYPE
			SYNTAX SleControlRequestResultType
			MAX-ACCESS read-only
			STATUS current
			DESCRIPTION
				"The result of the last user command."
			::= { sleV2Dhcp4RelayIfControl 5 }

		
		-- 1.3.6.1.4.1.6296.102.6.2.7.1.2.6
		sleV2Dhcp4RelayIfControlIndex OBJECT-TYPE
			SYNTAX INTEGER (1..4094)
			MAX-ACCESS read-write
			STATUS current
			DESCRIPTION
				"Network Interface Index."
			::= { sleV2Dhcp4RelayIfControl 6 }

		
		-- 1.3.6.1.4.1.6296.102.6.2.7.1.2.7
		sleV2Dhcp4RelayIfControlSimpleOpt82AdminState OBJECT-TYPE
			SYNTAX INTEGER
				{
				disable(0),
				enable(1)
				}
			MAX-ACCESS read-write
			STATUS current
			DESCRIPTION
				"The Simplified Option82 status of interface."
			DEFVAL { 0 }
			::= { sleV2Dhcp4RelayIfControl 7 }

		
		-- 1.3.6.1.4.1.6296.102.6.2.7.1.2.8
		sleV2Dhcp4RelayIfControlMaxHops OBJECT-TYPE
			SYNTAX INTEGER (1..15)
			MAX-ACCESS read-write
			STATUS current
			DESCRIPTION
				"Description."
			::= { sleV2Dhcp4RelayIfControl 8 }

		
		-- 1.3.6.1.4.1.6296.102.6.2.7.1.3
		sleV2Dhcp4RelayIfNotification OBJECT IDENTIFIER ::= { sleV2Dhcp4RelayInterface 3 }

		
		-- 1.3.6.1.4.1.6296.102.6.2.7.1.3.1
		sleV2Dhcp4RelayIfSimpleOpt82AdminStateChanged NOTIFICATION-TYPE
			OBJECTS { sleV2Dhcp4RelayIfControlRequest, sleV2Dhcp4RelayIfControlTimeStamp, sleV2Dhcp4RelayIfControllReqResult, sleV2Dhcp4RelayIfSimpleOpt82AdminState }
			STATUS current
			DESCRIPTION 
				"setDhcpSimplifiedOpt82status"
			::= { sleV2Dhcp4RelayIfNotification 1 }

		
		-- 1.3.6.1.4.1.6296.102.6.2.7.1.3.2
		sleV2Dhcp4RelayIfMaxHopsChanged NOTIFICATION-TYPE
			OBJECTS { sleV2Dhcp4RelayIfControlRequest, sleV2Dhcp4RelayIfControlTimeStamp, sleV2Dhcp4RelayIfMaxHops, sleV2Dhcp4RelayIfControllReqResult, sleV2Dhcp4RelayIfSimpleOpt82AdminState
				 }
			STATUS current
			DESCRIPTION 
				"setDhcpSimplifiedOpt82status"
			::= { sleV2Dhcp4RelayIfNotification 2 }

		
		-- 1.3.6.1.4.1.6296.102.6.2.7.2
		sleV2Dhcp4RelayHelper OBJECT IDENTIFIER ::= { sleV2Dhcp4Relay 2 }

		
		-- 1.3.6.1.4.1.6296.102.6.2.7.2.1
		sleV2Dhcp4RelayHelperTable OBJECT-TYPE
			SYNTAX SEQUENCE OF SleV2Dhcp4RelayHelperEntry
			MAX-ACCESS not-accessible
			STATUS current
			DESCRIPTION
				"Description."
			::= { sleV2Dhcp4RelayHelper 1 }

		
		-- 1.3.6.1.4.1.6296.102.6.2.7.2.1.1
		sleV2Dhcp4RelayHelperEntry OBJECT-TYPE
			SYNTAX SleV2Dhcp4RelayHelperEntry
			MAX-ACCESS not-accessible
			STATUS current
			DESCRIPTION
				"Description."
			INDEX { sleV2Dhcp4RelayIfIndex, sleV2Dhcp4RelayHelperOui, sleV2Dhcp4RelayHelperAddress }
			::= { sleV2Dhcp4RelayHelperTable 1 }

		
		SleV2Dhcp4RelayHelperEntry ::=
			SEQUENCE { 
				sleV2Dhcp4RelayHelperOui
					OCTET STRING,
				sleV2Dhcp4RelayHelperAddress
					IpAddress,
				sleV2Dhcp4RelayHelperType
					INTEGER
			 }

		-- 1.3.6.1.4.1.6296.102.6.2.7.2.1.1.1
		sleV2Dhcp4RelayHelperOui OBJECT-TYPE
			SYNTAX OCTET STRING (SIZE (3))
			MAX-ACCESS read-only
			STATUS current
			DESCRIPTION
				"00:00:00 - ff:ff:ff"
			::= { sleV2Dhcp4RelayHelperEntry 1 }

		
		-- 1.3.6.1.4.1.6296.102.6.2.7.2.1.1.2
		sleV2Dhcp4RelayHelperAddress OBJECT-TYPE
			SYNTAX IpAddress
			MAX-ACCESS read-only
			STATUS current
			DESCRIPTION
				"."
			::= { sleV2Dhcp4RelayHelperEntry 2 }

		
		-- 1.3.6.1.4.1.6296.102.6.2.7.2.1.1.3
		sleV2Dhcp4RelayHelperType OBJECT-TYPE
			SYNTAX INTEGER { unknown(0) }
			MAX-ACCESS read-only
			STATUS current
			DESCRIPTION
				"Description."
			::= { sleV2Dhcp4RelayHelperEntry 3 }

		
		-- 1.3.6.1.4.1.6296.102.6.2.7.2.2
		sleV2Dhcp4RelayHelperControl OBJECT IDENTIFIER ::= { sleV2Dhcp4RelayHelper 2 }

		
		-- 1.3.6.1.4.1.6296.102.6.2.7.2.2.1
		sleV2Dhcp4RelayHelperControlRequest OBJECT-TYPE
			SYNTAX INTEGER
				{
				createDhcpRelayHelperEntry(1),
				destroyDhcpRelayHelperEntry(2),
				clearDhcpRelayHelperEntry(3)
				}
			MAX-ACCESS read-write
			STATUS current
			DESCRIPTION
				"The request of a user command."
			::= { sleV2Dhcp4RelayHelperControl 1 }

		
		-- 1.3.6.1.4.1.6296.102.6.2.7.2.2.2
		sleV2Dhcp4RelayHelperControlStatus OBJECT-TYPE
			SYNTAX SleControlStatusType
			MAX-ACCESS read-only
			STATUS current
			DESCRIPTION
				"The status of a user command."
			::= { sleV2Dhcp4RelayHelperControl 2 }

		
		-- 1.3.6.1.4.1.6296.102.6.2.7.2.2.3
		sleV2Dhcp4RelayHelperControlTimer OBJECT-TYPE
			SYNTAX Gauge32
			MAX-ACCESS read-write
			STATUS current
			DESCRIPTION
				"The maximum wait time for the manager for a long running user command."
			::= { sleV2Dhcp4RelayHelperControl 3 }

		
		-- 1.3.6.1.4.1.6296.102.6.2.7.2.2.4
		sleV2Dhcp4RelayHelperControlTimeStamp OBJECT-TYPE
			SYNTAX TimeTicks
			MAX-ACCESS read-only
			STATUS current
			DESCRIPTION
				"The time stamp of the last command (end of command)."
			::= { sleV2Dhcp4RelayHelperControl 4 }

		
		-- 1.3.6.1.4.1.6296.102.6.2.7.2.2.5
		sleV2Dhcp4RelayHelperControlReqResult OBJECT-TYPE
			SYNTAX SleControlRequestResultType
			MAX-ACCESS read-only
			STATUS current
			DESCRIPTION
				"The result of the last user command."
			::= { sleV2Dhcp4RelayHelperControl 5 }

		
		-- 1.3.6.1.4.1.6296.102.6.2.7.2.2.6
		sleV2Dhcp4RelayHelperControlIfIndex OBJECT-TYPE
			SYNTAX INTEGER (1..4094)
			MAX-ACCESS read-write
			STATUS current
			DESCRIPTION
				"."
			::= { sleV2Dhcp4RelayHelperControl 6 }

		
		-- 1.3.6.1.4.1.6296.102.6.2.7.2.2.7
		sleV2Dhcp4RelayHelperControlOui OBJECT-TYPE
			SYNTAX OCTET STRING (SIZE (3))
			MAX-ACCESS read-write
			STATUS current
			DESCRIPTION
				"00:00:00 - ff:ff:ff"
			::= { sleV2Dhcp4RelayHelperControl 7 }

		
		-- 1.3.6.1.4.1.6296.102.6.2.7.2.2.8
		sleV2Dhcp4RelayHelperControlAddress OBJECT-TYPE
			SYNTAX IpAddress
			MAX-ACCESS read-write
			STATUS current
			DESCRIPTION
				"."
			::= { sleV2Dhcp4RelayHelperControl 8 }

		
		-- 1.3.6.1.4.1.6296.102.6.2.7.2.2.9
		sleV2Dhcp4RelayHelperControlType OBJECT-TYPE
			SYNTAX INTEGER { unknown(0) }
			MAX-ACCESS read-write
			STATUS current
			DESCRIPTION
				"Description."
			::= { sleV2Dhcp4RelayHelperControl 9 }

		
		-- 1.3.6.1.4.1.6296.102.6.2.7.2.3
		sleV2Dhcp4RelayHelperNotification OBJECT IDENTIFIER ::= { sleV2Dhcp4RelayHelper 3 }

		
		-- 1.3.6.1.4.1.6296.102.6.2.7.2.3.1
		sleV2Dhcp4RelayHelperCreated NOTIFICATION-TYPE
			OBJECTS { sleV2Dhcp4RelayHelperControlRequest, sleV2Dhcp4RelayHelperControlTimeStamp, sleV2Dhcp4RelayHelperControlReqResult, sleV2Dhcp4RelayHelperType }
			STATUS current
			DESCRIPTION 
				"."
			::= { sleV2Dhcp4RelayHelperNotification 1 }

		
		-- 1.3.6.1.4.1.6296.102.6.2.7.2.3.2
		sleV2Dhcp4RelayHelperDestroyed NOTIFICATION-TYPE
			OBJECTS { sleV2Dhcp4RelayHelperControlRequest, sleV2Dhcp4RelayHelperControlTimeStamp, sleV2Dhcp4RelayHelperControlReqResult, sleV2Dhcp4RelayHelperControlIfIndex, sleV2Dhcp4RelayHelperControlOui, 
				sleV2Dhcp4RelayHelperControlAddress }
			STATUS current
			DESCRIPTION 
				"."
			::= { sleV2Dhcp4RelayHelperNotification 2 }

		
		-- 1.3.6.1.4.1.6296.102.6.2.7.2.3.3
		sleV2Dhcp4RelayHelperCleared NOTIFICATION-TYPE
			OBJECTS { sleV2Dhcp4RelayHelperControlRequest, sleV2Dhcp4RelayHelperControlTimeStamp, sleV2Dhcp4RelayHelperControlReqResult, sleV2Dhcp4RelayHelperControlIfIndex, sleV2Dhcp4RelayHelperControlOui
				 }
			STATUS current
			DESCRIPTION 
				"."
			::= { sleV2Dhcp4RelayHelperNotification 3 }

		
		-- 1.3.6.1.4.1.6296.102.6.2.7.3
		sleV2Dhcp4RelayStats OBJECT IDENTIFIER ::= { sleV2Dhcp4Relay 3 }

		
		-- 1.3.6.1.4.1.6296.102.6.2.7.3.1
		sleV2Dhcp4RelayIntrStatsTable OBJECT-TYPE
			SYNTAX SEQUENCE OF SleV2Dhcp4RelayIntrStatsEntry
			MAX-ACCESS not-accessible
			STATUS current
			DESCRIPTION
				"Description."
			::= { sleV2Dhcp4RelayStats 1 }

		
		-- 1.3.6.1.4.1.6296.102.6.2.7.3.1.1
		sleV2Dhcp4RelayIntrStatsEntry OBJECT-TYPE
			SYNTAX SleV2Dhcp4RelayIntrStatsEntry
			MAX-ACCESS not-accessible
			STATUS current
			DESCRIPTION
				"Description."
			INDEX { sleV2Dhcp4RelayIntrIndex }
			::= { sleV2Dhcp4RelayIntrStatsTable 1 }

		
		SleV2Dhcp4RelayIntrStatsEntry ::=
			SEQUENCE { 
				sleV2Dhcp4RelayIntrIndex
					Integer32,
				sleV2Dhcp4RelayIntrRcvd
					Counter32,
				sleV2Dhcp4RelayIntrSent
					Gauge32,
				sleV2Dhcp4RelayIntrRcvdErrors
					Counter32,
				sleV2Dhcp4RelayIntrSentErrors
					Counter32,
				sleV2Dhcp4RelayIntrRcvdBootpRequest
					Counter32,
				sleV2Dhcp4RelayIntrRcvdBootpReply
					Counter32,
				sleV2Dhcp4RelayIntrSentBootpRequest
					Counter32,
				sleV2Dhcp4RelayIntrSentBootpReply
					Counter32,
				sleV2Dhcp4RelayIntrRcvdDiscover
					Counter32,
				sleV2Dhcp4RelayIntrRcvdRequest
					Counter32,
				sleV2Dhcp4RelayIntrRcvdRelease
					Counter32,
				sleV2Dhcp4RelayIntrRcvdInform
					Counter32,
				sleV2Dhcp4RelayIntrRcvdDecline
					Counter32,
				sleV2Dhcp4RelayIntrSentDiscover
					Counter32,
				sleV2Dhcp4RelayIntrSentRequest
					Counter32,
				sleV2Dhcp4RelayIntrSentRelease
					Counter32,
				sleV2Dhcp4RelayIntrSentInform
					Counter32,
				sleV2Dhcp4RelayIntrSentDecline
					Counter32,
				sleV2Dhcp4RelayIntrRcvdOffer
					Counter32,
				sleV2Dhcp4RelayIntrRcvdAck
					Counter32,
				sleV2Dhcp4RelayIntrRcvdNack
					Counter32,
				sleV2Dhcp4RelayIntrSentOffer
					Counter32,
				sleV2Dhcp4RelayIntrSentAck
					Counter32,
				sleV2Dhcp4RelayIntrSentNack
					Counter32
			 }

		-- 1.3.6.1.4.1.6296.102.6.2.7.3.1.1.1
		sleV2Dhcp4RelayIntrIndex OBJECT-TYPE
			SYNTAX Integer32 (1..65535)
			MAX-ACCESS read-only
			STATUS current
			DESCRIPTION
				"The relay interface index.  
				Same as  VLAN index related to the interface."
			::= { sleV2Dhcp4RelayIntrStatsEntry 1 }

		
		-- 1.3.6.1.4.1.6296.102.6.2.7.3.1.1.2
		sleV2Dhcp4RelayIntrRcvd OBJECT-TYPE
			SYNTAX Counter32
			MAX-ACCESS read-only
			STATUS current
			DESCRIPTION
				"The received-packets.
				"
			::= { sleV2Dhcp4RelayIntrStatsEntry 2 }

		
		-- 1.3.6.1.4.1.6296.102.6.2.7.3.1.1.3
		sleV2Dhcp4RelayIntrSent OBJECT-TYPE
			SYNTAX Gauge32
			MAX-ACCESS read-only
			STATUS current
			DESCRIPTION
				"The sent-packets.
				"
			::= { sleV2Dhcp4RelayIntrStatsEntry 3 }

		
		-- 1.3.6.1.4.1.6296.102.6.2.7.3.1.1.4
		sleV2Dhcp4RelayIntrRcvdErrors OBJECT-TYPE
			SYNTAX Counter32
			MAX-ACCESS read-only
			STATUS current
			DESCRIPTION
				"The received error packtes
				"
			::= { sleV2Dhcp4RelayIntrStatsEntry 4 }

		
		-- 1.3.6.1.4.1.6296.102.6.2.7.3.1.1.5
		sleV2Dhcp4RelayIntrSentErrors OBJECT-TYPE
			SYNTAX Counter32
			MAX-ACCESS read-only
			STATUS current
			DESCRIPTION
				"The sent error packtes.
				"
			::= { sleV2Dhcp4RelayIntrStatsEntry 5 }

		
		-- 1.3.6.1.4.1.6296.102.6.2.7.3.1.1.6
		sleV2Dhcp4RelayIntrRcvdBootpRequest OBJECT-TYPE
			SYNTAX Counter32
			MAX-ACCESS read-only
			STATUS current
			DESCRIPTION
				"The received bootp request.
				"
			::= { sleV2Dhcp4RelayIntrStatsEntry 6 }

		
		-- 1.3.6.1.4.1.6296.102.6.2.7.3.1.1.7
		sleV2Dhcp4RelayIntrRcvdBootpReply OBJECT-TYPE
			SYNTAX Counter32
			MAX-ACCESS read-only
			STATUS current
			DESCRIPTION
				"The received bootp reply.
				"
			::= { sleV2Dhcp4RelayIntrStatsEntry 7 }

		
		-- 1.3.6.1.4.1.6296.102.6.2.7.3.1.1.8
		sleV2Dhcp4RelayIntrSentBootpRequest OBJECT-TYPE
			SYNTAX Counter32
			MAX-ACCESS read-only
			STATUS current
			DESCRIPTION
				"The sent bootp request.
				"
			::= { sleV2Dhcp4RelayIntrStatsEntry 8 }

		
		-- 1.3.6.1.4.1.6296.102.6.2.7.3.1.1.9
		sleV2Dhcp4RelayIntrSentBootpReply OBJECT-TYPE
			SYNTAX Counter32
			MAX-ACCESS read-only
			STATUS current
			DESCRIPTION
				"The sent bootp reply
				"
			::= { sleV2Dhcp4RelayIntrStatsEntry 9 }

		
		-- 1.3.6.1.4.1.6296.102.6.2.7.3.1.1.10
		sleV2Dhcp4RelayIntrRcvdDiscover OBJECT-TYPE
			SYNTAX Counter32
			MAX-ACCESS read-only
			STATUS current
			DESCRIPTION
				"The received discover from client.
				"
			::= { sleV2Dhcp4RelayIntrStatsEntry 10 }

		
		-- 1.3.6.1.4.1.6296.102.6.2.7.3.1.1.11
		sleV2Dhcp4RelayIntrRcvdRequest OBJECT-TYPE
			SYNTAX Counter32
			MAX-ACCESS read-only
			STATUS current
			DESCRIPTION
				"The received request from client.
				"
			::= { sleV2Dhcp4RelayIntrStatsEntry 11 }

		
		-- 1.3.6.1.4.1.6296.102.6.2.7.3.1.1.12
		sleV2Dhcp4RelayIntrRcvdRelease OBJECT-TYPE
			SYNTAX Counter32
			MAX-ACCESS read-only
			STATUS current
			DESCRIPTION
				"The received release from client.
				"
			::= { sleV2Dhcp4RelayIntrStatsEntry 12 }

		
		-- 1.3.6.1.4.1.6296.102.6.2.7.3.1.1.13
		sleV2Dhcp4RelayIntrRcvdInform OBJECT-TYPE
			SYNTAX Counter32
			MAX-ACCESS read-only
			STATUS current
			DESCRIPTION
				"The received inform from client.
				"
			::= { sleV2Dhcp4RelayIntrStatsEntry 13 }

		
		-- 1.3.6.1.4.1.6296.102.6.2.7.3.1.1.14
		sleV2Dhcp4RelayIntrRcvdDecline OBJECT-TYPE
			SYNTAX Counter32
			MAX-ACCESS read-only
			STATUS current
			DESCRIPTION
				"The received decline from client.
				"
			::= { sleV2Dhcp4RelayIntrStatsEntry 14 }

		
		-- 1.3.6.1.4.1.6296.102.6.2.7.3.1.1.15
		sleV2Dhcp4RelayIntrSentDiscover OBJECT-TYPE
			SYNTAX Counter32
			MAX-ACCESS read-only
			STATUS current
			DESCRIPTION
				"The sent discover to server.
				"
			::= { sleV2Dhcp4RelayIntrStatsEntry 15 }

		
		-- 1.3.6.1.4.1.6296.102.6.2.7.3.1.1.16
		sleV2Dhcp4RelayIntrSentRequest OBJECT-TYPE
			SYNTAX Counter32
			MAX-ACCESS read-only
			STATUS current
			DESCRIPTION
				"The sent request to server.
				"
			::= { sleV2Dhcp4RelayIntrStatsEntry 16 }

		
		-- 1.3.6.1.4.1.6296.102.6.2.7.3.1.1.17
		sleV2Dhcp4RelayIntrSentRelease OBJECT-TYPE
			SYNTAX Counter32
			MAX-ACCESS read-only
			STATUS current
			DESCRIPTION
				"The sent release to server.
				"
			::= { sleV2Dhcp4RelayIntrStatsEntry 17 }

		
		-- 1.3.6.1.4.1.6296.102.6.2.7.3.1.1.18
		sleV2Dhcp4RelayIntrSentInform OBJECT-TYPE
			SYNTAX Counter32
			MAX-ACCESS read-only
			STATUS current
			DESCRIPTION
				"The sent inform to server.
				"
			::= { sleV2Dhcp4RelayIntrStatsEntry 18 }

		
		-- 1.3.6.1.4.1.6296.102.6.2.7.3.1.1.19
		sleV2Dhcp4RelayIntrSentDecline OBJECT-TYPE
			SYNTAX Counter32
			MAX-ACCESS read-only
			STATUS current
			DESCRIPTION
				"The sent decline to server.
				"
			::= { sleV2Dhcp4RelayIntrStatsEntry 19 }

		
		-- 1.3.6.1.4.1.6296.102.6.2.7.3.1.1.20
		sleV2Dhcp4RelayIntrRcvdOffer OBJECT-TYPE
			SYNTAX Counter32
			MAX-ACCESS read-only
			STATUS current
			DESCRIPTION
				"The received offer from server
				"
			::= { sleV2Dhcp4RelayIntrStatsEntry 20 }

		
		-- 1.3.6.1.4.1.6296.102.6.2.7.3.1.1.21
		sleV2Dhcp4RelayIntrRcvdAck OBJECT-TYPE
			SYNTAX Counter32
			MAX-ACCESS read-only
			STATUS current
			DESCRIPTION
				"The received ack from server
				"
			::= { sleV2Dhcp4RelayIntrStatsEntry 21 }

		
		-- 1.3.6.1.4.1.6296.102.6.2.7.3.1.1.22
		sleV2Dhcp4RelayIntrRcvdNack OBJECT-TYPE
			SYNTAX Counter32
			MAX-ACCESS read-only
			STATUS current
			DESCRIPTION
				"The received nak from server
				"
			::= { sleV2Dhcp4RelayIntrStatsEntry 22 }

		
		-- 1.3.6.1.4.1.6296.102.6.2.7.3.1.1.23
		sleV2Dhcp4RelayIntrSentOffer OBJECT-TYPE
			SYNTAX Counter32
			MAX-ACCESS read-only
			STATUS current
			DESCRIPTION
				"The sent offer to client
				"
			::= { sleV2Dhcp4RelayIntrStatsEntry 23 }

		
		-- 1.3.6.1.4.1.6296.102.6.2.7.3.1.1.24
		sleV2Dhcp4RelayIntrSentAck OBJECT-TYPE
			SYNTAX Counter32
			MAX-ACCESS read-only
			STATUS current
			DESCRIPTION
				"The sent ack to client
				"
			::= { sleV2Dhcp4RelayIntrStatsEntry 24 }

		
		-- 1.3.6.1.4.1.6296.102.6.2.7.3.1.1.25
		sleV2Dhcp4RelayIntrSentNack OBJECT-TYPE
			SYNTAX Counter32
			MAX-ACCESS read-only
			STATUS current
			DESCRIPTION
				"The sent nack to client
				"
			::= { sleV2Dhcp4RelayIntrStatsEntry 25 }

		
		-- 1.3.6.1.4.1.6296.102.6.2.7.3.2
		sleV2Dhcp4RelayIntrStatsControl OBJECT IDENTIFIER ::= { sleV2Dhcp4RelayStats 2 }

		
		-- 1.3.6.1.4.1.6296.102.6.2.7.3.2.1
		sleV2Dhcp4RelayIntrStatsControlRequest OBJECT-TYPE
			SYNTAX INTEGER { clearRelayStats(1) }
			MAX-ACCESS read-write
			STATUS current
			DESCRIPTION
				"Description."
			::= { sleV2Dhcp4RelayIntrStatsControl 1 }

		
		-- 1.3.6.1.4.1.6296.102.6.2.7.3.2.2
		sleV2Dhcp4RelayIntrStatsControlStatus OBJECT-TYPE
			SYNTAX SleControlStatusType
			MAX-ACCESS read-only
			STATUS current
			DESCRIPTION
				"Description."
			::= { sleV2Dhcp4RelayIntrStatsControl 2 }

		
		-- 1.3.6.1.4.1.6296.102.6.2.7.3.2.3
		sleV2Dhcp4RelayIntrStatsControlTimer OBJECT-TYPE
			SYNTAX Gauge32
			MAX-ACCESS read-write
			STATUS current
			DESCRIPTION
				"Description."
			::= { sleV2Dhcp4RelayIntrStatsControl 3 }

		
		-- 1.3.6.1.4.1.6296.102.6.2.7.3.2.4
		sleV2Dhcp4RelayIntrStatsControITimeStamp OBJECT-TYPE
			SYNTAX TimeTicks
			MAX-ACCESS read-only
			STATUS current
			DESCRIPTION
				"Description."
			::= { sleV2Dhcp4RelayIntrStatsControl 4 }

		
		-- 1.3.6.1.4.1.6296.102.6.2.7.3.2.5
		sleV2Dhcp4RelayIntrStatsControIResult OBJECT-TYPE
			SYNTAX SleControlRequestResultType
			MAX-ACCESS read-only
			STATUS current
			DESCRIPTION
				"Description."
			::= { sleV2Dhcp4RelayIntrStatsControl 5 }

		
		-- 1.3.6.1.4.1.6296.102.6.2.7.3.2.6
		sleV2Dhcp4RelayIntrStatsControIndex OBJECT-TYPE
			SYNTAX Integer32
			MAX-ACCESS read-write
			STATUS current
			DESCRIPTION
				"Description."
			::= { sleV2Dhcp4RelayIntrStatsControl 6 }

		
		-- 1.3.6.1.4.1.6296.102.6.2.7.3.3
		sleV2Dhcp4RelayIntrStatsNotification OBJECT IDENTIFIER ::= { sleV2Dhcp4RelayStats 3 }

		
		-- 1.3.6.1.4.1.6296.102.6.2.7.3.3.1
		sleV2Dhcp4RelayintrStatsCleared NOTIFICATION-TYPE
			OBJECTS { sleV2Dhcp4RelayIntrStatsControlRequest, sleV2Dhcp4RelayIntrStatsControITimeStamp, sleV2Dhcp4RelayIntrStatsControIResult, sleV2Dhcp4RelayIntrStatsControIndex }
			STATUS current
			DESCRIPTION 
				"Description."
			::= { sleV2Dhcp4RelayIntrStatsNotification 1 }

		
		-- 1.3.6.1.4.1.6296.102.6.2.8
		sleV2Dhcp4Client OBJECT IDENTIFIER ::= { sleV2Dhcp4 8 }

		
		-- 1.3.6.1.4.1.6296.102.6.2.8.1
		sleV2Dhcp4ClientInterface OBJECT IDENTIFIER ::= { sleV2Dhcp4Client 1 }

		
		-- 1.3.6.1.4.1.6296.102.6.2.8.1.1
		sleV2Dhcp4ClientIfTable OBJECT-TYPE
			SYNTAX SEQUENCE OF SleV2Dhcp4ClientIfEntry
			MAX-ACCESS not-accessible
			STATUS current
			DESCRIPTION
				"Description."
			::= { sleV2Dhcp4ClientInterface 1 }

		
		-- 1.3.6.1.4.1.6296.102.6.2.8.1.1.1
		sleV2Dhcp4ClientIfEntry OBJECT-TYPE
			SYNTAX SleV2Dhcp4ClientIfEntry
			MAX-ACCESS not-accessible
			STATUS current
			DESCRIPTION
				"Description."
			INDEX { sleV2Dhcp4ClientIfIndex }
			::= { sleV2Dhcp4ClientIfTable 1 }

		
		SleV2Dhcp4ClientIfEntry ::=
			SEQUENCE { 
				sleV2Dhcp4ClientIfIndex
					INTEGER,
				sleV2Dhcp4ClientIfActivity
					INTEGER,
				sleV2Dhcp4ClientIfAddress
					IpAddress,
				sleV2Dhcp4ClientIfMask
					IpAddress,
				sleV2Dhcp4ClientIfServer
					IpAddress,
				sleV2Dhcp4ClientIfHostName
					OCTET STRING,
				sleV2Dhcp4ClientIfRequestFlag
					BITS,
				sleV2Dhcp4ClientIfClientType
					INTEGER,
				sleV2Dhcp4ClientIfClientId
					OCTET STRING,
				sleV2Dhcp4ClientIfClassType
					INTEGER,
				sleV2Dhcp4ClientIfClassId
					OCTET STRING,
				sleV2Dhcp4ClientIfLeasetime
					INTEGER,
				sleV2Dhcp4ClientIfExpired
					Unsigned32,
				sleV2Dhcp4ClientIfState
					INTEGER,
				sleV2Dhcp4ClientIfLeasetimeOption
					INTEGER
			 }

		-- 1.3.6.1.4.1.6296.102.6.2.8.1.1.1.1
		sleV2Dhcp4ClientIfIndex OBJECT-TYPE
			SYNTAX INTEGER (1..4094)
			MAX-ACCESS read-only
			STATUS current
			DESCRIPTION
				"Description."
			::= { sleV2Dhcp4ClientIfEntry 1 }

		
		-- 1.3.6.1.4.1.6296.102.6.2.8.1.1.1.2
		sleV2Dhcp4ClientIfActivity OBJECT-TYPE
			SYNTAX INTEGER
				{
				disable(0),
				enable(1)
				}
			MAX-ACCESS read-only
			STATUS current
			DESCRIPTION
				"Description."
			DEFVAL { disable }
			::= { sleV2Dhcp4ClientIfEntry 2 }

		
		-- 1.3.6.1.4.1.6296.102.6.2.8.1.1.1.3
		sleV2Dhcp4ClientIfAddress OBJECT-TYPE
			SYNTAX IpAddress
			MAX-ACCESS read-only
			STATUS current
			DESCRIPTION
				"The IP address acquired by DHCP Client active in this interface."
			::= { sleV2Dhcp4ClientIfEntry 3 }

		
		-- 1.3.6.1.4.1.6296.102.6.2.8.1.1.1.4
		sleV2Dhcp4ClientIfMask OBJECT-TYPE
			SYNTAX IpAddress
			MAX-ACCESS read-only
			STATUS current
			DESCRIPTION
				"The subnet mask associated with the IP address acquired by DHCP Client.  
				The value of the mask is an IP address with all the network 
				bits set to 1 and all the hosts bits set to 0."
			::= { sleV2Dhcp4ClientIfEntry 4 }

		
		-- 1.3.6.1.4.1.6296.102.6.2.8.1.1.1.5
		sleV2Dhcp4ClientIfServer OBJECT-TYPE
			SYNTAX IpAddress
			MAX-ACCESS read-only
			STATUS current
			DESCRIPTION
				"DHCP Server's IP address."
			::= { sleV2Dhcp4ClientIfEntry 5 }

		
		-- 1.3.6.1.4.1.6296.102.6.2.8.1.1.1.6
		sleV2Dhcp4ClientIfHostName OBJECT-TYPE
			SYNTAX OCTET STRING (SIZE (0 | 1..64))
			MAX-ACCESS read-only
			STATUS current
			DESCRIPTION
				"Description."
			::= { sleV2Dhcp4ClientIfEntry 6 }

		
		-- 1.3.6.1.4.1.6296.102.6.2.8.1.1.1.7
		sleV2Dhcp4ClientIfRequestFlag OBJECT-TYPE
			SYNTAX BITS
				{
				unused0(0),
				subnetMask(1),
				timeOffset(2),
				router(3),
				timeServer(4),
				nameServer(5),
				domainNameServer(6),
				logServer(7),
				cookieServer(8),
				lprServer(9),
				impressServer(10),
				resourceLocationServer(11),
				hostName(12),
				bootFileSize(13),
				meritFile(14),
				domainName(15),
				swapServer(16),
				rootPath(17),
				extensionsPath(18),
				ipForwardState(19),
				nonLocalSourceRoutingState(20),
				policyFilter(21),
				maximumDatagramReassemblySize(22),
				defaultIpTimeToLive(23),
				pathMtuAgingTimeout(24),
				pathMtuPlateauTable(25),
				interfaceMtu(26),
				allSubnetsAreLocal(27),
				broadcastAddress(28),
				performMaskDiscovery(29),
				maskSupplier(30),
				performRouterDiscovery(31),
				routerSolicitationAddress(32),
				staticRoute(33),
				trailerEncapsulation(34),
				arpCacheTimeout(35),
				ethernetEncapsulationOption(36),
				tcpDefaultTtl(37),
				tcpKeepaliveInterval(38),
				tcpKeepaliveGarbage(39),
				nisDomain(40),
				nisServers(41),
				networkTimeProtocolServers(42),
				vendorSpecificInformation(43),
				netbiosOverTcpIpNameServer(44),
				netbiosOverTcpIpDatagramDistributionServer(45),
				netbiosOverTcpIpNodeType(46),
				netbiosOverTcpIpScope(47),
				xWindowSystemFontServer(48),
				xWindowSystemDisplayManager(49),
				requestedIpAddress(50),
				ipAddressLeaseTime(51),
				optionOverload(52),
				dhcpMessageType(53),
				serverIdentifier(54),
				unused55(55),
				message(56),
				maximumDhcpMessageSize(57),
				renewalTimeValue(58),
				rebindingTimeValue(59),
				vendorClassIdentifier(60),
				clientIdentifier(61),
				undefined62(62),
				undefined63(63),
				nisPlusDomain(64),
				nisPlusServers(65),
				tftpServerName(66),
				bootFileName(67),
				mobileIpHomeAgent(68),
				smtpServer(69),
				pop3Server(70),
				nntpServer(71),
				wwwServer(72),
				defaultFingerServer(73),
				ircServer(74),
				streetTalkServer(75),
				stdaServer(76)
				}
			MAX-ACCESS read-only
			STATUS current
			DESCRIPTION
				"Description."
			::= { sleV2Dhcp4ClientIfEntry 7 }

		
		-- 1.3.6.1.4.1.6296.102.6.2.8.1.1.1.8
		sleV2Dhcp4ClientIfClientType OBJECT-TYPE
			SYNTAX INTEGER
				{
				text(0),
				hex(1)
				}
			MAX-ACCESS read-only
			STATUS current
			DESCRIPTION
				"DHCP Client-identifier input style.
				0 : text(ascii) string format
				1 : hexadecimal format"
			DEFVAL { text }
			::= { sleV2Dhcp4ClientIfEntry 8 }

		
		-- 1.3.6.1.4.1.6296.102.6.2.8.1.1.1.9
		sleV2Dhcp4ClientIfClientId OBJECT-TYPE
			SYNTAX OCTET STRING (SIZE (0 | 1..64))
			MAX-ACCESS read-only
			STATUS current
			DESCRIPTION
				"DHCP Client-identifier value.
				This is used by DHCP clients to specify their unique identifier.
				DHCP servers use this value to index their database of address bindings.
				This value is expected to be unique for all clients in an administrative domain."
			::= { sleV2Dhcp4ClientIfEntry 9 }

		
		-- 1.3.6.1.4.1.6296.102.6.2.8.1.1.1.10
		sleV2Dhcp4ClientIfClassType OBJECT-TYPE
			SYNTAX INTEGER
				{
				text(0),
				hex(1)
				}
			MAX-ACCESS read-only
			STATUS current
			DESCRIPTION
				"DHCP Class identifier input style.
				0 : text(ascii) string format
				1 : hexadecimal format"
			DEFVAL { text }
			::= { sleV2Dhcp4ClientIfEntry 10 }

		
		-- 1.3.6.1.4.1.6296.102.6.2.8.1.1.1.11
		sleV2Dhcp4ClientIfClassId OBJECT-TYPE
			SYNTAX OCTET STRING (SIZE (0 | 1..64))
			MAX-ACCESS read-only
			STATUS current
			DESCRIPTION
				"DHCP Class identifier value.
				This is used by DHCP clients to optionally identify the vendor 
				type and configuration of a DHCP client.
				The information is a string of n octets, interpreted by servers.
				Vendors may choose to define specific vendor class identifiers 
				to convey particular configuration or other identification 
				information about a client.
				For example, the identifier may encode the client's hardware configuration."
			::= { sleV2Dhcp4ClientIfEntry 11 }

		
		-- 1.3.6.1.4.1.6296.102.6.2.8.1.1.1.12
		sleV2Dhcp4ClientIfLeasetime OBJECT-TYPE
			SYNTAX INTEGER (120..2147483637)
			UNITS "second"
			MAX-ACCESS read-only
			STATUS current
			DESCRIPTION
				"The leased time for IP address acquired by DHCP Client.
				Default lease-time: 3600s"
			DEFVAL { 3600 }
			::= { sleV2Dhcp4ClientIfEntry 12 }

		
		-- 1.3.6.1.4.1.6296.102.6.2.8.1.1.1.13
		sleV2Dhcp4ClientIfExpired OBJECT-TYPE
			SYNTAX Unsigned32
			UNITS "second"
			MAX-ACCESS read-only
			STATUS current
			DESCRIPTION
				"Description."
			::= { sleV2Dhcp4ClientIfEntry 13 }

		
		-- 1.3.6.1.4.1.6296.102.6.2.8.1.1.1.14
		sleV2Dhcp4ClientIfState OBJECT-TYPE
			SYNTAX INTEGER
				{
				halt(0),
				init(1),
				request(3),
				bound(4),
				renew(5),
				rebind(6),
				nonactive(255)
				}
			MAX-ACCESS read-only
			STATUS current
			DESCRIPTION
				"The operating status of DHCP Client."
			DEFVAL { non-active }
			::= { sleV2Dhcp4ClientIfEntry 14 }

		
		-- 1.3.6.1.4.1.6296.102.6.2.8.1.1.1.15
		sleV2Dhcp4ClientIfLeasetimeOption OBJECT-TYPE
			SYNTAX INTEGER
				{
				notUsed(0),
				used(1)
				}
			MAX-ACCESS read-only
			STATUS current
			DESCRIPTION
				"The operating status of DHCP Client."
			DEFVAL { notUsed }
			::= { sleV2Dhcp4ClientIfEntry 15 }

		
		-- 1.3.6.1.4.1.6296.102.6.2.8.1.2
		sleV2Dhcp4ClientIfControl OBJECT IDENTIFIER ::= { sleV2Dhcp4ClientInterface 2 }

		
		-- 1.3.6.1.4.1.6296.102.6.2.8.1.2.1
		sleV2Dhcp4ClientIfControlRequest OBJECT-TYPE
			SYNTAX INTEGER
				{
				setDhcpClientActivity(1),
				setDhcpClientProfile(2),
				renewDhcpClientAddress(3),
				releaseDhcpClientAddress(4),
				setDhcpClientLeasetimeOption(5)
				}
			MAX-ACCESS read-write
			STATUS current
			DESCRIPTION
				"The request of a user command."
			::= { sleV2Dhcp4ClientIfControl 1 }

		
		-- 1.3.6.1.4.1.6296.102.6.2.8.1.2.2
		sleV2Dhcp4ClientIfControlStatus OBJECT-TYPE
			SYNTAX SleControlStatusType
			MAX-ACCESS read-only
			STATUS current
			DESCRIPTION
				"The status of a user command."
			::= { sleV2Dhcp4ClientIfControl 2 }

		
		-- 1.3.6.1.4.1.6296.102.6.2.8.1.2.3
		sleV2Dhcp4ClientIfControlTimer OBJECT-TYPE
			SYNTAX Gauge32
			MAX-ACCESS read-write
			STATUS current
			DESCRIPTION
				"The maximum wait time for the manager for a long running user command."
			::= { sleV2Dhcp4ClientIfControl 3 }

		
		-- 1.3.6.1.4.1.6296.102.6.2.8.1.2.4
		sleV2Dhcp4ClientIfControlTimeStamp OBJECT-TYPE
			SYNTAX TimeTicks
			MAX-ACCESS read-only
			STATUS current
			DESCRIPTION
				"The time stamp of the last command (end of command)."
			::= { sleV2Dhcp4ClientIfControl 4 }

		
		-- 1.3.6.1.4.1.6296.102.6.2.8.1.2.5
		sleV2Dhcp4ClientIfControlReqResult OBJECT-TYPE
			SYNTAX SleControlRequestResultType
			MAX-ACCESS read-only
			STATUS current
			DESCRIPTION
				"The result of the last user command."
			::= { sleV2Dhcp4ClientIfControl 5 }

		
		-- 1.3.6.1.4.1.6296.102.6.2.8.1.2.6
		sleV2Dhcp4ClientIfControlIndex OBJECT-TYPE
			SYNTAX INTEGER (1..4094)
			MAX-ACCESS read-write
			STATUS current
			DESCRIPTION
				"Network Interface Index."
			::= { sleV2Dhcp4ClientIfControl 6 }

		
		-- 1.3.6.1.4.1.6296.102.6.2.8.1.2.7
		sleV2Dhcp4ClientIfControlActivity OBJECT-TYPE
			SYNTAX INTEGER
				{
				disable(0),
				enable(1)
				}
			MAX-ACCESS read-write
			STATUS current
			DESCRIPTION
				"Network Interface Index."
			::= { sleV2Dhcp4ClientIfControl 7 }

		
		-- 1.3.6.1.4.1.6296.102.6.2.8.1.2.8
		sleV2Dhcp4ClientIfControlHostName OBJECT-TYPE
			SYNTAX OCTET STRING (SIZE (0 | 1..64))
			MAX-ACCESS read-write
			STATUS current
			DESCRIPTION
				"Description."
			::= { sleV2Dhcp4ClientIfControl 8 }

		
		-- 1.3.6.1.4.1.6296.102.6.2.8.1.2.9
		sleV2Dhcp4ClientIfControlRequestFlag OBJECT-TYPE
			SYNTAX BITS
				{
				unused0(0),
				subnetMask(1),
				timeOffset(2),
				router(3),
				timeServer(4),
				nameServer(5),
				domainNameServer(6),
				logServer(7),
				cookieServer(8),
				lprServer(9),
				impressServer(10),
				resourceLocationServer(11),
				hostName(12),
				bootFileSize(13),
				meritFile(14),
				domainName(15),
				swapServer(16),
				rootPath(17),
				extensionsPath(18),
				ipForwardState(19),
				nonLocalSourceRoutingState(20),
				policyFilter(21),
				maximumDatagramReassemblySize(22),
				defaultIpTimeToLive(23),
				pathMtuAgingTimeout(24),
				pathMtuPlateauTable(25),
				interfaceMtu(26),
				allSubnetsAreLocal(27),
				broadcastAddress(28),
				performMaskDiscovery(29),
				maskSupplier(30),
				performRouterDiscovery(31),
				routerSolicitationAddress(32),
				staticRoute(33),
				trailerEncapsulation(34),
				arpCacheTimeout(35),
				ethernetEncapsulationOption(36),
				tcpDefaultTtl(37),
				tcpKeepaliveInterval(38),
				tcpKeepaliveGarbage(39),
				nisDomain(40),
				nisServers(41),
				networkTimeProtocolServers(42),
				vendorSpecificInformation(43),
				netbiosOverTcpIpNameServer(44),
				netbiosOverTcpIpDatagramDistributionServer(45),
				netbiosOverTcpIpNodeType(46),
				netbiosOverTcpIpScope(47),
				xWindowSystemFontServer(48),
				xWindowSystemDisplayManager(49),
				requestedIpAddress(50),
				ipAddressLeaseTime(51),
				optionOverload(52),
				dhcpMessageType(53),
				serverIdentifier(54),
				unused55(55),
				message(56),
				maximumDhcpMessageSize(57),
				renewalTimeValue(58),
				rebindingTimeValue(59),
				vendorClassIdentifier(60),
				clientIdentifier(61),
				undefined62(62),
				undefined63(63),
				nisPlusDomain(64),
				nisPlusServers(65),
				tftpServerName(66),
				bootFileName(67),
				mobileIpHomeAgent(68),
				smtpServer(69),
				pop3Server(70),
				nntpServer(71),
				wwwServer(72),
				defaultFingerServer(73),
				ircServer(74),
				streetTalkServer(75),
				stdaServer(76)
				}
			MAX-ACCESS read-write
			STATUS current
			DESCRIPTION
				"Description."
			::= { sleV2Dhcp4ClientIfControl 9 }

		
		-- 1.3.6.1.4.1.6296.102.6.2.8.1.2.10
		sleV2Dhcp4ClientIfControlClientType OBJECT-TYPE
			SYNTAX INTEGER
				{
				text(0),
				hex(1)
				}
			MAX-ACCESS read-write
			STATUS current
			DESCRIPTION
				"DHCP Client-identifier input style.
				0 : text(ascii) string format
				1 : hexadecimal format"
			DEFVAL { text }
			::= { sleV2Dhcp4ClientIfControl 10 }

		
		-- 1.3.6.1.4.1.6296.102.6.2.8.1.2.11
		sleV2Dhcp4ClientIfControlClientId OBJECT-TYPE
			SYNTAX OCTET STRING (SIZE (0 | 1..64))
			MAX-ACCESS read-write
			STATUS current
			DESCRIPTION
				"DHCP Client-identifier value.
				This is used by DHCP clients to specify their unique identifier.
				DHCP servers use this value to index their database of address bindings.
				This value is expected to be unique for all clients in an administrative domain."
			::= { sleV2Dhcp4ClientIfControl 11 }

		
		-- 1.3.6.1.4.1.6296.102.6.2.8.1.2.12
		sleV2Dhcp4ClientIfControlClassType OBJECT-TYPE
			SYNTAX INTEGER
				{
				text(0),
				hex(1)
				}
			MAX-ACCESS read-write
			STATUS current
			DESCRIPTION
				"DHCP Class identifier input style.
				0 : text(ascii) string format
				1 : hexadecimal format"
			DEFVAL { text }
			::= { sleV2Dhcp4ClientIfControl 12 }

		
		-- 1.3.6.1.4.1.6296.102.6.2.8.1.2.13
		sleV2Dhcp4ClientIfControlClassId OBJECT-TYPE
			SYNTAX OCTET STRING (SIZE (0 | 1..64))
			MAX-ACCESS read-write
			STATUS current
			DESCRIPTION
				"DHCP Class identifier value.
				This is used by DHCP clients to optionally identify the vendor 
				type and configuration of a DHCP client.
				The information is a string of n octets, interpreted by servers.
				Vendors may choose to define specific vendor class identifiers 
				to convey particular configuration or other identification 
				information about a client.
				For example, the identifier may encode the client's hardware configuration."
			::= { sleV2Dhcp4ClientIfControl 13 }

		
		-- 1.3.6.1.4.1.6296.102.6.2.8.1.2.14
		sleV2Dhcp4ClientIfControlLeasetime OBJECT-TYPE
			SYNTAX INTEGER (120..2147483637)
			MAX-ACCESS read-write
			STATUS current
			DESCRIPTION
				"The leased time for IP address acquired by DHCP Client.
				Default lease-time: 3600s"
			::= { sleV2Dhcp4ClientIfControl 14 }

		
		-- 1.3.6.1.4.1.6296.102.6.2.8.1.2.15
		sleV2Dhcp4ClientIfControlLeasetimeOption OBJECT-TYPE
			SYNTAX INTEGER
				{
				notUsed(0),
				used(1)
				}
			MAX-ACCESS read-write
			STATUS current
			DESCRIPTION
				"The leased time for IP address acquired by DHCP Client.
				Default lease-time: 3600s"
			::= { sleV2Dhcp4ClientIfControl 15 }

		
		-- 1.3.6.1.4.1.6296.102.6.2.8.1.3
		sleV2Dhcp4ClientIfNotification OBJECT IDENTIFIER ::= { sleV2Dhcp4ClientInterface 3 }

		
		-- 1.3.6.1.4.1.6296.102.6.2.8.1.3.1
		sleV2Dhcp4ClientIfActivityChanged NOTIFICATION-TYPE
			OBJECTS { sleV2Dhcp4ClientIfControlRequest, sleV2Dhcp4ClientIfControlTimeStamp, sleV2Dhcp4ClientIfControlReqResult, sleV2Dhcp4ClientIfActivity }
			STATUS current
			DESCRIPTION 
				"Description."
			::= { sleV2Dhcp4ClientIfNotification 1 }

		
		-- 1.3.6.1.4.1.6296.102.6.2.8.1.3.2
		sleV2Dhcp4ClientIfProfileChanged NOTIFICATION-TYPE
			OBJECTS { sleV2Dhcp4ClientIfControlRequest, sleV2Dhcp4ClientIfControlTimeStamp, sleV2Dhcp4ClientIfControlReqResult, sleV2Dhcp4ClientIfHostName, sleV2Dhcp4ClientIfRequestFlag, 
				sleV2Dhcp4ClientIfClientType, sleV2Dhcp4ClientIfClientId, sleV2Dhcp4ClientIfClassType, sleV2Dhcp4ClientIfClassId, sleV2Dhcp4ClientIfLeasetime
				 }
			STATUS current
			DESCRIPTION 
				"Description."
			::= { sleV2Dhcp4ClientIfNotification 2 }

		
		-- 1.3.6.1.4.1.6296.102.6.2.8.1.3.3
		sleV2Dhcp4ClientIfRenewed NOTIFICATION-TYPE
			OBJECTS { sleV2Dhcp4ClientIfControlRequest, sleV2Dhcp4ClientIfControlTimeStamp, sleV2Dhcp4ClientIfControlReqResult, sleV2Dhcp4ClientIfControlIndex }
			STATUS current
			DESCRIPTION 
				"Description."
			::= { sleV2Dhcp4ClientIfNotification 3 }

		
		-- 1.3.6.1.4.1.6296.102.6.2.8.1.3.4
		sleV2Dhcp4ClientIfReleased NOTIFICATION-TYPE
			OBJECTS { sleV2Dhcp4ClientIfControlRequest, sleV2Dhcp4ClientIfControlTimeStamp, sleV2Dhcp4ClientIfControlReqResult, sleV2Dhcp4ClientIfControlIndex }
			STATUS current
			DESCRIPTION 
				"Description."
			::= { sleV2Dhcp4ClientIfNotification 4 }

		
		-- 1.3.6.1.4.1.6296.102.6.2.8.1.3.5
		sleV2Dhcp4ClientIfLeasetimeOptionChanged NOTIFICATION-TYPE
			OBJECTS { sleV2Dhcp4ClientIfControlRequest, sleV2Dhcp4ClientIfControlTimeStamp, sleV2Dhcp4ClientIfControlReqResult, sleV2Dhcp4ClientIfControlIndex }
			STATUS current
			DESCRIPTION 
				"Description."
			::= { sleV2Dhcp4ClientIfNotification 5 }

		
		-- 1.3.6.1.4.1.6296.102.6.2.8.2
		sleV2Dhcp4ClientOption OBJECT IDENTIFIER ::= { sleV2Dhcp4Client 2 }

		
		-- 1.3.6.1.4.1.6296.102.6.2.8.2.1
		sleV2Dhcp4ClientOptionTable OBJECT-TYPE
			SYNTAX SEQUENCE OF SleV2Dhcp4ClientOptionEntry
			MAX-ACCESS not-accessible
			STATUS current
			DESCRIPTION
				"Description."
			::= { sleV2Dhcp4ClientOption 1 }

		
		-- 1.3.6.1.4.1.6296.102.6.2.8.2.1.1
		sleV2Dhcp4ClientOptionEntry OBJECT-TYPE
			SYNTAX SleV2Dhcp4ClientOptionEntry
			MAX-ACCESS not-accessible
			STATUS current
			DESCRIPTION
				"Description."
			INDEX { sleV2Dhcp4ClientIfIndex, sleV2Dhcp4OptionCode, sleV2Dhcp4OptionInstance }
			::= { sleV2Dhcp4ClientOptionTable 1 }

		
		SleV2Dhcp4ClientOptionEntry ::=
			SEQUENCE { 
				sleV2Dhcp4ClientOptionCode
					INTEGER,
				sleV2Dhcp4ClientOptionInstance
					INTEGER,
				sleV2Dhcp4ClientOptionType
					INTEGER,
				sleV2Dhcp4ClientOptionValue
					OCTET STRING
			 }

		-- 1.3.6.1.4.1.6296.102.6.2.8.2.1.1.1
		sleV2Dhcp4ClientOptionCode OBJECT-TYPE
			SYNTAX INTEGER
				{
				subnetMask(1),
				timeOffset(2),
				router(3),
				timeServer(4),
				nameServer(5),
				domainNameServer(6),
				logServer(7),
				cookieServer(8),
				lprServer(9),
				impressServer(10),
				resourceLocationServer(11),
				hostName(12),
				bootFileSize(13),
				meritFile(14),
				domainName(15),
				swapServer(16),
				rootPath(17),
				extensionsPath(18),
				ipForwardState(19),
				nonLocalSourceRoutingState(20),
				policyFilter(21),
				maximumDatagramReassemblySize(22),
				defaultIpTimeToLive(23),
				pathMtuAgingTimeout(24),
				pathMtuPlateauTable(25),
				interfaceMtu(26),
				allSubnetsAreLocal(27),
				broadcastAddress(28),
				performMaskDiscovery(29),
				maskSupplier(30),
				performRouterDiscovery(31),
				routerSolicitationAddress(32),
				staticRoute(33),
				trailerEncapsulation(34),
				arpCacheTimeout(35),
				ethernetEncapsulationOption(36),
				tcpDefaultTtl(37),
				tcpKeepaliveInterval(38),
				tcpKeepaliveGarbage(39),
				nisDomain(40),
				nisServers(41),
				networkTimeProtocolServers(42),
				vendorSpecificInformation(43),
				netbiosOverTcpIpNameServer(44),
				netbiosOverTcpIpDatagramDistributionServer(45),
				netbiosOverTcpIpNodeType(46),
				netbiosOverTcpIpScope(47),
				xWindowSystemFontServer(48),
				xWindowSystemDisplayManager(49),
				requestedIpAddress(50),
				ipAddressLeaseTime(51),
				optionOverload(52),
				dhcpMessageType(53),
				serverIdentifier(54),
				parameterRequestList(55),
				message(56),
				maximumDhcpMessageSize(57),
				renewalTimeValue(58),
				rebindingTimeValue(59),
				vendorClassIdentifier(60),
				clientIdentifier(61),
				nisPlusDomain(64),
				nisPlusServers(65),
				tftpServerName(66),
				bootFileName(67),
				mobileIpHomeAgent(68),
				smtpServer(69),
				pop3Server(70),
				nntpServer(71),
				wwwServer(72),
				defaultFingerServer(73),
				ircServer(74),
				streetTalkServer(75),
				stdaServer(76)
				}
			MAX-ACCESS read-only
			STATUS current
			DESCRIPTION
				"3: default Gateway
				4: DNS Server"
			::= { sleV2Dhcp4ClientOptionEntry 1 }

		
		-- 1.3.6.1.4.1.6296.102.6.2.8.2.1.1.2
		sleV2Dhcp4ClientOptionInstance OBJECT-TYPE
			SYNTAX INTEGER (1..8)
			MAX-ACCESS read-only
			STATUS current
			DESCRIPTION
				"The IP address acquired by DHCP Client active in this interface."
			::= { sleV2Dhcp4ClientOptionEntry 2 }

		
		-- 1.3.6.1.4.1.6296.102.6.2.8.2.1.1.3
		sleV2Dhcp4ClientOptionType OBJECT-TYPE
			SYNTAX INTEGER
				{
				ipaddress(1),
				hex(2),
				text(3)
				}
			MAX-ACCESS read-only
			STATUS current
			DESCRIPTION
				"The subnet mask associated with the IP address acquired by DHCP Client.  
				The value of the mask is an IP address with all the network 
				bits set to 1 and all the hosts bits set to 0."
			::= { sleV2Dhcp4ClientOptionEntry 3 }

		
		-- 1.3.6.1.4.1.6296.102.6.2.8.2.1.1.4
		sleV2Dhcp4ClientOptionValue OBJECT-TYPE
			SYNTAX OCTET STRING (SIZE (1..64))
			MAX-ACCESS read-only
			STATUS current
			DESCRIPTION
				"The Gateway's IP address acquired by DHCP Client active in this interface."
			::= { sleV2Dhcp4ClientOptionEntry 4 }

		
		-- 1.3.6.1.4.1.6296.102.6.2.9
		sleV2Dhcp4Port OBJECT IDENTIFIER ::= { sleV2Dhcp4 9 }

		
		-- 1.3.6.1.4.1.6296.102.6.2.9.1
		sleV2Dhcp4PortLease OBJECT IDENTIFIER ::= { sleV2Dhcp4Port 1 }

		
		-- 1.3.6.1.4.1.6296.102.6.2.9.1.1
		sleV2Dhcp4PortLeaseTable OBJECT-TYPE
			SYNTAX SEQUENCE OF SleV2Dhcp4PortLeaseEntry
			MAX-ACCESS not-accessible
			STATUS current
			DESCRIPTION
				"Description."
			::= { sleV2Dhcp4PortLease 1 }

		
		-- 1.3.6.1.4.1.6296.102.6.2.9.1.1.1
		sleV2Dhcp4PortLeaseEntry OBJECT-TYPE
			SYNTAX SleV2Dhcp4PortLeaseEntry
			MAX-ACCESS not-accessible
			STATUS current
			DESCRIPTION
				"Description."
			INDEX { sleV2Dhcp4PortLeaseIndex }
			::= { sleV2Dhcp4PortLeaseTable 1 }

		
		SleV2Dhcp4PortLeaseEntry ::=
			SEQUENCE { 
				sleV2Dhcp4PortLeaseIndex
					InterfaceIndex,
				sleV2Dhcp4PortLeaseLimit
					INTEGER,
				sleV2Dhcp4PortLeaseCount
					Integer32
			 }

		-- 1.3.6.1.4.1.6296.102.6.2.9.1.1.1.1
		sleV2Dhcp4PortLeaseIndex OBJECT-TYPE
			SYNTAX InterfaceIndex
			MAX-ACCESS read-only
			STATUS current
			DESCRIPTION
				"Description."
			::= { sleV2Dhcp4PortLeaseEntry 1 }

		
		-- 1.3.6.1.4.1.6296.102.6.2.9.1.1.1.2
		sleV2Dhcp4PortLeaseLimit OBJECT-TYPE
			SYNTAX INTEGER (-1 | 1..256)
			MAX-ACCESS read-only
			STATUS current
			DESCRIPTION
				"Description."
			::= { sleV2Dhcp4PortLeaseEntry 2 }

		
		-- 1.3.6.1.4.1.6296.102.6.2.9.1.1.1.3
		sleV2Dhcp4PortLeaseCount OBJECT-TYPE
			SYNTAX Integer32
			MAX-ACCESS read-only
			STATUS current
			DESCRIPTION
				"Description."
			::= { sleV2Dhcp4PortLeaseEntry 3 }

		
		-- 1.3.6.1.4.1.6296.102.6.2.9.1.2
		sleV2Dhcp4PortAddrLeaseTable OBJECT-TYPE
			SYNTAX SEQUENCE OF SleV2Dhcp4PortAddrLeaseEntry
			MAX-ACCESS not-accessible
			STATUS current
			DESCRIPTION
				"Description."
			::= { sleV2Dhcp4PortLease 2 }

		
		-- 1.3.6.1.4.1.6296.102.6.2.9.1.2.1
		sleV2Dhcp4PortAddrLeaseEntry OBJECT-TYPE
			SYNTAX SleV2Dhcp4PortAddrLeaseEntry
			MAX-ACCESS not-accessible
			STATUS current
			DESCRIPTION
				"Description."
			INDEX { sleV2Dhcp4PortAddrtLeaseIndex, sleV2Dhcp4PortAddrLeaseAddress }
			::= { sleV2Dhcp4PortAddrLeaseTable 1 }

		
		SleV2Dhcp4PortAddrLeaseEntry ::=
			SEQUENCE { 
				sleV2Dhcp4PortAddrtLeaseIndex
					InterfaceIndex,
				sleV2Dhcp4PortAddrLeaseAddress
					IpAddress,
				sleV2Dhcp4PortAddrLeasePoolIndex
					INTEGER,
				sleV2Dhcp4PortAddrLeaseStatus
					INTEGER,
				sleV2Dhcp4PortAddrLeaseMac
					MacAddress,
				sleV2Dhcp4PortAddrLeaseHostName
					OCTET STRING,
				sleV2Dhcp4PortAddrLeaseClientId
					OCTET STRING,
				sleV2Dhcp4PortAddrLeaseRemoteId
					OCTET STRING,
				sleV2Dhcp4PortAddrLeaseCircuitId
					OCTET STRING,
				sleV2Dhcp4PortAddrLeaseStartTime
					Unsigned32,
				sleV2Dhcp4PortAddrLeaseFinishTime
					Unsigned32
			 }

		-- 1.3.6.1.4.1.6296.102.6.2.9.1.2.1.1
		sleV2Dhcp4PortAddrtLeaseIndex OBJECT-TYPE
			SYNTAX InterfaceIndex
			MAX-ACCESS read-write
			STATUS current
			DESCRIPTION
				"Description."
			::= { sleV2Dhcp4PortAddrLeaseEntry 1 }

		
		-- 1.3.6.1.4.1.6296.102.6.2.9.1.2.1.2
		sleV2Dhcp4PortAddrLeaseAddress OBJECT-TYPE
			SYNTAX IpAddress
			MAX-ACCESS read-only
			STATUS current
			DESCRIPTION
				"Description."
			::= { sleV2Dhcp4PortAddrLeaseEntry 2 }

		
		-- 1.3.6.1.4.1.6296.102.6.2.9.1.2.1.3
		sleV2Dhcp4PortAddrLeasePoolIndex OBJECT-TYPE
			SYNTAX INTEGER (1..255)
			MAX-ACCESS read-only
			STATUS current
			DESCRIPTION
				"Description."
			::= { sleV2Dhcp4PortAddrLeaseEntry 3 }

		
		-- 1.3.6.1.4.1.6296.102.6.2.9.1.2.1.4
		sleV2Dhcp4PortAddrLeaseStatus OBJECT-TYPE
			SYNTAX INTEGER
				{
				fixed(1),
				offered(2),
				bound(3),
				abandon(4),
				free(5)
				}
			MAX-ACCESS read-only
			STATUS current
			DESCRIPTION
				"Description."
			::= { sleV2Dhcp4PortAddrLeaseEntry 4 }

		
		-- 1.3.6.1.4.1.6296.102.6.2.9.1.2.1.5
		sleV2Dhcp4PortAddrLeaseMac OBJECT-TYPE
			SYNTAX MacAddress
			MAX-ACCESS read-only
			STATUS current
			DESCRIPTION
				"Description."
			::= { sleV2Dhcp4PortAddrLeaseEntry 5 }

		
		-- 1.3.6.1.4.1.6296.102.6.2.9.1.2.1.6
		sleV2Dhcp4PortAddrLeaseHostName OBJECT-TYPE
			SYNTAX OCTET STRING (SIZE (0 | 1..64))
			MAX-ACCESS read-write
			STATUS current
			DESCRIPTION
				"Description."
			::= { sleV2Dhcp4PortAddrLeaseEntry 6 }

		
		-- 1.3.6.1.4.1.6296.102.6.2.9.1.2.1.7
		sleV2Dhcp4PortAddrLeaseClientId OBJECT-TYPE
			SYNTAX OCTET STRING (SIZE (0 | 1..64))
			MAX-ACCESS read-only
			STATUS current
			DESCRIPTION
				"Description."
			::= { sleV2Dhcp4PortAddrLeaseEntry 7 }

		
		-- 1.3.6.1.4.1.6296.102.6.2.9.1.2.1.8
		sleV2Dhcp4PortAddrLeaseRemoteId OBJECT-TYPE
			SYNTAX OCTET STRING (SIZE (0 | 1..32))
			MAX-ACCESS read-only
			STATUS current
			DESCRIPTION
				"Description."
			::= { sleV2Dhcp4PortAddrLeaseEntry 8 }

		
		-- 1.3.6.1.4.1.6296.102.6.2.9.1.2.1.9
		sleV2Dhcp4PortAddrLeaseCircuitId OBJECT-TYPE
			SYNTAX OCTET STRING (SIZE (0 | 1..32))
			MAX-ACCESS read-only
			STATUS current
			DESCRIPTION
				"Description."
			::= { sleV2Dhcp4PortAddrLeaseEntry 9 }

		
		-- 1.3.6.1.4.1.6296.102.6.2.9.1.2.1.10
		sleV2Dhcp4PortAddrLeaseStartTime OBJECT-TYPE
			SYNTAX Unsigned32
			MAX-ACCESS read-only
			STATUS current
			DESCRIPTION
				"Description."
			::= { sleV2Dhcp4PortAddrLeaseEntry 10 }

		
		-- 1.3.6.1.4.1.6296.102.6.2.9.1.2.1.11
		sleV2Dhcp4PortAddrLeaseFinishTime OBJECT-TYPE
			SYNTAX Unsigned32
			MAX-ACCESS read-only
			STATUS current
			DESCRIPTION
				"Description."
			::= { sleV2Dhcp4PortAddrLeaseEntry 11 }

		
		-- 1.3.6.1.4.1.6296.102.6.2.9.1.3
		sleV2Dhcp4PortLeaseControl OBJECT IDENTIFIER ::= { sleV2Dhcp4PortLease 3 }

		
		-- 1.3.6.1.4.1.6296.102.6.2.9.1.3.1
		sleV2Dhcp4PortLeaseControlRequest OBJECT-TYPE
			SYNTAX INTEGER { setDhcp4PortLeaseLimit(1) }
			MAX-ACCESS read-write
			STATUS current
			DESCRIPTION
				"Description."
			::= { sleV2Dhcp4PortLeaseControl 1 }

		
		-- 1.3.6.1.4.1.6296.102.6.2.9.1.3.2
		sleV2Dhcp4PortLeaseControlStatus OBJECT-TYPE
			SYNTAX SleControlStatusType
			MAX-ACCESS read-only
			STATUS current
			DESCRIPTION
				"Description."
			::= { sleV2Dhcp4PortLeaseControl 2 }

		
		-- 1.3.6.1.4.1.6296.102.6.2.9.1.3.3
		sleV2Dhcp4PortLeaseControlTimer OBJECT-TYPE
			SYNTAX Gauge32
			MAX-ACCESS read-write
			STATUS current
			DESCRIPTION
				"Description."
			::= { sleV2Dhcp4PortLeaseControl 3 }

		
		-- 1.3.6.1.4.1.6296.102.6.2.9.1.3.4
		sleV2Dhcp4PortLeaseControlTimeStamp OBJECT-TYPE
			SYNTAX TimeTicks
			MAX-ACCESS read-only
			STATUS current
			DESCRIPTION
				"Description."
			::= { sleV2Dhcp4PortLeaseControl 4 }

		
		-- 1.3.6.1.4.1.6296.102.6.2.9.1.3.5
		sleV2Dhcp4PortLeaseControlReqResult OBJECT-TYPE
			SYNTAX SleControlRequestResultType
			MAX-ACCESS read-only
			STATUS current
			DESCRIPTION
				"Description."
			::= { sleV2Dhcp4PortLeaseControl 5 }

		
		-- 1.3.6.1.4.1.6296.102.6.2.9.1.3.6
		sleV2Dhcp4PortLeaseControlIndex OBJECT-TYPE
			SYNTAX InterfaceIndex
			MAX-ACCESS read-write
			STATUS current
			DESCRIPTION
				"Description."
			::= { sleV2Dhcp4PortLeaseControl 6 }

		
		-- 1.3.6.1.4.1.6296.102.6.2.9.1.3.7
		sleV2Dhcp4PortLeaseControlLimit OBJECT-TYPE
			SYNTAX INTEGER (-1 | 1..256)
			MAX-ACCESS read-write
			STATUS current
			DESCRIPTION
				"Description."
			::= { sleV2Dhcp4PortLeaseControl 7 }

		
		-- 1.3.6.1.4.1.6296.102.6.2.9.1.4
		sleV2DhcpPortLeaseNotification OBJECT IDENTIFIER ::= { sleV2Dhcp4PortLease 4 }

		
		-- 1.3.6.1.4.1.6296.102.6.2.9.1.4.1
		sleV2Dhcp4PortLeaseLimitChanged NOTIFICATION-TYPE
			OBJECTS { sleV2Dhcp4PortLeaseControlRequest, sleV2Dhcp4PortLeaseControlTimeStamp, sleV2Dhcp4PortLeaseControlReqResult, sleV2Dhcp4PortLeaseLimit }
			STATUS current
			DESCRIPTION 
				"Description."
			::= { sleV2DhcpPortLeaseNotification 1 }

		
		-- 1.3.6.1.4.1.6296.102.6.3
		sleV2Dhcp6 OBJECT IDENTIFIER ::= { sleV2Dhcp 3 }

		
		-- 1.3.6.1.4.1.6296.102.6.4
		sleV2DhcpGroup OBJECT-GROUP
			OBJECTS { sleV2Dhcp4ClassRangeStart, sleV2Dhcp4ClassRangeEnd, sleV2Dhcp4ClassRangeControlRequest, sleV2Dhcp4ClassRangeControlStatus, sleV2Dhcp4ClassRangeControlTimer, 
				sleV2Dhcp4ClassRangeControlTimeStamp, sleV2Dhcp4ClassRangeControlReqResult, sleV2Dhcp4ClassRangeControlPoolIndex, sleV2Dhcp4ClassRangeControlStart, sleV2Dhcp4ClassRangeControlEnd, 
				sleV2Dhcp4RelayHelperAddress, sleV2Dhcp4RelayHelperControlRequest, sleV2Dhcp4RelayHelperControlStatus, sleV2Dhcp4RelayHelperControlTimer, sleV2Dhcp4RelayHelperControlTimeStamp, 
				sleV2Dhcp4RelayHelperControlReqResult, sleV2Dhcp4RelayHelperControlIfIndex, sleV2Dhcp4RelayHelperControlAddress, sleV2Dhcp4DatabaseURL, sleV2Dhcp4DatabaseInterval, 
				sleV2Dhcp4PingTimeout, sleV2Dhcp4Option82Policy, sleV2Dhcp4Option82SystemRemoteId, sleV2Dhcp4ControlDatabaseURL, sleV2Dhcp4ControlDatabaseInterval, 
				sleV2Dhcp4ControlPingTimeout, sleV2Dhcp4ControlOption82Policy, sleV2Dhcp4ControlOption82SystemRemoteId, sleV2Dhcp4PoolIndex, sleV2Dhcp4PoolName, 
				sleV2Dhcp4PoolDefaultLeaseTime, sleV2Dhcp4PoolMaxLeaseTime, sleV2Dhcp4PoolDomainName, sleV2Dhcp4PoolSummaryTotal, sleV2Dhcp4PoolSummaryAllocated, 
				sleV2Dhcp4PoolSummaryBound, sleV2Dhcp4PoolSummaryOffered, sleV2Dhcp4PoolSummaryFixed, sleV2Dhcp4PoolSummaryAbandon, sleV2Dhcp4PoolSummaryAvailable, 
				sleV2Dhcp4PoolControlRequest, sleV2Dhcp4PoolControlStatus, sleV2Dhcp4PoolControlTimer, sleV2Dhcp4PoolControlTimeStamp, sleV2Dhcp4PoolControlReqResult, 
				sleV2Dhcp4PoolControlIndex, sleV2Dhcp4PoolControlName, sleV2Dhcp4PoolControlDefaultLeaseTime, sleV2Dhcp4PoolControlMaxLeaseTime, sleV2Dhcp4PoolControlDomainName, 
				sleV2Dhcp4PoolControlOriginURL, sleV2Dhcp4PoolControlOriginFileName, sleV2Dhcp4NetworkAddress, sleV2Dhcp4NetworkMask, sleV2Dhcp4NetworkControlRequest, 
				sleV2Dhcp4NetworkControlStatus, sleV2Dhcp4NetworkControlTimer, sleV2Dhcp4NetworkControlTimeStamp, sleV2Dhcp4NetworkControlReqResult, sleV2Dhcp4NetworkControlAddress, 
				sleV2Dhcp4NetworkControlMask, sleV2Dhcp4RangeStart, sleV2Dhcp4RangeEnd, sleV2Dhcp4RangeControlRequest, sleV2Dhcp4RangeControlStatus, 
				sleV2Dhcp4RangeControlTimer, sleV2Dhcp4RangeControlTimeStamp, sleV2Dhcp4RangeControlReqResult, sleV2Dhcp4RangeControlPoolIndex, sleV2Dhcp4RangeControlStart, 
				sleV2Dhcp4RangeControlEnd, sleV2Dhcp4FixedMac, sleV2Dhcp4FixedControlRequest, sleV2Dhcp4FixedControlStatus, sleV2Dhcp4FixedControlTimer, 
				sleV2Dhcp4FixedControlTimeStamp, sleV2Dhcp4FixedControlReqResult, sleV2Dhcp4DnsIndex, sleV2Dhcp4DnsControlRequest, sleV2Dhcp4DnsControlStatus, 
				sleV2Dhcp4DnsControlTimer, sleV2Dhcp4DnsControlTimeStamp, sleV2Dhcp4DnsControlReqResult, sleV2Dhcp4DnsControlPoolIndex, sleV2Dhcp4DnsControlIndex, 
				sleV2Dhcp4DefaultGatewayIndex, sleV2Dhcp4DefaultGatewayControlRequest, sleV2Dhcp4DefaultGatewayControlStatus, sleV2Dhcp4DefaultGatewayControlTimer, sleV2Dhcp4DefaultGatewayControlTimeStamp, 
				sleV2Dhcp4DefaultGatewayControlReqResult, sleV2Dhcp4DefaultGatewayControlPoolIndex, sleV2Dhcp4DefaultGatewayControlIndex, sleV2Dhcp4OptionCode, sleV2Dhcp4OptionInstance, 
				sleV2Dhcp4OptionType, sleV2Dhcp4OptionValue, sleV2Dhcp4OptionControlRequest, sleV2Dhcp4OptionControlStatus, sleV2Dhcp4OptionControlTimer, 
				sleV2Dhcp4OptionControlTimeStamp, sleV2Dhcp4OptionControlReqResult, sleV2Dhcp4OptionControlCode, sleV2Dhcp4OptionControlInstance, sleV2Dhcp4OptionControlType, 
				sleV2Dhcp4OptionControlValue, sleV2Dhcp4ClassName, sleV2Dhcp4ClassControlRequest, sleV2Dhcp4ClassControlStatus, sleV2Dhcp4ClassControlTimer, 
				sleV2Dhcp4ClassControlReqResult, sleV2Dhcp4Option82TrustDefault, sleV2Dhcp4FilterPortControlRequest, sleV2Dhcp4FilterPortControlStatus, sleV2Dhcp4FilterPortControlTimer, 
				sleV2Dhcp4FilterPortControlTimeStamp, sleV2Dhcp4FilterPortControlReqResult, sleV2Dhcp4FilterPortControlIndex, sleV2Dhcp4FilterAddressMac, sleV2Dhcp4FilterAddressControlRequest, 
				sleV2Dhcp4FilterAddressControlStatus, sleV2Dhcp4FilterAddressControlTimer, sleV2Dhcp4FilterAddressControlTimeStamp, sleV2Dhcp4FilterAddressControlReqResult, sleV2Dhcp4FilterAddressControlMac, 
				sleV2Dhcp4PacketStatsReceived, sleV2Dhcp4PacketStatsSent, sleV2Dhcp4PacketStatsReceivedErrors, sleV2Dhcp4PacketStatsSentErrors, sleV2Dhcp4PacketStatsBootpReceivedRequests, 
				sleV2Dhcp4PacketStatsBootpReceivedReplies, sleV2Dhcp4PacketStatsBootpSentRequests, sleV2Dhcp4PacketStatsBootpSentReplies, sleV2Dhcp4PacketStatsReceivedDiscover, sleV2Dhcp4PacketStatsReceivedRequest, 
				sleV2Dhcp4PacketStatsReceivedRelease, sleV2Dhcp4PacketStatscReceivedInform, sleV2Dhcp4PacketStatsReceivedDecline, sleV2Dhcp4PacketStatsSentOffer, sleV2Dhcp4PacketStatsSentAck, 
				sleV2Dhcp4PacketStatsSentNak, sleV2Dhcp4DatabaseKey, sleV2Dhcp4DebugStatus, sleV2Dhcp4AuthArpTime, sleV2Dhcp4AuthArpLeft, 
				sleV2Dhcp4SummaryPoolCnt, sleV2Dhcp4SummaryTotal, sleV2Dhcp4SummaryAvailable, sleV2Dhcp4SummaryAbandon, sleV2Dhcp4SummaryBound, 
				sleV2Dhcp4SummaryOffered, sleV2Dhcp4SummaryFixed, sleV2Dhcp4ControlDatabaseKey, sleV2Dhcp4ControlDebugStatus, sleV2Dhcp4IllegalMac, 
				sleV2Dhcp4IllegalTime, sleV2Dhcp4IllegalControlRequest, sleV2Dhcp4IllegalControlStatus, sleV2Dhcp4IllegalControlTimer, sleV2Dhcp4IllegalControlTimeStamp, 
				sleV2Dhcp4IllegalControlReqResult, sleV2Dhcp4ClassControlName, sleV2Dhcp4ControlOption82TrustDefault, sleV2Dhcp4ClassControlTimeStamp, sleV2Dhcp4FixedControlPoolIndex, 
				sleV2Dhcp4FixedControlAddress, sleV2Dhcp4FixedControlMac, sleV2Dhcp4ServiceActivity, sleV2Dhcp4ClassUsage, sleV2Dhcp4SmartRelayUsage, 
				sleV2Dhcp4Option82Usage, sleV2Dhcp4ControlClassUsage, sleV2Dhcp4ControlSmartRelayUsage, sleV2Dhcp4ControlOption82Usage, sleV2Dhcp4NetworkControlPoolIndex, 
				sleV2Dhcp4FixedAddress, sleV2Dhcp4DnsAddress, sleV2Dhcp4DnsControlAddress, sleV2Dhcp4DefaultGatewayAddress, sleV2Dhcp4DefaultGatewayControlAddress, 
				sleV2Dhcp4OptionControlPoolIndex, sleV2Dhcp4FilterPortState, sleV2Dhcp4FilterPortControlState, sleV2Dhcp4ClientIfIndex, sleV2Dhcp4ClientIfActivity, 
				sleV2Dhcp4ClientIfAddress, sleV2Dhcp4ClientIfMask, sleV2Dhcp4ClientIfServer, sleV2Dhcp4ClientIfClientType, sleV2Dhcp4ClientIfClientId, 
				sleV2Dhcp4ClientIfClassType, sleV2Dhcp4ClientIfClassId, sleV2Dhcp4ClientIfLeasetime, sleV2Dhcp4ClientIfExpired, sleV2Dhcp4ClientIfState, 
				sleV2Dhcp4ClientIfControlRequest, sleV2Dhcp4ClientIfControlStatus, sleV2Dhcp4ClientIfControlTimer, sleV2Dhcp4ClientIfControlTimeStamp, sleV2Dhcp4ClientIfControlReqResult, 
				sleV2Dhcp4ClientIfControlIndex, sleV2Dhcp4ClientIfControlClientType, sleV2Dhcp4ClientIfControlClientId, sleV2Dhcp4ClientIfControlClassType, sleV2Dhcp4ClientIfControlClassId, 
				sleV2Dhcp4ClientIfControlLeasetime, sleV2Dhcp4ClientOptionCode, sleV2Dhcp4ClientOptionInstance, sleV2Dhcp4ClientOptionType, sleV2Dhcp4ClientOptionValue, 
				sleV2Dhcp4RelayIfIndex, sleV2Dhcp4Option82SystemRemoteType, sleV2Dhcp4ControlOption82SystemRemoteType, sleV2Ds4Activity, sleV2Ds4VerifyMacState, 
				sleV2Ds4DatabaseURL, sleV2Ds4DatabaseInterval, sleV2Ds4ControlRequest, sleV2Ds4ControlStatus, sleV2Ds4ControlTimer, 
				sleV2Ds4ControlTimeStamp, sleV2Ds4ControlReqResult, sleV2Ds4ControlActivity, sleV2Ds4ControlVerifyMacState, sleV2Ds4ControlDatabaseURL, 
				sleV2Ds4ControlDatabaseInterval, sleV2Ds4VlanIndex, sleV2Ds4VlanState, sleV2Ds4VlanControlRequest, sleV2Ds4VlanControlStatus, 
				sleV2Ds4VlanControlTimer, sleV2Ds4VlanControlTimeStamp, sleV2Ds4VlanControlReqResult, sleV2Ds4VlanControlState, sleV2Ds4PortIndex, 
				sleV2Ds4PortTrustState, sleV2Ds4PortLimitRate, sleV2Ds4PortLimitLease, sleV2Ds4PortSrcGuardState, sleV2Ds4PortControlRequest, 
				sleV2Ds4PortControlStatus, sleV2Ds4PortControlTimer, sleV2Ds4PortControlTimeStamp, sleV2Ds4PortControlReqResult, sleV2Ds4PortControlTrustState, 
				sleV2Ds4PortControlLimitRate, sleV2Ds4PortControlLimitLease, sleV2Ds4PortControlSrcGuardState, sleV2Ds4BindingsVlanIndex, sleV2Ds4BindingsPortIndex, 
				sleV2Ds4BindingsAddress, sleV2Ds4BindingsMac, sleV2Ds4BindingsType, sleV2Ds4BindingsLeasedTime, sleV2Ds4BindingsControlRequest, 
				sleV2Ds4BindingsControlStatus, sleV2Ds4BindingsControlTimer, sleV2Ds4BindingsControlTimeStamp, sleV2Ds4BindingsControlReqResult, sleV2Ds4BindingsControlVlanIndex, 
				sleV2Ds4BindingsControlPortIndex, sleV2Ds4BindingsControlAddress, sleV2Ds4BindingsControlMac, sleV2Dhcp4IllegalAddress, sleV2Dhcp4ControlServiceActivity, 
				sleV2Dhcp4ClientIfControlRequestFlag, sleV2Dhcp4ClientIfControlHostName, sleV2Dhcp4ClientIfRequestFlag, sleV2Dhcp4ClientIfHostName, sleV2Dhcp4ControlAuthArpTime, 
				sleV2Dhcp4ControlRequest, sleV2Dhcp4ControlStatus, sleV2Dhcp4ControlTimer, sleV2Dhcp4ControlTimeStamp, sleV2Dhcp4ControlReqResult, 
				sleV2Dhcp4ClientIfControlActivity, sleV2Ds4BindingsState, sleV2Dhcp4LeasedAddress, sleV2Dhcp4LeasedPoolIndex, sleV2Dhcp4LeasedStatus, 
				sleV2Dhcp4LeasedMac, sleV2Dhcp4LeasedHostName, sleV2Dhcp4LeasedClientId, sleV2Dhcp4LeasedRemoteId, sleV2Dhcp4LeasedCircuitId, 
				sleV2Dhcp4LeasedStartTime, sleV2Dhcp4LeasedFinishTime, sleV2Dhcp4LeasedControlRequest, sleV2Dhcp4LeasedControlStatus, sleV2Dhcp4LeasedControlTimer, 
				sleV2Dhcp4LeasedControlTimeStamp, sleV2Dhcp4LeasedControlReqResult, sleV2Dhcp4RelayHelperType, sleV2Dhcp4RelayHelperControlType, sleV2Dhcp4LeasedControlPoolIndex, 
				sleV2Dhcp4LeasedControlAddress, sleV2Dhcp4LeasedControlMask, sleV2Ds4VlanControlIndex, sleV2Ds4PortControlIndex, sleV2Dhcp4RelayIfControlRequest, 
				sleV2Dhcp4RelayIfControlStatus, sleV2Dhcp4RelayIfControlTimer, sleV2Dhcp4RelayIfControlTimeStamp, sleV2Dhcp4RelayIfControllReqResult, sleV2Dhcp4RelayIfControlIndex, 
				sleV2Ds4BindingsControlType, sleV2Dhcp4FilterPortIndex, sleV2Ds4BindingsControlLeasedTime, sleV2Dhcp4Option82PortIndex, sleV2Dhcp4Option82PortCircuitType, 
				sleV2Dhcp4Option82PortCircuitId, sleV2Dhcp4Option82PortTrustState, sleV2Dhcp4Option82PortControlRequest, sleV2Dhcp4Option82PortControlStatus, sleV2Dhcp4Option82PortControlTimer, 
				sleV2Dhcp4Option82PortControlTimeStamp, sleV2Dhcp4Option82PortControlReqResult, sleV2Dhcp4Option82PortControlIndex, sleV2Dhcp4Option82PortControlCircuitType, sleV2Dhcp4Option82PortControlCircuitId, 
				sleV2Dhcp4Option82PortControlTrustState, sleV2Dhcp4RelayIfSimpleOpt82AdminState, sleV2Dhcp4RelayIfSimpleOpt82OperState, sleV2Dhcp4RelayHelperOui, sleV2Dhcp4RelayHelperControlOui, 
				sleV2Dhcp4RelayIfControlSimpleOpt82AdminState, sleV2Dhcp4PacketStatsControlRequest, sleV2Dhcp4PacketStatsControlStatus, sleV2Dhcp4PacketStatsControlTimer, sleV2Dhcp4PacketStatsControlTimeStamp, 
				sleV2Dhcp4PacketStatsControlReqResult, sleV2Dhcp4CRCMapClass, sleV2Dhcp4CRCMapRemote, sleV2Dhcp4CRCMapCircuit, sleV2Dhcp4CRCMapControlRequest, 
				sleV2Dhcp4CRCMapControlStatus, sleV2Dhcp4CRCMapControlTimer, sleV2Dhcp4CRCMapControlTimeStamp, sleV2Dhcp4CRCMapControlReqResult, sleV2Dhcp4CRCMapControlClass, 
				sleV2Dhcp4CRCMapControlRemote, sleV2Dhcp4Option82Drop, sleV2Dhcp4ControlOption82Drop, sleV2Dhcp4ClassRangeControlName, sleV2Dhcp4RemoteId, 
				sleV2Dhcp4RemoteType, sleV2Dhcp4RemoteClass, sleV2Dhcp4RemoteTrust, sleV2Dhcp4RemoteControlRequest, sleV2Dhcp4RemoteControlStatus, 
				sleV2Dhcp4RemoteControlTimer, sleV2Dhcp4RemoteControlTimeStamp, sleV2Dhcp4RemoteControlReqResult, sleV2Dhcp4RemoteControlId, sleV2Dhcp4RemoteControlType, 
				sleV2Dhcp4RemoteControlClass, sleV2Dhcp4RemoteControlTrust, sleV2Dhcp4RCircuitId, sleV2Dhcp4RCircuitType, sleV2Dhcp4RCircuitClass, 
				sleV2Dhcp4RCircuitControlRequest, sleV2Dhcp4RCircuitControlStatus, sleV2Dhcp4RCircuitControlTimer, sleV2Dhcp4RCircuitControlTimeStamp, sleV2Dhcp4RCircuitControlReqResult, 
				sleV2Dhcp4RCircuitControlRemote, sleV2Dhcp4RCircuitControlId, sleV2Dhcp4RCircuitControlType, sleV2Dhcp4ClientHardwareAddress, sleV2Dhcp4ControlClientHardwareAddress, 
				sleV2Dhcp4PoolMeritDumpPath, sleV2Dhcp4PoolRootPath, sleV2Dhcp4PoolControlMeritDumpPath, sleV2Dhcp4PoolControlRootPath, sleV2Dhcp4LogsIndex, 
				sleV2Dhcp4LogsAddress, sleV2Dhcp4LogsControlRequest, sleV2Dhcp4LogsControlStatus, sleV2Dhcp4LogsControlTimer, sleV2Dhcp4LogsControlTimeStamp, 
				sleV2Dhcp4LogsControlReqResult, sleV2Dhcp4LogsControlPoolIndex, sleV2Dhcp4LogsControlIndex, sleV2Dhcp4LogsControlAddress, sleV2Dhcp4NtpIndex, 
				sleV2Dhcp4NtpAddress, sleV2Dhcp4NtpControlRequest, sleV2Dhcp4NtpControlStatus, sleV2Dhcp4NtpControlTimer, sleV2Dhcp4NtpControlTimeStamp, 
				sleV2Dhcp4NtpControlReqResult, sleV2Dhcp4NtpControlPoolIndex, sleV2Dhcp4NtpControlIndex, sleV2Dhcp4NtpControlAddress, sleV2Ds4PortTimeout, 
				sleV2Ds4PortStatus, sleV2Ds4PortControlTimeout, sleV2Ds4PortControlPStatus, sleV2Ds4BindingsMaskLen, sleV2Ds4BindingsControlMaskLen, 
				sleV2Ds4PortFilterMode, sleV2Ds4PortFilterDelayTimer, sleV2Ds4PortFilterDelayCounter, sleV2Ds4PortControlFilterMode, sleV2Ds4PortControlFilterDelayTimer, 
				sleV2Ds4PortControlFilterDelayCounter, sleV2Dhcp4PortLeaseIndex, sleV2Dhcp4PortLeaseLimit, sleV2Dhcp4PortLeaseCount, sleV2Dhcp4PortLeaseControlRequest, 
				sleV2Dhcp4PortLeaseControlStatus, sleV2Dhcp4PortLeaseControlTimer, sleV2Dhcp4PortLeaseControlTimeStamp, sleV2Dhcp4PortLeaseControlReqResult, sleV2Dhcp4PortLeaseControlIndex, 
				sleV2Dhcp4PortLeaseControlLimit, sleV2Dhcp4PacketStatsPortReceived, sleV2Dhcp4PacketStatsPortSent, sleV2Dhcp4PacketStatsPortReceivedError, sleV2Dhcp4PacketStatsPortSentError, 
				sleV2Dhcp4PacketStatsPortReceivedDiscover, sleV2Dhcp4PacketStatsPortReceivedRequest, sleV2Dhcp4PacketStatsPortReceivedRelease, sleV2Dhcp4PacketStatsPortReceivedInform, sleV2Dhcp4PacketStatsPortReceivedDecline, 
				sleV2Dhcp4PacketStatsPortSentOffer, sleV2Dhcp4PacketStatsPortSentAck, sleV2Dhcp4PacketStatsPortSentNak, sleV2Dhcp4PacketStatsPortIndex, sleV2Dhcp4PEStatus, 
				sleV2Dhcp4ControlPEStatus, sleV2Dhcp4PEVendorIfIndex, sleV2Dhcp4PEVendorID, sleV2Dhcp4PEVendorStart, sleV2Dhcp4PEVendorEnd, 
				sleV2Dhcp4PEVendorControlRequest, sleV2Dhcp4PEVendorControlStatus, sleV2Dhcp4PEVendorControlTimer, sleV2Dhcp4PEVendorControlTimeStamp, sleV2Dhcp4PEVendorControlReqResult, 
				sleV2Dhcp4PEVendorControlIfIndex, sleV2Dhcp4PEVendorControlVendorID, sleV2Dhcp4PEVendorControlStart, sleV2Dhcp4PEVendorControlEnd, sleV2Dhcp4PEAddressIfIndex, 
				sleV2Dhcp4PEAddressStart, sleV2Dhcp4PEAddressEnd, sleV2Dhcp4PEAddressControlRequest, sleV2Dhcp4PEAddressControlStatus, sleV2Dhcp4PEAddressControlTimer, 
				sleV2Dhcp4PEAddressControlTimeStamp, sleV2Dhcp4PEAddressControlReqResult, sleV2Dhcp4PEAddressControlStart, sleV2Dhcp4PEAddressControlEnd, sleV2Dhcp4PENonPEStart, 
				sleV2Dhcp4PENonPEEnd, sleV2Dhcp4PENonPEControlRequest, sleV2Dhcp4PENonPEControlStatus, sleV2Dhcp4PENonPEControlTimer, sleV2Dhcp4PENonPEControlTimeStamp, 
				sleV2Dhcp4PENonPEControlReqResult, sleV2Dhcp4PENonPEControlStart, sleV2Dhcp4PENonPEControlEnd, sleV2Dhcp4RCircuitControlClass, sleV2Dhcp4ArpPingFlag, 
				sleV2Dhcp4ArpRetransmits, sleV2Dhcp4ArpTimeout, sleV2Dhcp4PingRetransmits, sleV2Dhcp4ControlArpPingFlag, sleV2Dhcp4ControlArpRetransmits, 
				sleV2Dhcp4ControlArpTimeout, sleV2Dhcp4ControlPingRetransmits, sleV2Dhcp4PortAddrtLeaseIndex, sleV2Dhcp4PortAddrLeaseAddress, sleV2Dhcp4PortAddrLeasePoolIndex, 
				sleV2Dhcp4PortAddrLeaseStatus, sleV2Dhcp4PortAddrLeaseMac, sleV2Dhcp4PortAddrLeaseHostName, sleV2Dhcp4PortAddrLeaseClientId, sleV2Dhcp4PortAddrLeaseRemoteId, 
				sleV2Dhcp4PortAddrLeaseCircuitId, sleV2Dhcp4PortAddrLeaseStartTime, sleV2Dhcp4PortAddrLeaseFinishTime, sleV2Dhcp4PEVendorPoolIndex, sleV2Dhcp4PEVendorControlPoolIndex, 
				sleV2Dhcp4PEAddressPoolIndex, sleV2Dhcp4PEAddressControlIfIndex, sleV2Dhcp4PENonPEPoolIndex, sleV2Dhcp4PoolSummaryNetwork, sleV2Dhcp4SummaryAllocated, 
				sleV2Dhcp4StateIndex, sleV2Dhcp4StateTotal, sleV2Dhcp4StateFixed, sleV2Dhcp4StateDynamic, sleV2Dhcp4StatePEntry, 
				sleV2Dhcp4StateBindIpAddress, sleV2Dhcp4StateBindMac, sleV2Dhcp4StateBindState, sleV2Dhcp4StateBindType, sleV2Dhcp4StateBindExpiration, 
				sleV2Dhcp4StateBindPort, sleV2Dhcp4StatePoolTotal, sleV2Dhcp4StatePoolFixed, sleV2Dhcp4StatePoolDynamic, sleV2Dhcp4StatePoolPEntry, 
				sleV2Dhcp4StateBindPoolIndex, sleV2Dhcp4RemoteLeaseLimit, sleV2Dhcp4RemoteLeaseCnt, sleV4Dhcp4RemoteControlLeaseLimit, sleV2Dhcp4RCircuitLeaseLimit, 
				sleV2Dhcp4RCircuitLeaseCnt, sleV2Dhcp4RCircuitControlLeaseLimit, sleV2Dhcp4RelayIfMaxHops, sleV2Dhcp4RelayIfControlMaxHops, sleV2Dhcp4ClientIfLeasetimeOption, 
				sleV2Dhcp4ClientIfControlLeasetimeOption, sleV2Dhcp4PENonPEControlPoolIndex, sleV2Dhcp4FilterAddressType, sleV2Dhcp4FilterAddressControlType, sleV2Ds4ArpInspectionTime, 
				sleV2Ds4ControlArpInspectionTime, sleV2Dhcp4RelayIntrIndex, sleV2Dhcp4RelayIntrRcvd, sleV2Dhcp4RelayIntrSent, sleV2Dhcp4RelayIntrRcvdErrors, 
				sleV2Dhcp4RelayIntrSentErrors, sleV2Dhcp4RelayIntrRcvdBootpRequest, sleV2Dhcp4RelayIntrRcvdBootpReply, sleV2Dhcp4RelayIntrSentBootpRequest, sleV2Dhcp4RelayIntrSentBootpReply, 
				sleV2Dhcp4RelayIntrRcvdDiscover, sleV2Dhcp4RelayIntrRcvdRequest, sleV2Dhcp4RelayIntrRcvdRelease, sleV2Dhcp4RelayIntrRcvdInform, sleV2Dhcp4RelayIntrRcvdDecline, 
				sleV2Dhcp4RelayIntrSentDiscover, sleV2Dhcp4RelayIntrSentRequest, sleV2Dhcp4RelayIntrSentRelease, sleV2Dhcp4RelayIntrSentInform, sleV2Dhcp4RelayIntrSentDecline, 
				sleV2Dhcp4RelayIntrRcvdOffer, sleV2Dhcp4RelayIntrRcvdAck, sleV2Dhcp4RelayIntrRcvdNack, sleV2Dhcp4RelayIntrSentOffer, sleV2Dhcp4RelayIntrSentAck, 
				sleV2Dhcp4RelayIntrSentNack, sleV2Dhcp4RelayIntrStatsControlRequest, sleV2Dhcp4RelayIntrStatsControlStatus, sleV2Dhcp4RelayIntrStatsControlTimer, sleV2Dhcp4RelayIntrStatsControITimeStamp, 
				sleV2Dhcp4RelayIntrStatsControIResult, sleV2Dhcp4RelayIntrStatsControIndex, sleV2Dhcp4Option82SystemRemoteOption, sleV2Dhcp4ControlOption82SystemRemoteOption, sleV2Dhcp4OptionFormatName, 
				sleV2Dhcp4OptionFormatControlRequest, sleV2Dhcp4OptionFormatControlStatus, sleV2Dhcp4OptionFormatControlTimer, sleV2Dhcp4OptionFormatControlTimeStamp, sleV2Dhcp4OptionFormatControlReqResult, 
				sleV2Dhcp4OptionFormatControlName, sleV2Dhcp4OptionFormatAttrID, sleV2Dhcp4OptionFormatAttrLength, sleV2Dhcp4OptionFormatAttrHiddenLength, sleV2Dhcp4OptionFormatAttrType, 
				sleV2Dhcp4OptionFormatAttrVarType, sleV2Dhcp4OptionFormatAttrVarValue, sleV2Dhcp4OptionFormatAttrControlRequest, sleV2Dhcp4OptionFormatAttrControlStatus, sleV2Dhcp4OptionFormatAttrControlTimer, 
				sleV2Dhcp4OptionFormatAttrControlTimeStamp, sleV2Dhcp4OptionFormatAttrControlReqResult, sleV2Dhcp4OptionFormatAttrControlName, sleV2Dhcp4OptionFormatAttrControlID, sleV2Dhcp4OptionFormatAttrControlLength, 
				sleV2Dhcp4OptionFormatAttrControlHiddenLength, sleV2Dhcp4OptionFormatAttrControlType, sleV2Dhcp4OptionFormatAttrControlVarType, sleV2Dhcp4OptionFormatAttrControlVarValue, sleV2Dhcp4Option82PortPolicy, 
				sleV2Dhcp4Option82PortPolicyDrop, sleV2Dhcp4Option82PortControlPolicy, sleV2Dhcp4Option82PortControlPolicyDrop, sleV2Dhcp4Option82SystemCircuitPortType, sleV2Dhcp4ControlOption82SystemCircuitPortType, 
				sleV2Ds4LimitRateDiscover, sleV2Ds4LimitRateRequest, sleV2Ds4ControlLimitRateDiscover, sleV2Ds4ControlLimitRateRequest, sleV2Ds4InformationOption, 
				sleV2Ds4ControlInformationOption, sleV2Ds4VlanInfoOptState, sleV2Dhcp4PEAddressControlPoolIndex, sleV2Dhcp4AuthArpReadyTime, sleV2Dhcp4AuthArpRemainTime, 
				sleV2Dhcp4ControlAuthArpReadyTime, sleV2Ds4VlanInfoOptControlRequest, sleV2Ds4VlanInfoOptControlStatus, sleV2Ds4VlanInfoOptControlTimer, sleV2Ds4VlanInfoOptControlTimeStamp, 
				sleV2Ds4VlanInfoOptControlReqResult, sleV2Ds4VlanInfoOptControlIndex, sleV2Ds4VlanInfoOptControlState, sleV2Ds4VlanInfoOptIndex }
			STATUS current
			DESCRIPTION 
				"Description."
			::= { sleV2Dhcp 4 }

		
		-- 1.3.6.1.4.1.6296.102.6.5
		sleV2DhcpNotificationGroup NOTIFICATION-GROUP
			NOTIFICATIONS { sleV2Dhcp4RelayHelperCreated, sleV2Dhcp4RelayHelperDestroyed, sleV2Dhcp4LeasedAddressCleared, sleV2Dhcp4LeasedNetworkCleared, sleV2Dhcp4LeasedPoolCleared, 
				sleV2Dhcp4LeasedAllCleared, sleV2Dhcp4ServiceActivityChanged, sleV2Dhcp4ClassUsageChanged, sleV2Dhcp4SmartRelayUsageChanged, sleV2Dhcp4Option82UsageChanged, 
				sleV2Dhcp4DefaultGatewayDestroyed, sleV2Dhcp4FilterPortStateChanged, sleV2Dhcp4DatabaseProfileChanged, sleV2Dhcp4Option82PolicyChanged, sleV2Dhcp4Option82SystemRemoteIdChanged, 
				sleV2Dhcp4PoolCreated, sleV2Dhcp4PoolDestroyed, sleV2Dhcp4PoolLeaseTimeProfileChanged, sleV2Dhcp4PoolDomainNameChanged, sleV2Dhcp4PoolOriginProfileChanged, 
				sleV2Dhcp4NetworkCreated, sleV2Dhcp4NetworkDestroyed, sleV2Dhcp4RangeCreated, sleV2Dhcp4RangeDestroyed, sleV2Dhcp4FixedCreated, 
				sleV2Dhcp4FixedDestroyed, sleV2Dhcp4DnsCreated, sleV2Dhcp4DnsDestroyed, sleV2Dhcp4DefaultGatewayCreated, sleV2Dhcp4OptionCreated, 
				sleV2Dhcp4OptionDestroyed, sleV2Dhcp4ClassCreated, sleV2Dhcp4ClassDestroyed, sleV2Dhcp4Option82TrustDefaultChanged, sleV2Dhcp4FilterAddressCreated, 
				sleV2Dhcp4FilterAddressDestroyed, sleV2Dhcp4PacketStatsCleared, sleV2Dhcp4DatabaseKeyChanged, sleV2Dhcp4DebugStatusChanged, sleV2Dhcp4IllegalCleared, 
				sleV2Dhcp4AuthoArpTimeChanged, sleV2Dhcp4ClientIfReleased, sleV2Dhcp4ClientIfRenewed, sleV2Dhcp4ClientIfProfileChanged, sleV2Ds4ActivityChanged, 
				sleV2Ds4VerifyMacStateChanged, sleV2Ds4DatabaseProfileChanged, sleV2Ds4VlanStateChanged, sleV2Ds4PortTrustStateChanged, sleV2Ds4PortLimitProfileChagned, 
				sleV2Ds4PortSrcGuardStateChanged, sleV2Dhcp4ClientIfActivityChanged, sleV2Ds4BindingsCreated, sleV2Ds4DatabaseRenewed, sleV2Ds4BindingsDestroyed, 
				sleV2Dhcp4Option82PortCircuitIdChanged, sleV2Dhcp4Option82PortTrustStateChanged, sleV2Dhcp4RelayIfSimpleOpt82AdminStateChanged, sleV2Dhcp4ClassRangeCreated, sleV2Ds4BindingsCleared, 
				sleV2Dhcp4RelayHelperCleared, sleV2Dhcp4CRCMapCircuitCleared, sleV2Dhcp4CRCMapRemoteCleared, sleV2Dhcp4ClassRangeDestroyed, sleV2Dhcp4RemoteCreated, 
				sleV2Dhcp4RemoteDestroyed, sleV2Dhcp4RemoteChanged, sleV2Dhcp4RemoteCleared, sleV2Dhcp4RCircuitCreated, sleV2Dhcp4RCircuitDestroyed, 
				sleV2Dhcp4ClientHardwareAddressChanged, sleV2Dhcp4PoolMeritDumpPathChanged, sleV2Dhcp4LogsCreated, sleV2Dhcp4LogsDestroyed, sleV2Dhcp4NtpCreated, 
				sleV2Dhcp4NtpDestroyed, sleV2Ds4PortTimeoutChanged, sleV2Ds4PortStatusChanged, sleV2Ds4PortFilterModeChanged, sleV2Ds4PortFilterDelayChanged, 
				sleV2Dhcp4PortLeaseLimitChanged, sleV2Dhcp4PEStatusChanged, sleV2Dhcp4PEVendorCreated, sleV2Dhcp4PEVendorDestroyed, sleV2Dhcp4PEVendorAllDestroyed, 
				sleV2Dhcp4PEAddressCreated, sleV2Dhcp4PEAddressDestroyed, sleV2Dhcp4PEAddressAllDestroyed, sleV2Dhcp4PENonPECreated, sleV2Dhcp4PENonPEDestroyed, 
				sleV2Dhcp4RCircuitChanged, sleV2Dhcp4RelayIfMaxHopsChanged, sleV2Dhcp4ClientIfLeasetimeOptionChanged, sleV2Ds4ArpInspectionTimeChanged, sleV2Dhcp4RelayintrStatsCleared, 
				sleV2Dhcp4Option82SystemRemoteOptionChanged, sleV2Dhcp4Option82PortCircuitIdCleared, sleV2Dhcp4OptionFormatCreated, sleV2Dhcp4OptionFormatDestroyed, sleV2Dhcp4OptionFormatAttrAdded, 
				sleV2Dhcp4OptionFormatAttrDeleted, sleV2Dhcp4OptionFormatAttrModified, sleV2Dhcp4Option82PortPolicyChanged, sleV2DhcpOption82SystemCirucitIdPortTypeChanged, sleV2Ds4LimitRateDiscoverChanged, 
				sleV2Ds4LimitRateRequestChanged, sleV2Ds4InformationOptionChanged, sleV2Ds4VlanInfoOptStateChanged, sleV2Dhcp4RCircuitCleared, sleV2Dhcp4ArpPingProfileChanged, 
				sleV2Dhcp4PoolRootPathChanged }
			STATUS current
			DESCRIPTION 
				"Description."
			::= { sleV2Dhcp 5 }

		
	
	END

--
-- slev2-dhcp-mib.mib
--
