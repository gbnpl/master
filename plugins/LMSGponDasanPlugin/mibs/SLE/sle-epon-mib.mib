--
-- sle-epon-mib.mib
-- MIB generated by MG-SOFT Visual MIB Builder Version 6.0  Build 88
-- Monday, April 08, 2013 at 20:02:37
--

	SLE-EPON-MIB DEFINITIONS ::= BEGIN
 
		IMPORTS
			sleMgmt			
				FROM DASAN-SMI			
			ifIndex			
				FROM IF-MIB			
			VlanIndex, PortList			
				FROM Q-BRIDGE-MIB			
			sysDescr			
				FROM RFC1213-MIB			
			SleControlStatusType, SleControlRequestResultType			
				FROM SLE-TC-MIB			
			OBJECT-GROUP, NOTIFICATION-GROUP			
				FROM SNMPv2-CONF			
			TimeTicks, IpAddress, Integer32, Gauge32, Counter32, 
			Counter64, BITS, OBJECT-TYPE, MODULE-IDENTITY, NOTIFICATION-TYPE			
				FROM SNMPv2-SMI			
			MacAddress, TEXTUAL-CONVENTION			
				FROM SNMPv2-TC;
	
	
		-- 1.3.6.1.4.1.6296.101.20
		sleEpon MODULE-IDENTITY 
			LAST-UPDATED "200601251753Z"		-- January 25, 2006 at 17:53 GMT
			ORGANIZATION 
				"Organization."
			CONTACT-INFO 
				"Contact-info."
			DESCRIPTION 
				"Description."
			::= { sleMgmt 20 }

		
	
	
--
-- Textual conventions
--
	
		EnableFlag ::= TEXTUAL-CONVENTION
			STATUS current
			DESCRIPTION 
				"Description."
			SYNTAX INTEGER
				{
				enable(1),
				disable(2)
				}

	
--
-- Node definitions
--
	
		-- 1.3.6.1.4.1.6296.101.20.1
		sleEponBase OBJECT IDENTIFIER ::= { sleEpon 1 }

		
		-- 1.3.6.1.4.1.6296.101.20.1.1
		sleEponBaseInfo OBJECT IDENTIFIER ::= { sleEponBase 1 }

		
		-- 1.3.6.1.4.1.6296.101.20.1.1.1
		sleEponBaseSlaPlatoMaxBandwdith OBJECT-TYPE
			SYNTAX INTEGER (1000..900000 | 1000000)
			UNITS "kbps"
			MAX-ACCESS read-only
			STATUS current
			DESCRIPTION
				"Description."
			::= { sleEponBaseInfo 1 }

		
		-- 1.3.6.1.4.1.6296.101.20.1.1.2
		sleEponBaseDPShapingMaxBandwidth OBJECT-TYPE
			SYNTAX INTEGER (0 | 1000..900000)
			UNITS "kbps"
			MAX-ACCESS read-only
			STATUS current
			DESCRIPTION
				"Description."
			::= { sleEponBaseInfo 2 }

		
		-- 1.3.6.1.4.1.6296.101.20.1.1.3
		sleEponBasePortMaxHost OBJECT-TYPE
			SYNTAX INTEGER (0 | 1..16)
			MAX-ACCESS read-only
			STATUS current
			DESCRIPTION
				"Description."
			::= { sleEponBaseInfo 3 }

		
		-- 1.3.6.1.4.1.6296.101.20.1.1.4
		sleEponBaseOnuAutoUpgrade OBJECT-TYPE
			SYNTAX EnableFlag
			MAX-ACCESS read-only
			STATUS current
			DESCRIPTION
				"The status of ONU auto-upgrade."
			::= { sleEponBaseInfo 4 }

		
		-- 1.3.6.1.4.1.6296.101.20.1.1.5
		sleEponBaseOnuAutoUpgradeRebootTime OBJECT-TYPE
			SYNTAX INTEGER (-1 | 0..23)
			UNITS "hour"
			MAX-ACCESS read-only
			STATUS current
			DESCRIPTION
				"The reboot-time of ONU auto-upgrade."
			::= { sleEponBaseInfo 5 }

		
		-- 1.3.6.1.4.1.6296.101.20.1.1.6
		sleEponBaseOnuAgingTime OBJECT-TYPE
			SYNTAX Integer32 (0..30)
			UNITS "day"
			MAX-ACCESS read-only
			STATUS current
			DESCRIPTION
				"Description."
			::= { sleEponBaseInfo 6 }

		
		-- 1.3.6.1.4.1.6296.101.20.1.1.7
		sleEponBaseAlarmStatus OBJECT-TYPE
			SYNTAX BITS
				{
				critical(0),
				major(1),
				minor(2)
				}
			MAX-ACCESS read-only
			STATUS current
			DESCRIPTION
				"Description."
			::= { sleEponBaseInfo 7 }

		
		-- 1.3.6.1.4.1.6296.101.20.1.1.8
		sleEponBaseAlarmMode OBJECT-TYPE
			SYNTAX INTEGER
				{
				auto(0),
				manual(1)
				}
			MAX-ACCESS read-only
			STATUS current
			DESCRIPTION
				"Description."
			::= { sleEponBaseInfo 8 }

		
		-- 1.3.6.1.4.1.6296.101.20.1.2
		sleEponBaseControl OBJECT IDENTIFIER ::= { sleEponBase 2 }

		
		-- 1.3.6.1.4.1.6296.101.20.1.2.1
		sleEponBaseControlRequest OBJECT-TYPE
			SYNTAX INTEGER
				{
				setEponBaseDefaultBandwidth(1),
				setEponBaseDefaultMaxhost(2),
				setEponBaseOnuAutoUpgrade(3),
				setEponBaseOnuAgingTime(4),
				setEponBaseAlarmStatus(5),
				setEponBaseAlarmMode(6)
				}
			MAX-ACCESS read-write
			STATUS current
			DESCRIPTION
				"Description."
			::= { sleEponBaseControl 1 }

		
		-- 1.3.6.1.4.1.6296.101.20.1.2.2
		sleEponBaseControlStatus OBJECT-TYPE
			SYNTAX SleControlStatusType
			MAX-ACCESS read-only
			STATUS current
			DESCRIPTION
				"Description."
			::= { sleEponBaseControl 2 }

		
		-- 1.3.6.1.4.1.6296.101.20.1.2.3
		sleEponBaseControlTimer OBJECT-TYPE
			SYNTAX Gauge32
			MAX-ACCESS read-write
			STATUS current
			DESCRIPTION
				"Description."
			::= { sleEponBaseControl 3 }

		
		-- 1.3.6.1.4.1.6296.101.20.1.2.4
		sleEponBaseControlTimeStamp OBJECT-TYPE
			SYNTAX TimeTicks
			MAX-ACCESS read-only
			STATUS current
			DESCRIPTION
				"Description."
			::= { sleEponBaseControl 4 }

		
		-- 1.3.6.1.4.1.6296.101.20.1.2.5
		sleEponBaseControlReqResult OBJECT-TYPE
			SYNTAX SleControlRequestResultType
			MAX-ACCESS read-only
			STATUS current
			DESCRIPTION
				"Description."
			::= { sleEponBaseControl 5 }

		
		-- 1.3.6.1.4.1.6296.101.20.1.2.6
		sleEponBaseControlSlaPlatoMaxBandwdith OBJECT-TYPE
			SYNTAX INTEGER (1000..900000 | 1000000)
			UNITS "kbps"
			MAX-ACCESS read-write
			STATUS current
			DESCRIPTION
				"Description."
			::= { sleEponBaseControl 6 }

		
		-- 1.3.6.1.4.1.6296.101.20.1.2.7
		sleEponBaseControlDPShapingMaxBandwidth OBJECT-TYPE
			SYNTAX INTEGER (0 | 1000..900000)
			UNITS "Mbps"
			MAX-ACCESS read-write
			STATUS current
			DESCRIPTION
				"Description."
			::= { sleEponBaseControl 7 }

		
		-- 1.3.6.1.4.1.6296.101.20.1.2.8
		sleEponBaseControlPortMaxHost OBJECT-TYPE
			SYNTAX INTEGER (0 | 1..16)
			MAX-ACCESS read-write
			STATUS current
			DESCRIPTION
				"Description."
			::= { sleEponBaseControl 8 }

		
		-- 1.3.6.1.4.1.6296.101.20.1.2.9
		sleEponBaseControlOnuAutoUpgrade OBJECT-TYPE
			SYNTAX EnableFlag
			MAX-ACCESS read-write
			STATUS current
			DESCRIPTION
				"The status of ONU auto-upgrade."
			::= { sleEponBaseControl 9 }

		
		-- 1.3.6.1.4.1.6296.101.20.1.2.10
		sleEponBaseControlOnuAutoUpgradeRebootTime OBJECT-TYPE
			SYNTAX INTEGER (-1 | 0..23)
			UNITS "hour"
			MAX-ACCESS read-write
			STATUS current
			DESCRIPTION
				"The reboot-time of ONU auto-upgrade."
			::= { sleEponBaseControl 10 }

		
		-- 1.3.6.1.4.1.6296.101.20.1.2.11
		sleEponBaseControlOnuAgingTime OBJECT-TYPE
			SYNTAX Integer32 (0..30)
			UNITS "day"
			MAX-ACCESS read-write
			STATUS current
			DESCRIPTION
				"Description."
			::= { sleEponBaseControl 11 }

		
		-- 1.3.6.1.4.1.6296.101.20.1.2.12
		sleEponBaseControlAlarmStatus OBJECT-TYPE
			SYNTAX BITS
				{
				critical(0),
				major(1),
				minor(2)
				}
			MAX-ACCESS read-write
			STATUS current
			DESCRIPTION
				"Description."
			::= { sleEponBaseControl 12 }

		
		-- 1.3.6.1.4.1.6296.101.20.1.2.13
		sleEponBaseControlAlarmMode OBJECT-TYPE
			SYNTAX INTEGER
				{
				auto(0),
				manual(1)
				}
			MAX-ACCESS read-write
			STATUS current
			DESCRIPTION
				"Description."
			::= { sleEponBaseControl 13 }

		
		-- 1.3.6.1.4.1.6296.101.20.1.3
		sleEponBaseNotification OBJECT IDENTIFIER ::= { sleEponBase 3 }

		
		-- 1.3.6.1.4.1.6296.101.20.1.3.1
		sleEponBaseDefaultBandwidthChanged NOTIFICATION-TYPE
			OBJECTS { sleEponBaseControlRequest, sleEponBaseControlTimeStamp, sleEponBaseControlReqResult, sleEponBaseControlSlaPlatoMaxBandwdith, sleEponBaseControlDPShapingMaxBandwidth
				 }
			STATUS current
			DESCRIPTION 
				"Description."
			::= { sleEponBaseNotification 1 }

		
		-- 1.3.6.1.4.1.6296.101.20.1.3.2
		sleEponBaseDefaultMaxHost NOTIFICATION-TYPE
			OBJECTS { sleEponBaseControlRequest, sleEponBaseControlTimeStamp, sleEponBaseControlReqResult, sleEponBaseControlPortMaxHost }
			STATUS current
			DESCRIPTION 
				"Description."
			::= { sleEponBaseNotification 2 }

		
		-- 1.3.6.1.4.1.6296.101.20.1.3.3
		sleEponBaseOnuAutoUpgradeChanged NOTIFICATION-TYPE
			OBJECTS { sleEponBaseControlRequest, sleEponBaseControlTimeStamp, sleEponBaseControlReqResult, sleEponBaseControlOnuAutoUpgrade, sleEponBaseControlOnuAutoUpgradeRebootTime
				 }
			STATUS current
			DESCRIPTION 
				"Description."
			::= { sleEponBaseNotification 3 }

		
		-- 1.3.6.1.4.1.6296.101.20.1.3.4
		sleEponBaseOnuAgingTimeChanged NOTIFICATION-TYPE
			OBJECTS { sleEponBaseControlRequest, sleEponBaseControlTimeStamp, sleEponBaseControlReqResult, sleEponBaseControlOnuAgingTime }
			STATUS current
			DESCRIPTION 
				"Description."
			::= { sleEponBaseNotification 4 }

		
		-- 1.3.6.1.4.1.6296.101.20.1.3.5
		sleEponBaseAlarmStatusChanged NOTIFICATION-TYPE
			OBJECTS { sleEponBaseControlRequest, sleEponBaseControlTimeStamp, sleEponBaseControlReqResult, sleEponBaseControlAlarmStatus }
			STATUS current
			DESCRIPTION 
				"Description."
			::= { sleEponBaseNotification 5 }

		
		-- 1.3.6.1.4.1.6296.101.20.1.3.6
		sleEponBaseAlarmModeChanged NOTIFICATION-TYPE
			OBJECTS { sleEponBaseControlRequest, sleEponBaseControlTimeStamp, sleEponBaseControlReqResult, sleEponBaseAlarmMode }
			STATUS current
			DESCRIPTION 
				"Description."
			::= { sleEponBaseNotification 6 }

		
		-- 1.3.6.1.4.1.6296.101.20.2
		sleEponOlt OBJECT IDENTIFIER ::= { sleEpon 2 }

		
		-- 1.3.6.1.4.1.6296.101.20.2.1
		sleEponOltTable OBJECT-TYPE
			SYNTAX SEQUENCE OF SleEponOltEntry
			MAX-ACCESS not-accessible
			STATUS current
			DESCRIPTION
				"Description."
			::= { sleEponOlt 1 }

		
		-- 1.3.6.1.4.1.6296.101.20.2.1.1
		sleEponOltEntry OBJECT-TYPE
			SYNTAX SleEponOltEntry
			MAX-ACCESS not-accessible
			STATUS current
			DESCRIPTION
				"Description."
			INDEX { sleEponOltIndex }
			::= { sleEponOltTable 1 }

		
		SleEponOltEntry ::=
			SEQUENCE { 
				sleEponOltIndex
					INTEGER,
				sleEponOltRegMode
					INTEGER,
				sleEponOltStatus
					EnableFlag,
				sleEponOltEncryptionPolicy
					INTEGER,
				sleEponOltP2pAccessControl
					EnableFlag,
				sleEponOltDbaInternal
					EnableFlag,
				sleEponOltDbaCycle
					INTEGER,
				sleEponOltDbaDiscoveryFrequency
					INTEGER,
				sleEponOltDbaDiscoveryLength
					INTEGER,
				sleEponOltProfile
					OCTET STRING,
				sleEponOltTxFault
					INTEGER,
				sleEponOltLossOfSignal
					INTEGER,
				sleEponOltAdminRegMode
					INTEGER,
				sleEponOltSC
					EnableFlag,
				sleEponOltSCAutoOnuBlock
					EnableFlag,
				sleEponOltOperStatus
					INTEGER,
				sleEponOltFirmwareRev
					OCTET STRING,
				sleEponOltKeyExchangeTimeout
					INTEGER,
				sleEponOltRssiStatus
					EnableFlag,
				sleEponOltOnuRegisterCount
					INTEGER
			 }

		-- 1.3.6.1.4.1.6296.101.20.2.1.1.1
		sleEponOltIndex OBJECT-TYPE
			SYNTAX INTEGER (1..512)
			MAX-ACCESS read-only
			STATUS current
			DESCRIPTION
				"OLT port Index"
			::= { sleEponOltEntry 1 }

		
		-- 1.3.6.1.4.1.6296.101.20.2.1.1.2
		sleEponOltRegMode OBJECT-TYPE
			SYNTAX INTEGER
				{
				auto(1),
				manual(2),
				fixed(3),
				autoToManual(4),
				webBasedRegistry(5)
				}
			MAX-ACCESS read-only
			STATUS current
			DESCRIPTION
				"OLT port registeraton Mode {auto(1), manual(2)}"
			DEFVAL { auto }
			::= { sleEponOltEntry 2 }

		
		-- 1.3.6.1.4.1.6296.101.20.2.1.1.3
		sleEponOltStatus OBJECT-TYPE
			SYNTAX EnableFlag
			MAX-ACCESS read-only
			STATUS current
			DESCRIPTION
				"OLT port status "
			::= { sleEponOltEntry 3 }

		
		-- 1.3.6.1.4.1.6296.101.20.2.1.1.4
		sleEponOltEncryptionPolicy OBJECT-TYPE
			SYNTAX INTEGER
				{
				disable(1),
				down(2),
				both(3)
				}
			MAX-ACCESS read-only
			STATUS current
			DESCRIPTION
				"OLT port encryption policy"
			DEFVAL { disable }
			::= { sleEponOltEntry 4 }

		
		-- 1.3.6.1.4.1.6296.101.20.2.1.1.5
		sleEponOltP2pAccessControl OBJECT-TYPE
			SYNTAX EnableFlag
			MAX-ACCESS read-only
			STATUS current
			DESCRIPTION
				"OLT port p2p access Control "
			DEFVAL { disable }
			::= { sleEponOltEntry 5 }

		
		-- 1.3.6.1.4.1.6296.101.20.2.1.1.6
		sleEponOltDbaInternal OBJECT-TYPE
			SYNTAX EnableFlag
			MAX-ACCESS read-only
			STATUS current
			DESCRIPTION
				"OLT port DBA internal "
			DEFVAL { disable }
			::= { sleEponOltEntry 6 }

		
		-- 1.3.6.1.4.1.6296.101.20.2.1.1.7
		sleEponOltDbaCycle OBJECT-TYPE
			SYNTAX INTEGER (0 | 200..16777215)
			MAX-ACCESS read-only
			STATUS current
			DESCRIPTION
				"OLT port DBA cycle "
			::= { sleEponOltEntry 7 }

		
		-- 1.3.6.1.4.1.6296.101.20.2.1.1.8
		sleEponOltDbaDiscoveryFrequency OBJECT-TYPE
			SYNTAX INTEGER (0 | 1..65535)
			MAX-ACCESS read-only
			STATUS current
			DESCRIPTION
				"OLT port DBA Discovery Frequency"
			::= { sleEponOltEntry 8 }

		
		-- 1.3.6.1.4.1.6296.101.20.2.1.1.9
		sleEponOltDbaDiscoveryLength OBJECT-TYPE
			SYNTAX INTEGER (0 | 1..65535)
			MAX-ACCESS read-only
			STATUS current
			DESCRIPTION
				"OLT port DBA Discovery Length"
			::= { sleEponOltEntry 9 }

		
		-- 1.3.6.1.4.1.6296.101.20.2.1.1.10
		sleEponOltProfile OBJECT-TYPE
			SYNTAX OCTET STRING (SIZE (1..64))
			MAX-ACCESS read-only
			STATUS current
			DESCRIPTION
				"OLT port auto profile name"
			::= { sleEponOltEntry 10 }

		
		-- 1.3.6.1.4.1.6296.101.20.2.1.1.11
		sleEponOltTxFault OBJECT-TYPE
			SYNTAX INTEGER
				{
				unknown(0),
				normal(1),
				lagerFault(2)
				}
			MAX-ACCESS read-only
			STATUS current
			DESCRIPTION
				"This object indicates the status of Tx fault."
			::= { sleEponOltEntry 11 }

		
		-- 1.3.6.1.4.1.6296.101.20.2.1.1.12
		sleEponOltLossOfSignal OBJECT-TYPE
			SYNTAX INTEGER
				{
				unknown(0),
				normal(1),
				loss(2)
				}
			MAX-ACCESS read-only
			STATUS current
			DESCRIPTION
				"This object indicates the status of loss of signal"
			::= { sleEponOltEntry 12 }

		
		-- 1.3.6.1.4.1.6296.101.20.2.1.1.13
		sleEponOltAdminRegMode OBJECT-TYPE
			SYNTAX INTEGER
				{
				auto(1),
				manual(2),
				autoToManual(3),
				webBasedRegistry(4)
				}
			MAX-ACCESS read-only
			STATUS current
			DESCRIPTION
				"OLT port admin registeraton Mode {auto(1), manual(2), auto-to-manual(3), web-based-registry(4)}"
			::= { sleEponOltEntry 13 }

		
		-- 1.3.6.1.4.1.6296.101.20.2.1.1.14
		sleEponOltSC OBJECT-TYPE
			SYNTAX EnableFlag
			MAX-ACCESS read-only
			STATUS current
			DESCRIPTION
				"Description."
			::= { sleEponOltEntry 14 }

		
		-- 1.3.6.1.4.1.6296.101.20.2.1.1.15
		sleEponOltSCAutoOnuBlock OBJECT-TYPE
			SYNTAX EnableFlag
			MAX-ACCESS read-only
			STATUS current
			DESCRIPTION
				"Description."
			::= { sleEponOltEntry 15 }

		
		-- 1.3.6.1.4.1.6296.101.20.2.1.1.16
		sleEponOltOperStatus OBJECT-TYPE
			SYNTAX INTEGER
				{
				up(1),
				down(2),
				cableDown(3)
				}
			MAX-ACCESS read-only
			STATUS current
			DESCRIPTION
				"Description."
			::= { sleEponOltEntry 16 }

		
		-- 1.3.6.1.4.1.6296.101.20.2.1.1.17
		sleEponOltFirmwareRev OBJECT-TYPE
			SYNTAX OCTET STRING (SIZE (1..64))
			MAX-ACCESS read-only
			STATUS current
			DESCRIPTION
				"The firmware revision of OLT port."
			::= { sleEponOltEntry 17 }

		
		-- 1.3.6.1.4.1.6296.101.20.2.1.1.18
		sleEponOltKeyExchangeTimeout OBJECT-TYPE
			SYNTAX INTEGER (600..65535)
			MAX-ACCESS read-only
			STATUS current
			DESCRIPTION
				"Key Exchange Timeout"
			::= { sleEponOltEntry 18 }

		
		-- 1.3.6.1.4.1.6296.101.20.2.1.1.19
		sleEponOltRssiStatus OBJECT-TYPE
			SYNTAX EnableFlag
			MAX-ACCESS read-only
			STATUS current
			DESCRIPTION
				"Epon olt rssi disable/enable."
			::= { sleEponOltEntry 19 }

		
		-- 1.3.6.1.4.1.6296.101.20.2.1.1.20
		sleEponOltOnuRegisterCount OBJECT-TYPE
			SYNTAX INTEGER (1..32)
			MAX-ACCESS read-only
			STATUS current
			DESCRIPTION
				"onu register count."
			::= { sleEponOltEntry 20 }

		
		-- 1.3.6.1.4.1.6296.101.20.2.2
		sleEponOltControl OBJECT IDENTIFIER ::= { sleEponOlt 2 }

		
		-- 1.3.6.1.4.1.6296.101.20.2.2.1
		sleEponOltControlRequest OBJECT-TYPE
			SYNTAX INTEGER
				{
				setEponOltRegMode(1),
				setEponOltStatus(2),
				setEponOltAttributes(3),
				setEponOltProfile(4),
				setEponOltAttributeSC(5),
				setEponOltUpgrade(6),
				setEponOltReset(7),
				setEponOltRssiStatus(8)
				}
			MAX-ACCESS read-write
			STATUS current
			DESCRIPTION
				"The request of a user command"
			::= { sleEponOltControl 1 }

		
		-- 1.3.6.1.4.1.6296.101.20.2.2.2
		sleEponOltControlStatus OBJECT-TYPE
			SYNTAX SleControlStatusType
			MAX-ACCESS read-only
			STATUS current
			DESCRIPTION
				"The status of user command"
			::= { sleEponOltControl 2 }

		
		-- 1.3.6.1.4.1.6296.101.20.2.2.3
		sleEponOltControlTimer OBJECT-TYPE
			SYNTAX Gauge32
			MAX-ACCESS read-write
			STATUS current
			DESCRIPTION
				"The maximum time for the manager for a long running user command"
			::= { sleEponOltControl 3 }

		
		-- 1.3.6.1.4.1.6296.101.20.2.2.4
		sleEponOltControlTimeStamp OBJECT-TYPE
			SYNTAX TimeTicks
			MAX-ACCESS read-only
			STATUS current
			DESCRIPTION
				"The time stamp of the last command(end of command)"
			::= { sleEponOltControl 4 }

		
		-- 1.3.6.1.4.1.6296.101.20.2.2.5
		sleEponOltControlReqResult OBJECT-TYPE
			SYNTAX SleControlRequestResultType
			MAX-ACCESS read-only
			STATUS current
			DESCRIPTION
				"The result of the last user command"
			::= { sleEponOltControl 5 }

		
		-- 1.3.6.1.4.1.6296.101.20.2.2.6
		sleEponOltControlOltIndex OBJECT-TYPE
			SYNTAX Integer32
			MAX-ACCESS read-write
			STATUS current
			DESCRIPTION
				"OLT port Index"
			::= { sleEponOltControl 6 }

		
		-- 1.3.6.1.4.1.6296.101.20.2.2.7
		sleEponOltControlRegMode OBJECT-TYPE
			SYNTAX INTEGER
				{
				auto(1),
				manual(2),
				fixed(3),
				autoToManual(4),
				webBasedRegistry(5)
				}
			MAX-ACCESS read-write
			STATUS current
			DESCRIPTION
				"auto(1), manual(2), fixed(3) / DEFVAL : auto"
			DEFVAL { auto }
			::= { sleEponOltControl 7 }

		
		-- 1.3.6.1.4.1.6296.101.20.2.2.8
		sleEponOltControlOltStatus OBJECT-TYPE
			SYNTAX EnableFlag
			MAX-ACCESS read-write
			STATUS current
			DESCRIPTION
				"enable(1), disable(2)"
			::= { sleEponOltControl 8 }

		
		-- 1.3.6.1.4.1.6296.101.20.2.2.9
		sleEponOltControlEncryptionPolicy OBJECT-TYPE
			SYNTAX INTEGER
				{
				disable(1),
				down(2),
				both(3)
				}
			MAX-ACCESS read-write
			STATUS current
			DESCRIPTION
				"disable(1), down(2), both(3) / DEFVAL : disable"
			DEFVAL { disable }
			::= { sleEponOltControl 9 }

		
		-- 1.3.6.1.4.1.6296.101.20.2.2.10
		sleEponOltControlP2pAccessControl OBJECT-TYPE
			SYNTAX EnableFlag
			MAX-ACCESS read-write
			STATUS current
			DESCRIPTION
				"enable(1), disable(2)  / DEFVAL : disable "
			DEFVAL { disable }
			::= { sleEponOltControl 10 }

		
		-- 1.3.6.1.4.1.6296.101.20.2.2.11
		sleEponOltControlDbaInternal OBJECT-TYPE
			SYNTAX EnableFlag
			MAX-ACCESS read-write
			STATUS current
			DESCRIPTION
				"enable(1), disable(2)  / DEFVAL : disable"
			DEFVAL { disable }
			::= { sleEponOltControl 11 }

		
		-- 1.3.6.1.4.1.6296.101.20.2.2.12
		sleEponOltControlDbaCycle OBJECT-TYPE
			SYNTAX INTEGER (200..16777215)
			MAX-ACCESS read-write
			STATUS current
			DESCRIPTION
				"< 0 | 200..16777215>  / DEFVAL : 65536"
			DEFVAL { 65536 }
			::= { sleEponOltControl 12 }

		
		-- 1.3.6.1.4.1.6296.101.20.2.2.13
		sleEponOltControlDbaDiscoveryFrequency OBJECT-TYPE
			SYNTAX INTEGER (1..65535)
			MAX-ACCESS read-write
			STATUS current
			DESCRIPTION
				"< 0 | 1..65535>  /DEFVAL : 1792"
			DEFVAL { 1792 }
			::= { sleEponOltControl 13 }

		
		-- 1.3.6.1.4.1.6296.101.20.2.2.14
		sleEponOltControlDbaDiscoveryLength OBJECT-TYPE
			SYNTAX INTEGER (1..65535)
			MAX-ACCESS read-write
			STATUS current
			DESCRIPTION
				"< 0 | 1..65535>  /DEFVAL : 500"
			DEFVAL { 500 }
			::= { sleEponOltControl 14 }

		
		-- 1.3.6.1.4.1.6296.101.20.2.2.15
		sleEponOltControlProfile OBJECT-TYPE
			SYNTAX OCTET STRING (SIZE (1..64))
			MAX-ACCESS read-write
			STATUS current
			DESCRIPTION
				"OLT port auto profile name"
			::= { sleEponOltControl 15 }

		
		-- 1.3.6.1.4.1.6296.101.20.2.2.16
		sleEponOltControlSC OBJECT-TYPE
			SYNTAX EnableFlag
			MAX-ACCESS read-write
			STATUS current
			DESCRIPTION
				"Description."
			::= { sleEponOltControl 16 }

		
		-- 1.3.6.1.4.1.6296.101.20.2.2.17
		sleEponOltControlSCAutoOnuBlock OBJECT-TYPE
			SYNTAX EnableFlag
			MAX-ACCESS read-write
			STATUS current
			DESCRIPTION
				"Description."
			::= { sleEponOltControl 17 }

		
		-- 1.3.6.1.4.1.6296.101.20.2.2.18
		sleEponOltControlUpgradeFilename OBJECT-TYPE
			SYNTAX OCTET STRING (SIZE (1..64))
			MAX-ACCESS read-write
			STATUS current
			DESCRIPTION
				"Description."
			::= { sleEponOltControl 18 }

		
		-- 1.3.6.1.4.1.6296.101.20.2.2.19
		sleEponOltControlKeyExchangeTimeout OBJECT-TYPE
			SYNTAX INTEGER (600..65535)
			MAX-ACCESS read-write
			STATUS current
			DESCRIPTION
				"Key Exchange Timeout"
			::= { sleEponOltControl 19 }

		
		-- 1.3.6.1.4.1.6296.101.20.2.2.20
		sleEponOltControlRssiStatus OBJECT-TYPE
			SYNTAX EnableFlag
			MAX-ACCESS read-write
			STATUS current
			DESCRIPTION
				"Epon olt rssi disable/enable."
			::= { sleEponOltControl 20 }

		
		-- 1.3.6.1.4.1.6296.101.20.2.3
		sleEponOltNotification OBJECT IDENTIFIER ::= { sleEponOlt 3 }

		
		-- 1.3.6.1.4.1.6296.101.20.2.3.1
		sleEponOltRegModeChanged NOTIFICATION-TYPE
			OBJECTS { sleEponOltControlRequest, sleEponOltControlTimeStamp, sleEponOltControlReqResult, sleEponOltControlOltIndex, sleEponOltControlRegMode
				 }
			STATUS current
			DESCRIPTION 
				"Description."
			::= { sleEponOltNotification 1 }

		
		-- 1.3.6.1.4.1.6296.101.20.2.3.2
		sleEponOltStatusChanged NOTIFICATION-TYPE
			OBJECTS { sleEponOltControlRequest, sleEponOltControlTimeStamp, sleEponOltControlReqResult, sleEponOltControlOltIndex, sleEponOltControlOltStatus
				 }
			STATUS current
			DESCRIPTION 
				"Description."
			::= { sleEponOltNotification 2 }

		
		-- 1.3.6.1.4.1.6296.101.20.2.3.3
		sleEponOltAttributesChanged NOTIFICATION-TYPE
			OBJECTS { sleEponOltControlRequest, sleEponOltControlTimeStamp, sleEponOltControlReqResult, sleEponOltControlOltIndex, sleEponOltControlDbaInternal, 
				sleEponOltControlDbaCycle, sleEponOltControlDbaDiscoveryFrequency, sleEponOltControlDbaDiscoveryLength }
			STATUS current
			DESCRIPTION 
				"Description."
			::= { sleEponOltNotification 3 }

		
		-- 1.3.6.1.4.1.6296.101.20.2.3.4
		sleEponOltProfileChanged NOTIFICATION-TYPE
			OBJECTS { sleEponOltControlRequest, sleEponOltControlTimeStamp, sleEponOltControlReqResult, sleEponOltControlOltIndex, sleEponOltControlProfile
				 }
			STATUS current
			DESCRIPTION 
				"Description."
			::= { sleEponOltNotification 4 }

		
		-- 1.3.6.1.4.1.6296.101.20.2.3.5
		sleEponOltSCChanged NOTIFICATION-TYPE
			OBJECTS { sleEponOltControlRequest, sleEponOltControlTimeStamp, sleEponOltControlReqResult, sleEponOltControlOltIndex, sleEponOltControlSC, 
				sleEponOltControlSCAutoOnuBlock }
			STATUS current
			DESCRIPTION 
				"Description."
			::= { sleEponOltNotification 5 }

		
		-- 1.3.6.1.4.1.6296.101.20.2.3.6
		sleEponOltUpgraded NOTIFICATION-TYPE
			OBJECTS { sleEponOltControlRequest, sleEponOltControlTimeStamp, sleEponOltControlReqResult, sleEponOltControlOltIndex, sleEponOltControlUpgradeFilename
				 }
			STATUS current
			DESCRIPTION 
				"Description."
			::= { sleEponOltNotification 6 }

		
		-- 1.3.6.1.4.1.6296.101.20.2.3.7
		sleEponOltReset NOTIFICATION-TYPE
			OBJECTS { sleEponOltControlRequest, sleEponOltControlTimeStamp, sleEponOltControlReqResult, sleEponOltControlOltIndex }
			STATUS current
			DESCRIPTION 
				"Description."
			::= { sleEponOltNotification 7 }

		
		-- 1.3.6.1.4.1.6296.101.20.2.3.8
		sleEponOltRssiStatusChanged NOTIFICATION-TYPE
			OBJECTS { sleEponOltControlRequest, sleEponOltControlTimeStamp, sleEponOltControlReqResult, sleEponOltControlOltIndex, sleEponOltControlRssiStatus
				 }
			STATUS current
			DESCRIPTION 
				"Description."
			::= { sleEponOltNotification 8 }

		
		-- 1.3.6.1.4.1.6296.101.20.2.4
		sleEponOltP2PTable OBJECT-TYPE
			SYNTAX SEQUENCE OF SleEponOltP2PEntry
			MAX-ACCESS not-accessible
			STATUS current
			DESCRIPTION
				"Description."
			::= { sleEponOlt 4 }

		
		-- 1.3.6.1.4.1.6296.101.20.2.4.1
		sleEponOltP2PEntry OBJECT-TYPE
			SYNTAX SleEponOltP2PEntry
			MAX-ACCESS not-accessible
			STATUS current
			DESCRIPTION
				"Description."
			INDEX { sleEponOltIndex, sleEponOltP2PIndex }
			::= { sleEponOltP2PTable 1 }

		
		SleEponOltP2PEntry ::=
			SEQUENCE { 
				sleEponOltP2PIndex
					INTEGER,
				sleEponOltP2PEnable
					OCTET STRING,
				sleEponOltP2POnuID1
					Integer32,
				sleEponOltP2POnuID2
					Integer32
			 }

		-- 1.3.6.1.4.1.6296.101.20.2.4.1.1
		sleEponOltP2PIndex OBJECT-TYPE
			SYNTAX INTEGER (1..20)
			MAX-ACCESS read-only
			STATUS current
			DESCRIPTION
				"p2p index"
			::= { sleEponOltP2PEntry 1 }

		
		-- 1.3.6.1.4.1.6296.101.20.2.4.1.2
		sleEponOltP2PEnable OBJECT-TYPE
			SYNTAX OCTET STRING
			MAX-ACCESS read-only
			STATUS current
			DESCRIPTION
				"status of p2p access control : enable "
			::= { sleEponOltP2PEntry 2 }

		
		-- 1.3.6.1.4.1.6296.101.20.2.4.1.3
		sleEponOltP2POnuID1 OBJECT-TYPE
			SYNTAX Integer32 (1..64)
			MAX-ACCESS read-only
			STATUS current
			DESCRIPTION
				"p2p onu id 1"
			::= { sleEponOltP2PEntry 3 }

		
		-- 1.3.6.1.4.1.6296.101.20.2.4.1.4
		sleEponOltP2POnuID2 OBJECT-TYPE
			SYNTAX Integer32 (1..64)
			MAX-ACCESS read-only
			STATUS current
			DESCRIPTION
				"p2p onu id 2"
			::= { sleEponOltP2PEntry 4 }

		
		-- 1.3.6.1.4.1.6296.101.20.2.5
		sleEponOltP2PControl OBJECT IDENTIFIER ::= { sleEponOlt 5 }

		
		-- 1.3.6.1.4.1.6296.101.20.2.5.1
		sleEponOltP2PControlRequest OBJECT-TYPE
			SYNTAX INTEGER { setEponOltP2PAccessControl(1) }
			MAX-ACCESS read-write
			STATUS current
			DESCRIPTION
				"The request of a user command"
			::= { sleEponOltP2PControl 1 }

		
		-- 1.3.6.1.4.1.6296.101.20.2.5.2
		sleEponOltP2PControlStatus OBJECT-TYPE
			SYNTAX SleControlStatusType
			MAX-ACCESS read-only
			STATUS current
			DESCRIPTION
				"The status of user command"
			::= { sleEponOltP2PControl 2 }

		
		-- 1.3.6.1.4.1.6296.101.20.2.5.3
		sleEponOltP2PControlTimer OBJECT-TYPE
			SYNTAX Gauge32
			MAX-ACCESS read-write
			STATUS current
			DESCRIPTION
				"The maximum time for the manager for a long running user command"
			::= { sleEponOltP2PControl 3 }

		
		-- 1.3.6.1.4.1.6296.101.20.2.5.4
		sleEponOltP2PControlTimeStamp OBJECT-TYPE
			SYNTAX TimeTicks
			MAX-ACCESS read-only
			STATUS current
			DESCRIPTION
				"The time stamp of the last command(end of command)"
			::= { sleEponOltP2PControl 4 }

		
		-- 1.3.6.1.4.1.6296.101.20.2.5.5
		sleEponOltP2PControlReqResult OBJECT-TYPE
			SYNTAX SleControlRequestResultType
			MAX-ACCESS read-only
			STATUS current
			DESCRIPTION
				"The result of the last user command"
			::= { sleEponOltP2PControl 5 }

		
		-- 1.3.6.1.4.1.6296.101.20.2.5.6
		sleEponOltP2PControlOltIndex OBJECT-TYPE
			SYNTAX Integer32
			MAX-ACCESS read-write
			STATUS current
			DESCRIPTION
				"OLT port Index"
			::= { sleEponOltP2PControl 6 }

		
		-- 1.3.6.1.4.1.6296.101.20.2.5.7
		sleEponOltP2PControlEnable OBJECT-TYPE
			SYNTAX EnableFlag
			MAX-ACCESS read-write
			STATUS current
			DESCRIPTION
				"enable(1), disable(2)  / DEFVAL : disable "
			DEFVAL { disable }
			::= { sleEponOltP2PControl 7 }

		
		-- 1.3.6.1.4.1.6296.101.20.2.5.8
		sleEponOltP2PControlOnuID1 OBJECT-TYPE
			SYNTAX Integer32 (1..64)
			MAX-ACCESS read-write
			STATUS current
			DESCRIPTION
				"P2p onu id 1."
			::= { sleEponOltP2PControl 8 }

		
		-- 1.3.6.1.4.1.6296.101.20.2.5.9
		sleEponOltP2PControlOnuID2 OBJECT-TYPE
			SYNTAX Integer32 (1..64)
			MAX-ACCESS read-write
			STATUS current
			DESCRIPTION
				"P2p onu id 2."
			::= { sleEponOltP2PControl 9 }

		
		-- 1.3.6.1.4.1.6296.101.20.2.6
		sleEponOltP2PNotification OBJECT IDENTIFIER ::= { sleEponOlt 6 }

		
		-- 1.3.6.1.4.1.6296.101.20.2.6.1
		sleEponOltP2PAccessControlChanged NOTIFICATION-TYPE
			OBJECTS { sleEponOltP2PControlRequest, sleEponOltP2PControlTimeStamp, sleEponOltP2PControlReqResult, sleEponOltP2PControlOltIndex }
			STATUS current
			DESCRIPTION 
				"Description."
			::= { sleEponOltP2PNotification 1 }

		
		-- 1.3.6.1.4.1.6296.101.20.2.7
		sleEponOltDMI OBJECT IDENTIFIER ::= { sleEponOlt 7 }

		
		-- 1.3.6.1.4.1.6296.101.20.2.7.1
		sleEponOltDMITable OBJECT-TYPE
			SYNTAX SEQUENCE OF SleEponOltDMIEntry
			MAX-ACCESS not-accessible
			STATUS current
			DESCRIPTION
				"Description."
			::= { sleEponOltDMI 1 }

		
		-- 1.3.6.1.4.1.6296.101.20.2.7.1.1
		sleEponOltDMIEntry OBJECT-TYPE
			SYNTAX SleEponOltDMIEntry
			MAX-ACCESS not-accessible
			STATUS current
			DESCRIPTION
				"Description."
			INDEX { sleEponOltIndex, sleEponOnuIndex }
			::= { sleEponOltDMITable 1 }

		
		SleEponOltDMIEntry ::=
			SEQUENCE { 
				sleEponOltDMITemper
					OCTET STRING,
				sleEponOltDMIVoltage
					OCTET STRING,
				sleEponOltDMITxBias
					OCTET STRING,
				sleEponOltDMITxPower
					OCTET STRING,
				sleEponOltDMIRxPower
					OCTET STRING
			 }

		-- 1.3.6.1.4.1.6296.101.20.2.7.1.1.1
		sleEponOltDMITemper OBJECT-TYPE
			SYNTAX OCTET STRING
			MAX-ACCESS read-only
			STATUS current
			DESCRIPTION
				"onu DMI Temperature ,range is (-128 ~ 127.99 C)
				"
			::= { sleEponOltDMIEntry 1 }

		
		-- 1.3.6.1.4.1.6296.101.20.2.7.1.1.2
		sleEponOltDMIVoltage OBJECT-TYPE
			SYNTAX OCTET STRING
			MAX-ACCESS read-only
			STATUS current
			DESCRIPTION
				"onu DMI voltage,range is (0 ~ 6.5535 V).
				
				"
			::= { sleEponOltDMIEntry 2 }

		
		-- 1.3.6.1.4.1.6296.101.20.2.7.1.1.3
		sleEponOltDMITxBias OBJECT-TYPE
			SYNTAX OCTET STRING
			MAX-ACCESS read-only
			STATUS current
			DESCRIPTION
				"onu DMI txbias,range is (0 ~ 131 mA).
				"
			::= { sleEponOltDMIEntry 3 }

		
		-- 1.3.6.1.4.1.6296.101.20.2.7.1.1.4
		sleEponOltDMITxPower OBJECT-TYPE
			SYNTAX OCTET STRING
			MAX-ACCESS read-only
			STATUS current
			DESCRIPTION
				"onu DMI txpower, range is (-40 ~ 8.1647 dBm).
				"
			::= { sleEponOltDMIEntry 4 }

		
		-- 1.3.6.1.4.1.6296.101.20.2.7.1.1.5
		sleEponOltDMIRxPower OBJECT-TYPE
			SYNTAX OCTET STRING
			MAX-ACCESS read-only
			STATUS current
			DESCRIPTION
				"onu DMI rxpower,range is (-40 ~ 8.1647 dBm)."
			::= { sleEponOltDMIEntry 5 }

		
		-- 1.3.6.1.4.1.6296.101.20.3
		sleEponOnu OBJECT IDENTIFIER ::= { sleEpon 3 }

		
		-- 1.3.6.1.4.1.6296.101.20.3.1
		sleEponOnuTable OBJECT-TYPE
			SYNTAX SEQUENCE OF SleEponOnuEntry
			MAX-ACCESS not-accessible
			STATUS current
			DESCRIPTION
				"Description."
			::= { sleEponOnu 1 }

		
		-- 1.3.6.1.4.1.6296.101.20.3.1.1
		sleEponOnuEntry OBJECT-TYPE
			SYNTAX SleEponOnuEntry
			MAX-ACCESS not-accessible
			STATUS current
			DESCRIPTION
				"Description."
			INDEX { sleEponOltIndex, sleEponOnuIndex }
			::= { sleEponOnuTable 1 }

		
		SleEponOnuEntry ::=
			SEQUENCE { 
				sleEponOnuIndex
					INTEGER,
				sleEponOnuLlid
					INTEGER,
				sleEponOnuRegMode
					INTEGER,
				sleEponOnuStatus
					INTEGER,
				sleEponOnuMacAddress
					MacAddress,
				sleEponOnuRtt
					INTEGER,
				sleEponOnuDescription
					OCTET STRING,
				sleEponOnuProfile
					OCTET STRING,
				sleEponOnuLoopbackProvision
					INTEGER,
				sleEponOnuVendor
					OCTET STRING,
				sleEponOnuFirmwareRev
					OCTET STRING,
				sleEponOnuTxPowerOffTimer
					INTEGER,
				sleEponOnuLgPathStatus
					INTEGER,
				sleEponOnuModelType
					OCTET STRING,
				sleEponOnuSipGlobalConfigMode
					INTEGER,
				sleEponOnuSipGlobalConfigIp
					IpAddress,
				sleEponOnuSipGlobalConfigNetmask
					IpAddress,
				sleEponOnuSipGlobalConfigGateway
					IpAddress,
				sleEponOnuSipGlobalUserName
					OCTET STRING,
				sleEponOnuSipGlobalPasswd
					OCTET STRING,
				sleEponOnuSipGlobalConfigVid
					INTEGER,
				sleEponOnuRxPower
					Gauge32,
				sleEponOnuRxPowerAlarmStatus
					INTEGER,
				sleEponOnuRssiInfo
					OCTET STRING,
				sleEponOnuLoopDetectUnblockStatus
					INTEGER,
				sleEponOnuUpgradeStatus
					INTEGER,
				sleEponOnuOltRssiStatus
					INTEGER,
				sleEponOnuOltRssiInfo
					OCTET STRING,
				sleEponOnuMultiLlid
					INTEGER,
				sleEponOnuMultiMacAddress
					MacAddress,
				sleEponOltDBAMutilLLidLinkOperate
					INTEGER
			 }

		-- 1.3.6.1.4.1.6296.101.20.3.1.1.1
		sleEponOnuIndex OBJECT-TYPE
			SYNTAX INTEGER (1..64)
			MAX-ACCESS read-only
			STATUS current
			DESCRIPTION
				"ONU Index"
			::= { sleEponOnuEntry 1 }

		
		-- 1.3.6.1.4.1.6296.101.20.3.1.1.2
		sleEponOnuLlid OBJECT-TYPE
			SYNTAX INTEGER (1..64)
			MAX-ACCESS read-only
			STATUS current
			DESCRIPTION
				"ONU LLID"
			::= { sleEponOnuEntry 2 }

		
		-- 1.3.6.1.4.1.6296.101.20.3.1.1.3
		sleEponOnuRegMode OBJECT-TYPE
			SYNTAX INTEGER
				{
				auto(1),
				manual(2),
				static(3)
				}
			MAX-ACCESS read-only
			STATUS current
			DESCRIPTION
				"ONU registration mode"
			DEFVAL { auto }
			::= { sleEponOnuEntry 3 }

		
		-- 1.3.6.1.4.1.6296.101.20.3.1.1.4
		sleEponOnuStatus OBJECT-TYPE
			SYNTAX INTEGER
				{
				inactive(1),
				deny(2),
				block(3),
				active(4),
				reset(5)
				}
			MAX-ACCESS read-only
			STATUS current
			DESCRIPTION
				"ONU current status"
			::= { sleEponOnuEntry 4 }

		
		-- 1.3.6.1.4.1.6296.101.20.3.1.1.5
		sleEponOnuMacAddress OBJECT-TYPE
			SYNTAX MacAddress
			MAX-ACCESS read-only
			STATUS current
			DESCRIPTION
				"ONU Hardware address"
			::= { sleEponOnuEntry 5 }

		
		-- 1.3.6.1.4.1.6296.101.20.3.1.1.6
		sleEponOnuRtt OBJECT-TYPE
			SYNTAX INTEGER
			MAX-ACCESS read-only
			STATUS current
			DESCRIPTION
				"ONU Round Trip Time"
			::= { sleEponOnuEntry 6 }

		
		-- 1.3.6.1.4.1.6296.101.20.3.1.1.7
		sleEponOnuDescription OBJECT-TYPE
			SYNTAX OCTET STRING (SIZE (1..64))
			MAX-ACCESS read-only
			STATUS current
			DESCRIPTION
				"ONU Description"
			::= { sleEponOnuEntry 7 }

		
		-- 1.3.6.1.4.1.6296.101.20.3.1.1.8
		sleEponOnuProfile OBJECT-TYPE
			SYNTAX OCTET STRING (SIZE (1..64))
			MAX-ACCESS read-only
			STATUS current
			DESCRIPTION
				"ONU assigned-profile"
			::= { sleEponOnuEntry 8 }

		
		-- 1.3.6.1.4.1.6296.101.20.3.1.1.9
		sleEponOnuLoopbackProvision OBJECT-TYPE
			SYNTAX INTEGER
			MAX-ACCESS read-only
			STATUS current
			DESCRIPTION
				"ONU loopback test result
				-2 : not exist
				-1 : fail
				 X > 0  : Time.
				"
			::= { sleEponOnuEntry 9 }

		
		-- 1.3.6.1.4.1.6296.101.20.3.1.1.10
		sleEponOnuVendor OBJECT-TYPE
			SYNTAX OCTET STRING
			MAX-ACCESS read-only
			STATUS current
			DESCRIPTION
				"The name of ONU vendor"
			::= { sleEponOnuEntry 10 }

		
		-- 1.3.6.1.4.1.6296.101.20.3.1.1.11
		sleEponOnuFirmwareRev OBJECT-TYPE
			SYNTAX OCTET STRING
			MAX-ACCESS read-only
			STATUS current
			DESCRIPTION
				"The vendor-specific firmware revision"
			::= { sleEponOnuEntry 11 }

		
		-- 1.3.6.1.4.1.6296.101.20.3.1.1.12
		sleEponOnuTxPowerOffTimer OBJECT-TYPE
			SYNTAX INTEGER (0 | 10..65535)
			MAX-ACCESS read-only
			STATUS current
			DESCRIPTION
				"Description."
			::= { sleEponOnuEntry 12 }

		
		-- 1.3.6.1.4.1.6296.101.20.3.1.1.13
		sleEponOnuLgPathStatus OBJECT-TYPE
			SYNTAX INTEGER
			MAX-ACCESS read-only
			STATUS current
			DESCRIPTION
				"Description."
			::= { sleEponOnuEntry 13 }

		
		-- 1.3.6.1.4.1.6296.101.20.3.1.1.14
		sleEponOnuModelType OBJECT-TYPE
			SYNTAX OCTET STRING (SIZE (1..32))
			MAX-ACCESS read-only
			STATUS current
			DESCRIPTION
				"Description."
			::= { sleEponOnuEntry 14 }

		
		-- 1.3.6.1.4.1.6296.101.20.3.1.1.15
		sleEponOnuSipGlobalConfigMode OBJECT-TYPE
			SYNTAX INTEGER
				{
				ip(0),
				dhcp(1),
				pppoe(2)
				}
			MAX-ACCESS read-only
			STATUS current
			DESCRIPTION
				"Description."
			::= { sleEponOnuEntry 15 }

		
		-- 1.3.6.1.4.1.6296.101.20.3.1.1.16
		sleEponOnuSipGlobalConfigIp OBJECT-TYPE
			SYNTAX IpAddress
			MAX-ACCESS read-only
			STATUS current
			DESCRIPTION
				"Description."
			::= { sleEponOnuEntry 16 }

		
		-- 1.3.6.1.4.1.6296.101.20.3.1.1.17
		sleEponOnuSipGlobalConfigNetmask OBJECT-TYPE
			SYNTAX IpAddress
			MAX-ACCESS read-only
			STATUS current
			DESCRIPTION
				"Description."
			::= { sleEponOnuEntry 17 }

		
		-- 1.3.6.1.4.1.6296.101.20.3.1.1.18
		sleEponOnuSipGlobalConfigGateway OBJECT-TYPE
			SYNTAX IpAddress
			MAX-ACCESS read-only
			STATUS current
			DESCRIPTION
				"Description."
			::= { sleEponOnuEntry 18 }

		
		-- 1.3.6.1.4.1.6296.101.20.3.1.1.19
		sleEponOnuSipGlobalUserName OBJECT-TYPE
			SYNTAX OCTET STRING (SIZE (0..32))
			MAX-ACCESS read-only
			STATUS current
			DESCRIPTION
				"Description."
			::= { sleEponOnuEntry 19 }

		
		-- 1.3.6.1.4.1.6296.101.20.3.1.1.20
		sleEponOnuSipGlobalPasswd OBJECT-TYPE
			SYNTAX OCTET STRING (SIZE (0..32))
			MAX-ACCESS read-only
			STATUS current
			DESCRIPTION
				"Description."
			::= { sleEponOnuEntry 20 }

		
		-- 1.3.6.1.4.1.6296.101.20.3.1.1.21
		sleEponOnuSipGlobalConfigVid OBJECT-TYPE
			SYNTAX INTEGER
			MAX-ACCESS read-only
			STATUS current
			DESCRIPTION
				"Description."
			::= { sleEponOnuEntry 21 }

		
		-- 1.3.6.1.4.1.6296.101.20.3.1.1.22
		sleEponOnuRxPower OBJECT-TYPE
			SYNTAX Gauge32
			MAX-ACCESS read-only
			STATUS current
			DESCRIPTION
				"Description."
			::= { sleEponOnuEntry 22 }

		
		-- 1.3.6.1.4.1.6296.101.20.3.1.1.23
		sleEponOnuRxPowerAlarmStatus OBJECT-TYPE
			SYNTAX INTEGER
			MAX-ACCESS read-write
			STATUS current
			DESCRIPTION
				"Onu Rx Optical power alarm state of olt-side.
				1: RX Optical Power Alarm - Caution (orange)
				2: RX Optical Power Alarm cleard - OK (Green)
				"
			::= { sleEponOnuEntry 23 }

		
		-- 1.3.6.1.4.1.6296.101.20.3.1.1.24
		sleEponOnuRssiInfo OBJECT-TYPE
			SYNTAX OCTET STRING
			MAX-ACCESS read-only
			STATUS current
			DESCRIPTION
				"Epon onu rssi-info."
			::= { sleEponOnuEntry 24 }

		
		-- 1.3.6.1.4.1.6296.101.20.3.1.1.25
		sleEponOnuLoopDetectUnblockStatus OBJECT-TYPE
			SYNTAX INTEGER
				{
				blocked(1),
				unblocked(2)
				}
			MAX-ACCESS read-only
			STATUS current
			DESCRIPTION
				"Epon onu loopdetect unblock status."
			::= { sleEponOnuEntry 25 }

		
		-- 1.3.6.1.4.1.6296.101.20.3.1.1.26
		sleEponOnuUpgradeStatus OBJECT-TYPE
			SYNTAX INTEGER
				{
				notUpgrade(1),
				inactiveONT(2),
				waitingUpgrade(3),
				firmwareSending(4),
				firmwareSend(5),
				writingFlashOnOnu(6),
				upgradeOK(7),
				upgradeFail(8)
				}
			MAX-ACCESS read-only
			STATUS current
			DESCRIPTION
				"Onu upgrade state."
			::= { sleEponOnuEntry 26 }

		
		-- 1.3.6.1.4.1.6296.101.20.3.1.1.27
		sleEponOnuOltRssiStatus OBJECT-TYPE
			SYNTAX INTEGER
				{
				na(0),
				enable(1),
				disable(2),
				average(3)
				}
			MAX-ACCESS read-only
			STATUS current
			DESCRIPTION
				"Epon olt rssi-info."
			::= { sleEponOnuEntry 27 }

		
		-- 1.3.6.1.4.1.6296.101.20.3.1.1.28
		sleEponOnuOltRssiInfo OBJECT-TYPE
			SYNTAX OCTET STRING
			MAX-ACCESS read-only
			STATUS current
			DESCRIPTION
				"Epon olt rssi-info value."
			::= { sleEponOnuEntry 28 }

		
		-- 1.3.6.1.4.1.6296.101.20.3.1.1.29
		sleEponOnuMultiLlid OBJECT-TYPE
			SYNTAX INTEGER (1..64)
			MAX-ACCESS read-only
			STATUS current
			DESCRIPTION
				"ONU Multi LLID"
			::= { sleEponOnuEntry 29 }

		
		-- 1.3.6.1.4.1.6296.101.20.3.1.1.30
		sleEponOnuMultiMacAddress OBJECT-TYPE
			SYNTAX MacAddress
			MAX-ACCESS read-only
			STATUS current
			DESCRIPTION
				"ONU Hardware address"
			::= { sleEponOnuEntry 30 }

		
		-- 1.3.6.1.4.1.6296.101.20.3.1.1.31
		sleEponOltDBAMutilLLidLinkOperate OBJECT-TYPE
			SYNTAX INTEGER
				{
				disable(0),
				enable(1)
				}
			MAX-ACCESS read-write
			STATUS current
			DESCRIPTION
				"DBA multi llid link."
			::= { sleEponOnuEntry 31 }

		
		-- 1.3.6.1.4.1.6296.101.20.3.2
		sleEponOnuControl OBJECT IDENTIFIER ::= { sleEponOnu 2 }

		
		-- 1.3.6.1.4.1.6296.101.20.3.2.1
		sleEponOnuControlRequest OBJECT-TYPE
			SYNTAX INTEGER
				{
				setEponOnuRegMode(1),
				setEponOnuStatus(2),
				setEponOnuAttributes(3),
				setEponOnuRegister(4),
				setEponOnuDeregister(5),
				setEponOnuProfile(6),
				setEponOnuUpgrade(7),
				setEPonOnuLoopbackProvision(8),
				setEponOnuTxPowerOffTimer(9),
				setEponOnuProfileByMac(10),
				setEponOnuDeregisterByMac(11),
				setEponOnuSipGlobalConfigIP(13),
				setEponOnuSipGlobalConfigDHCP(14),
				setEponOnuSipGlobalConfigPPPoE(15),
				destroyEponOnuSipGlobalConfig(16),
				setEponOnuPingTest(17),
				setEponOnuLoopDetectUnblock(18),
				setEponOltRssiOnuSingle(19),
				setDBAMultiLLidLinkEnable(20),
				setDBAMultLLidLinkDisable(21)
				}
			MAX-ACCESS read-write
			STATUS current
			DESCRIPTION
				"The request of a user command"
			::= { sleEponOnuControl 1 }

		
		-- 1.3.6.1.4.1.6296.101.20.3.2.2
		sleEponOnuControlStatus OBJECT-TYPE
			SYNTAX SleControlStatusType
			MAX-ACCESS read-only
			STATUS current
			DESCRIPTION
				"The status of user command"
			::= { sleEponOnuControl 2 }

		
		-- 1.3.6.1.4.1.6296.101.20.3.2.3
		sleEponOnuControlTimer OBJECT-TYPE
			SYNTAX Gauge32
			MAX-ACCESS read-write
			STATUS current
			DESCRIPTION
				"The maximum time for the manager for a long running user command"
			::= { sleEponOnuControl 3 }

		
		-- 1.3.6.1.4.1.6296.101.20.3.2.4
		sleEponOnuControlTimeStamp OBJECT-TYPE
			SYNTAX TimeTicks
			MAX-ACCESS read-only
			STATUS current
			DESCRIPTION
				"The time stamp of the last command(end of command)"
			::= { sleEponOnuControl 4 }

		
		-- 1.3.6.1.4.1.6296.101.20.3.2.5
		sleEponOnuControlReqResult OBJECT-TYPE
			SYNTAX SleControlRequestResultType
			MAX-ACCESS read-only
			STATUS current
			DESCRIPTION
				"The result of the last user command"
			::= { sleEponOnuControl 5 }

		
		-- 1.3.6.1.4.1.6296.101.20.3.2.6
		sleEponOnuControlOltIndex OBJECT-TYPE
			SYNTAX INTEGER (1..512)
			MAX-ACCESS read-write
			STATUS current
			DESCRIPTION
				"OLT index"
			::= { sleEponOnuControl 6 }

		
		-- 1.3.6.1.4.1.6296.101.20.3.2.7
		sleEponOnuControlOnuIndex OBJECT-TYPE
			SYNTAX INTEGER (1..64)
			MAX-ACCESS read-write
			STATUS current
			DESCRIPTION
				"ONU index <1-32>"
			::= { sleEponOnuControl 7 }

		
		-- 1.3.6.1.4.1.6296.101.20.3.2.8
		sleEponOnuControlRegMode OBJECT-TYPE
			SYNTAX INTEGER
				{
				auto(1),
				manual(2)
				}
			MAX-ACCESS read-write
			STATUS current
			DESCRIPTION
				"ONU register mode {auto(1), manual(2)}"
			DEFVAL { auto }
			::= { sleEponOnuControl 8 }

		
		-- 1.3.6.1.4.1.6296.101.20.3.2.9
		sleEponOnuControlOnuStatus OBJECT-TYPE
			SYNTAX INTEGER
				{
				inactive(1),
				deny(2),
				block(3),
				active(4),
				reset(5)
				}
			MAX-ACCESS read-write
			STATUS current
			DESCRIPTION
				"1 : inactive 
				2 : deny 
				3 : block
				4 : active
				5 : reset
				"
			::= { sleEponOnuControl 9 }

		
		-- 1.3.6.1.4.1.6296.101.20.3.2.10
		sleEponOnuControlMacAddress OBJECT-TYPE
			SYNTAX MacAddress
			MAX-ACCESS read-write
			STATUS current
			DESCRIPTION
				"ONU MAC address"
			::= { sleEponOnuControl 10 }

		
		-- 1.3.6.1.4.1.6296.101.20.3.2.11
		sleEponOnuControlDescription OBJECT-TYPE
			SYNTAX OCTET STRING
			MAX-ACCESS read-write
			STATUS current
			DESCRIPTION
				"ONU description"
			::= { sleEponOnuControl 11 }

		
		-- 1.3.6.1.4.1.6296.101.20.3.2.12
		sleEponOnuControlProfile OBJECT-TYPE
			SYNTAX OCTET STRING (SIZE (1..64))
			MAX-ACCESS read-write
			STATUS current
			DESCRIPTION
				"Profile name"
			::= { sleEponOnuControl 12 }

		
		-- 1.3.6.1.4.1.6296.101.20.3.2.13
		sleEponOnuControlUpgradePath OBJECT-TYPE
			SYNTAX OCTET STRING (SIZE (1..64))
			UNITS "byte"
			MAX-ACCESS read-write
			STATUS current
			DESCRIPTION
				"Upgrade path"
			::= { sleEponOnuControl 13 }

		
		-- 1.3.6.1.4.1.6296.101.20.3.2.14
		sleEponOnuControlLoopbackProvision OBJECT-TYPE
			SYNTAX INTEGER { test(1) }
			MAX-ACCESS read-write
			STATUS current
			DESCRIPTION
				"1 : test"
			::= { sleEponOnuControl 14 }

		
		-- 1.3.6.1.4.1.6296.101.20.3.2.15
		sleEponOnuControlTxPowerOffTimer OBJECT-TYPE
			SYNTAX INTEGER (0 | 10..65535)
			MAX-ACCESS read-write
			STATUS current
			DESCRIPTION
				"Description."
			::= { sleEponOnuControl 15 }

		
		-- 1.3.6.1.4.1.6296.101.20.3.2.18
		sleEponOnuControlSipGlobalConfigMode OBJECT-TYPE
			SYNTAX INTEGER
				{
				ip(0),
				dhcp(1),
				pppoe(2)
				}
			MAX-ACCESS read-write
			STATUS current
			DESCRIPTION
				"Description."
			::= { sleEponOnuControl 18 }

		
		-- 1.3.6.1.4.1.6296.101.20.3.2.19
		sleEponOnuControlSipGlobalConfigIp OBJECT-TYPE
			SYNTAX IpAddress
			MAX-ACCESS read-write
			STATUS current
			DESCRIPTION
				"Description."
			::= { sleEponOnuControl 19 }

		
		-- 1.3.6.1.4.1.6296.101.20.3.2.20
		sleEponOnuControlSipGlobalConfigNetmask OBJECT-TYPE
			SYNTAX IpAddress
			MAX-ACCESS read-write
			STATUS current
			DESCRIPTION
				"Description."
			::= { sleEponOnuControl 20 }

		
		-- 1.3.6.1.4.1.6296.101.20.3.2.21
		sleEponOnuControlSipGlobalConfigGateway OBJECT-TYPE
			SYNTAX IpAddress
			MAX-ACCESS read-write
			STATUS current
			DESCRIPTION
				"Description."
			::= { sleEponOnuControl 21 }

		
		-- 1.3.6.1.4.1.6296.101.20.3.2.22
		sleEponOnuControlSipGlobalConfigUserName OBJECT-TYPE
			SYNTAX OCTET STRING (SIZE (0..32))
			MAX-ACCESS read-write
			STATUS current
			DESCRIPTION
				"Description."
			::= { sleEponOnuControl 22 }

		
		-- 1.3.6.1.4.1.6296.101.20.3.2.23
		sleEponOnuControlSipGlobalConfigUserPasswd OBJECT-TYPE
			SYNTAX OCTET STRING (SIZE (0..32))
			MAX-ACCESS read-write
			STATUS current
			DESCRIPTION
				"Description."
			::= { sleEponOnuControl 23 }

		
		-- 1.3.6.1.4.1.6296.101.20.3.2.24
		sleEponOnuControlSipGlobalConfigVid OBJECT-TYPE
			SYNTAX INTEGER
			MAX-ACCESS read-write
			STATUS current
			DESCRIPTION
				"Description."
			::= { sleEponOnuControl 24 }

		
		-- 1.3.6.1.4.1.6296.101.20.3.2.25
		sleEponOnuControlPingCount OBJECT-TYPE
			SYNTAX Integer32 (1..20)
			MAX-ACCESS read-write
			STATUS current
			DESCRIPTION
				"Onu Ping Test count."
			::= { sleEponOnuControl 25 }

		
		-- 1.3.6.1.4.1.6296.101.20.3.3
		sleEponOnuNotification OBJECT IDENTIFIER ::= { sleEponOnu 3 }

		
		-- 1.3.6.1.4.1.6296.101.20.3.3.1
		sleEponOnuRegModeChanged NOTIFICATION-TYPE
			OBJECTS { sleEponOnuControlRequest, sleEponOnuControlTimeStamp, sleEponOnuControlReqResult, sleEponOnuControlOltIndex, sleEponOnuControlOnuIndex, 
				sleEponOnuControlRegMode }
			STATUS current
			DESCRIPTION 
				"Description."
			::= { sleEponOnuNotification 1 }

		
		-- 1.3.6.1.4.1.6296.101.20.3.3.2
		sleEponOnuStatusChanged NOTIFICATION-TYPE
			OBJECTS { sleEponOnuControlRequest, sleEponOnuControlTimeStamp, sleEponOnuControlReqResult, sleEponOnuControlOltIndex, sleEponOnuControlOnuIndex, 
				sleEponOnuControlOnuStatus }
			STATUS current
			DESCRIPTION 
				"Description."
			::= { sleEponOnuNotification 2 }

		
		-- 1.3.6.1.4.1.6296.101.20.3.3.3
		sleEponOnuAttibutesChanged NOTIFICATION-TYPE
			OBJECTS { sleEponOnuControlRequest, sleEponOnuControlTimeStamp, sleEponOnuControlReqResult, sleEponOnuControlOltIndex, sleEponOnuControlOnuIndex, 
				sleEponOnuControlDescription }
			STATUS current
			DESCRIPTION 
				"Description."
			::= { sleEponOnuNotification 3 }

		
		-- 1.3.6.1.4.1.6296.101.20.3.3.4
		sleEponOnuRegistered NOTIFICATION-TYPE
			OBJECTS { sleEponOnuControlRequest, sleEponOnuControlTimeStamp, sleEponOnuControlReqResult, sleEponOnuControlOltIndex, sleEponOnuControlOnuIndex, 
				sleEponOnuControlMacAddress, sleEponOnuControlDescription }
			STATUS current
			DESCRIPTION 
				"Description."
			::= { sleEponOnuNotification 4 }

		
		-- 1.3.6.1.4.1.6296.101.20.3.3.5
		sleEponOnuDeregistered NOTIFICATION-TYPE
			OBJECTS { sleEponOnuControlRequest, sleEponOnuControlTimeStamp, sleEponOnuControlReqResult, sleEponOnuControlOltIndex, sleEponOnuControlOnuIndex
				 }
			STATUS current
			DESCRIPTION 
				"Description."
			::= { sleEponOnuNotification 5 }

		
		-- 1.3.6.1.4.1.6296.101.20.3.3.6
		sleEponOnuProfileChanged NOTIFICATION-TYPE
			OBJECTS { sleEponOnuControlRequest, sleEponOnuControlTimeStamp, sleEponOnuControlReqResult, sleEponOnuControlOltIndex, sleEponOnuControlOnuIndex, 
				sleEponOnuControlProfile }
			STATUS current
			DESCRIPTION 
				"Description."
			::= { sleEponOnuNotification 6 }

		
		-- 1.3.6.1.4.1.6296.101.20.3.3.7
		sleEponOnuUpgraded NOTIFICATION-TYPE
			OBJECTS { sleEponOnuControlRequest, sleEponOnuControlTimeStamp, sleEponOnuControlReqResult, sleEponOnuControlOltIndex, sleEponOnuControlOnuIndex, 
				sleEponOnuControlUpgradePath }
			STATUS current
			DESCRIPTION 
				"Description."
			::= { sleEponOnuNotification 7 }

		
		-- 1.3.6.1.4.1.6296.101.20.3.3.8
		sleEponOnuLoopbackProvisioned NOTIFICATION-TYPE
			OBJECTS { sleEponOnuControlRequest, sleEponOnuControlTimeStamp, sleEponOnuControlReqResult, sleEponOnuControlOltIndex, sleEponOnuControlOnuIndex, 
				sleEponOnuControlLoopbackProvision }
			STATUS current
			DESCRIPTION 
				"Description."
			::= { sleEponOnuNotification 8 }

		
		-- 1.3.6.1.4.1.6296.101.20.3.3.9
		sleEponOnuTxPowerOffChanged NOTIFICATION-TYPE
			OBJECTS { sleEponOnuControlRequest, sleEponOnuControlTimeStamp, sleEponOnuControlReqResult, sleEponOnuControlOltIndex, sleEponOnuControlOnuIndex, 
				sleEponOnuControlTxPowerOffTimer }
			STATUS current
			DESCRIPTION 
				"Description."
			::= { sleEponOnuNotification 9 }

		
		-- 1.3.6.1.4.1.6296.101.20.3.3.10
		sleEponOnuFristRegisteredOnAutoToManual NOTIFICATION-TYPE
			OBJECTS { sysDescr, sleEponOltIndex, sleEponOnuIndex }
			STATUS current
			DESCRIPTION 
				"Description."
			::= { sleEponOnuNotification 10 }

		
		-- 1.3.6.1.4.1.6296.101.20.3.3.11
		sleEponOnuProfileChangedByMac NOTIFICATION-TYPE
			OBJECTS { sleEponOnuControlRequest, sleEponOnuControlTimeStamp, sleEponOnuControlReqResult, sleEponOnuControlOltIndex, sleEponOnuControlMacAddress, 
				sleEponOnuControlProfile }
			STATUS current
			DESCRIPTION 
				"Description."
			::= { sleEponOnuNotification 11 }

		
		-- 1.3.6.1.4.1.6296.101.20.3.3.12
		sleEponOnuDeregisteredByMac NOTIFICATION-TYPE
			OBJECTS { sleEponOnuControlRequest, sleEponOnuControlTimeStamp, sleEponOnuControlReqResult, sleEponOnuControlOltIndex, sleEponOnuControlMacAddress
				 }
			STATUS current
			DESCRIPTION 
				"Description."
			::= { sleEponOnuNotification 12 }

		
		-- 1.3.6.1.4.1.6296.101.20.3.3.13
		sleEponOnuLgpauthStatusChanged NOTIFICATION-TYPE
			OBJECTS { sleEponOnuControlRequest, sleEponOnuControlTimeStamp, sleEponOnuControlReqResult, sleEponOnuControlOltIndex, sleEponOnuControlOnuIndex
				 }
			STATUS current
			DESCRIPTION 
				"Lgpauth status changed trap."
			::= { sleEponOnuNotification 13 }

		
		-- 1.3.6.1.4.1.6296.101.20.3.3.14
		sleEponOnuSipGlobalConfigIpChanged NOTIFICATION-TYPE
			OBJECTS { sleEponOnuControlRequest, sleEponOnuControlTimeStamp, sleEponOnuControlReqResult, sleEponOnuControlOltIndex, sleEponOnuControlOnuIndex, 
				sleEponOnuControlSipGlobalConfigMode, sleEponOnuControlSipGlobalConfigIp, sleEponOnuControlSipGlobalConfigNetmask, sleEponOnuControlSipGlobalConfigGateway, sleEponOnuControlSipGlobalConfigVid
				 }
			STATUS current
			DESCRIPTION 
				"Description."
			::= { sleEponOnuNotification 14 }

		
		-- 1.3.6.1.4.1.6296.101.20.3.3.15
		sleEponOnuSipGlobalConfigDhcpChanged NOTIFICATION-TYPE
			OBJECTS { sleEponOnuControlRequest, sleEponOnuControlTimeStamp, sleEponOnuControlReqResult, sleEponOnuControlOltIndex, sleEponOnuControlOnuIndex, 
				sleEponOnuControlSipGlobalConfigMode, sleEponOnuControlSipGlobalConfigVid }
			STATUS current
			DESCRIPTION 
				"Description."
			::= { sleEponOnuNotification 15 }

		
		-- 1.3.6.1.4.1.6296.101.20.3.3.16
		sleEponOnuSipGlobalConfigPPPoEChanged NOTIFICATION-TYPE
			OBJECTS { sleEponOnuControlRequest, sleEponOnuControlTimeStamp, sleEponOnuControlReqResult, sleEponOnuControlOltIndex, sleEponOnuControlOnuIndex, 
				sleEponOnuControlSipGlobalConfigMode, sleEponOnuControlSipGlobalConfigUserName, sleEponOnuControlSipGlobalConfigUserPasswd, sleEponOnuControlSipGlobalConfigVid }
			STATUS current
			DESCRIPTION 
				"Description."
			::= { sleEponOnuNotification 16 }

		
		-- 1.3.6.1.4.1.6296.101.20.3.3.17
		sleEponOnuSipGlobalConfigDestroyed NOTIFICATION-TYPE
			OBJECTS { sleEponOnuControlRequest, sleEponOnuControlTimeStamp, sleEponOnuControlReqResult, sleEponOnuControlOltIndex, sleEponOnuControlOnuIndex
				 }
			STATUS current
			DESCRIPTION 
				"Description."
			::= { sleEponOnuNotification 17 }

		
		-- 1.3.6.1.4.1.6296.101.20.3.3.18
		sleEponOnuPingTest NOTIFICATION-TYPE
			OBJECTS { sleEponOnuControlRequest, sleEponOnuControlTimeStamp, sleEponOnuControlReqResult, sleEponOnuControlOltIndex, sleEponOnuControlOnuIndex, 
				sleEponOnuControlPingCount }
			STATUS current
			DESCRIPTION 
				"Description."
			::= { sleEponOnuNotification 18 }

		
		-- 1.3.6.1.4.1.6296.101.20.3.3.19
		sleEponOnuLoopDectectUnblock NOTIFICATION-TYPE
			OBJECTS { sleEponOnuControlRequest, sleEponOnuControlTimeStamp, sleEponOnuControlReqResult, sleEponOnuControlOltIndex, sleEponOnuControlOnuIndex
				 }
			STATUS current
			DESCRIPTION 
				"Loop dectect unblock trap."
			::= { sleEponOnuNotification 19 }

		
		-- 1.3.6.1.4.1.6296.101.20.3.3.20
		setEponOnuOltRssiOnuSingle NOTIFICATION-TYPE
			OBJECTS { sleEponOnuControlRequest, sleEponOnuControlTimeStamp, sleEponOnuControlReqResult, sleEponOnuControlOltIndex, sleEponOnuControlOnuIndex
				 }
			STATUS current
			DESCRIPTION 
				"Description."
			::= { sleEponOnuNotification 20 }

		
		-- 1.3.6.1.4.1.6296.101.20.3.3.21
		sleEponOnuDBAMultiLLidLink NOTIFICATION-TYPE
			OBJECTS { sleEponOnuControlRequest, sleEponOnuControlTimeStamp, sleEponOnuControlReqResult, sleEponOnuControlOltIndex, sleEponOnuControlOnuIndex
				 }
			STATUS current
			DESCRIPTION 
				"Multi-llid link enable and disable trap."
			::= { sleEponOnuNotification 21 }

		
		-- 1.3.6.1.4.1.6296.101.20.3.4
		sleEponOnuDMI OBJECT IDENTIFIER ::= { sleEponOnu 4 }

		
		-- 1.3.6.1.4.1.6296.101.20.3.4.1
		sleEponOnuDMITable OBJECT-TYPE
			SYNTAX SEQUENCE OF SleEponOnuDMIEntry
			MAX-ACCESS not-accessible
			STATUS current
			DESCRIPTION
				"Description."
			::= { sleEponOnuDMI 1 }

		
		-- 1.3.6.1.4.1.6296.101.20.3.4.1.1
		sleEponOnuDMIEntry OBJECT-TYPE
			SYNTAX SleEponOnuDMIEntry
			MAX-ACCESS not-accessible
			STATUS current
			DESCRIPTION
				"Description."
			INDEX { sleEponOltIndex, sleEponOnuIndex }
			::= { sleEponOnuDMITable 1 }

		
		SleEponOnuDMIEntry ::=
			SEQUENCE { 
				sleEponOnuDMITemper
					OCTET STRING,
				sleEponOnuDMIVoltage
					OCTET STRING,
				sleEponOnuDMITxBias
					OCTET STRING,
				sleEponOnuDMITxPower
					OCTET STRING,
				sleEponOnuDMIRxPower
					OCTET STRING
			 }

		-- 1.3.6.1.4.1.6296.101.20.3.4.1.1.1
		sleEponOnuDMITemper OBJECT-TYPE
			SYNTAX OCTET STRING
			MAX-ACCESS read-only
			STATUS current
			DESCRIPTION
				"Onu DMI Temperature ,range is (-128 ~ 127.99 C)
				"
			::= { sleEponOnuDMIEntry 1 }

		
		-- 1.3.6.1.4.1.6296.101.20.3.4.1.1.2
		sleEponOnuDMIVoltage OBJECT-TYPE
			SYNTAX OCTET STRING
			MAX-ACCESS read-only
			STATUS current
			DESCRIPTION
				"Onu DMI voltage,range is (0 ~ 6.5535 V).
				
				"
			::= { sleEponOnuDMIEntry 2 }

		
		-- 1.3.6.1.4.1.6296.101.20.3.4.1.1.3
		sleEponOnuDMITxBias OBJECT-TYPE
			SYNTAX OCTET STRING
			MAX-ACCESS read-only
			STATUS current
			DESCRIPTION
				"Onu DMI txbias,range is (0 ~ 131 mA).
				"
			::= { sleEponOnuDMIEntry 3 }

		
		-- 1.3.6.1.4.1.6296.101.20.3.4.1.1.4
		sleEponOnuDMITxPower OBJECT-TYPE
			SYNTAX OCTET STRING
			MAX-ACCESS read-only
			STATUS current
			DESCRIPTION
				"Onu DMI txpower, range is (-40 ~ 8.1647 dBm).
				"
			::= { sleEponOnuDMIEntry 4 }

		
		-- 1.3.6.1.4.1.6296.101.20.3.4.1.1.5
		sleEponOnuDMIRxPower OBJECT-TYPE
			SYNTAX OCTET STRING
			MAX-ACCESS read-only
			STATUS current
			DESCRIPTION
				"Onu DMI rxpower,range is (-40 ~ 8.1647 dBm)."
			::= { sleEponOnuDMIEntry 5 }

		
		-- 1.3.6.1.4.1.6296.101.20.3.4.2
		sleEponOnuDMIThresholdTable OBJECT-TYPE
			SYNTAX SEQUENCE OF SleEponOnuDMIThresholdEntry
			MAX-ACCESS not-accessible
			STATUS current
			DESCRIPTION
				"Description."
			::= { sleEponOnuDMI 2 }

		
		-- 1.3.6.1.4.1.6296.101.20.3.4.2.1
		sleEponOnuDMIThresholdEntry OBJECT-TYPE
			SYNTAX SleEponOnuDMIThresholdEntry
			MAX-ACCESS not-accessible
			STATUS current
			DESCRIPTION
				"Description."
			INDEX { sleEponOltIndex, sleEponOnuIndex }
			::= { sleEponOnuDMIThresholdTable 1 }

		
		SleEponOnuDMIThresholdEntry ::=
			SEQUENCE { 
				sleEponOnuDMIThresholdWarnTemperLow
					Integer32,
				sleEponOnuDMIThresholdWarnTemperHigh
					Integer32,
				sleEponOnuDMIThresholdAlarmTemperLow
					Integer32,
				sleEponOnuDMIThresholdAlarmTemperHigh
					Integer32,
				sleEponOnuDMIThresholdWarnVoltageLow
					Integer32,
				sleEponOnuDMIThresholdWarnVoltageHigh
					Integer32,
				sleEponOnuDMIThresholdAlarmVoltageLow
					Integer32,
				sleEponOnuDMIThresholdAlarmVoltageHigh
					Integer32,
				sleEponOnuDMIThresholdWarnTxbiasLow
					Integer32,
				sleEponOnuDMIThresholdWarnTxbiasHigh
					Integer32,
				sleEponOnuDMIThresholdAlarmTxbiasLow
					Integer32,
				sleEponOnuDMIThresholdAlarmTxbiasHigh
					Integer32,
				sleEponOnuDMIThresholdWarnTxPowerLow
					Integer32,
				sleEponOnuDMIThresholdWarnTxPowerHigh
					Integer32,
				sleEponOnuDMIThresholdAlarmTxPowerLow
					Integer32,
				sleEponOnuDMIThresholdAlarmTxPowerHigh
					Integer32,
				sleEponOnuDMIThresholdWarnRxPowerLow
					Integer32,
				sleEponOnuDMIThresholdWarnRxPowerHigh
					Integer32,
				sleEponOnuDMIThresholdAlarmRxPowerLow
					Integer32,
				sleEponOnuDMIThresholdAlarmRxPowerHigh
					Integer32
			 }

		-- 1.3.6.1.4.1.6296.101.20.3.4.2.1.1
		sleEponOnuDMIThresholdWarnTemperLow OBJECT-TYPE
			SYNTAX Integer32
			MAX-ACCESS read-only
			STATUS current
			DESCRIPTION
				"The Temperature threshold -128~127.99(C)
				It must be devided by 10000."
			::= { sleEponOnuDMIThresholdEntry 1 }

		
		-- 1.3.6.1.4.1.6296.101.20.3.4.2.1.2
		sleEponOnuDMIThresholdWarnTemperHigh OBJECT-TYPE
			SYNTAX Integer32
			MAX-ACCESS read-only
			STATUS current
			DESCRIPTION
				"The Temperature threshold -128~127.99(C)
				It must be devided by 10000."
			::= { sleEponOnuDMIThresholdEntry 2 }

		
		-- 1.3.6.1.4.1.6296.101.20.3.4.2.1.3
		sleEponOnuDMIThresholdAlarmTemperLow OBJECT-TYPE
			SYNTAX Integer32
			MAX-ACCESS read-only
			STATUS current
			DESCRIPTION
				"The Temperature threshold -128~127.99(C)
				It must be devided by 10000."
			::= { sleEponOnuDMIThresholdEntry 3 }

		
		-- 1.3.6.1.4.1.6296.101.20.3.4.2.1.4
		sleEponOnuDMIThresholdAlarmTemperHigh OBJECT-TYPE
			SYNTAX Integer32
			MAX-ACCESS read-only
			STATUS current
			DESCRIPTION
				"The Temperature threshold -128~127.99(C)
				It must be devided by 10000."
			::= { sleEponOnuDMIThresholdEntry 4 }

		
		-- 1.3.6.1.4.1.6296.101.20.3.4.2.1.5
		sleEponOnuDMIThresholdWarnVoltageLow OBJECT-TYPE
			SYNTAX Integer32
			MAX-ACCESS read-only
			STATUS current
			DESCRIPTION
				"The Voltage threshold 0~6.5535(V)
				It must be devided by 10000."
			::= { sleEponOnuDMIThresholdEntry 5 }

		
		-- 1.3.6.1.4.1.6296.101.20.3.4.2.1.6
		sleEponOnuDMIThresholdWarnVoltageHigh OBJECT-TYPE
			SYNTAX Integer32
			MAX-ACCESS read-only
			STATUS current
			DESCRIPTION
				"The Voltage threshold 0~6.5535(V)
				It must be devided by 10000."
			::= { sleEponOnuDMIThresholdEntry 6 }

		
		-- 1.3.6.1.4.1.6296.101.20.3.4.2.1.7
		sleEponOnuDMIThresholdAlarmVoltageLow OBJECT-TYPE
			SYNTAX Integer32
			MAX-ACCESS read-only
			STATUS current
			DESCRIPTION
				"The Voltage threshold 0~6.5535(V)
				It must be devided by 10000."
			::= { sleEponOnuDMIThresholdEntry 7 }

		
		-- 1.3.6.1.4.1.6296.101.20.3.4.2.1.8
		sleEponOnuDMIThresholdAlarmVoltageHigh OBJECT-TYPE
			SYNTAX Integer32
			MAX-ACCESS read-only
			STATUS current
			DESCRIPTION
				"The Voltage threshold 0~6.5535(V)
				It must be devided by 10000."
			::= { sleEponOnuDMIThresholdEntry 8 }

		
		-- 1.3.6.1.4.1.6296.101.20.3.4.2.1.9
		sleEponOnuDMIThresholdWarnTxbiasLow OBJECT-TYPE
			SYNTAX Integer32 (0..131)
			MAX-ACCESS read-only
			STATUS current
			DESCRIPTION
				"The Txbias Threshold 0~131(mA)
				It must be devided by 10000.
				"
			::= { sleEponOnuDMIThresholdEntry 9 }

		
		-- 1.3.6.1.4.1.6296.101.20.3.4.2.1.10
		sleEponOnuDMIThresholdWarnTxbiasHigh OBJECT-TYPE
			SYNTAX Integer32 (0..131)
			MAX-ACCESS read-only
			STATUS current
			DESCRIPTION
				"The Txbias Threshold 0~131(mA)
				It must be devided by 10000."
			::= { sleEponOnuDMIThresholdEntry 10 }

		
		-- 1.3.6.1.4.1.6296.101.20.3.4.2.1.11
		sleEponOnuDMIThresholdAlarmTxbiasLow OBJECT-TYPE
			SYNTAX Integer32 (0..131)
			MAX-ACCESS read-only
			STATUS current
			DESCRIPTION
				"The Txbias Threshold 0~131(mA)
				It must be devided by 10000.
				"
			::= { sleEponOnuDMIThresholdEntry 11 }

		
		-- 1.3.6.1.4.1.6296.101.20.3.4.2.1.12
		sleEponOnuDMIThresholdAlarmTxbiasHigh OBJECT-TYPE
			SYNTAX Integer32 (0..131)
			MAX-ACCESS read-only
			STATUS current
			DESCRIPTION
				"The Txbias Threshold 0~131(mA)
				It must be devided by 10000.
				"
			::= { sleEponOnuDMIThresholdEntry 12 }

		
		-- 1.3.6.1.4.1.6296.101.20.3.4.2.1.13
		sleEponOnuDMIThresholdWarnTxPowerLow OBJECT-TYPE
			SYNTAX Integer32
			MAX-ACCESS read-only
			STATUS current
			DESCRIPTION
				"The Power threshold -40~8,1647 (dBm)
				It must be devided by 10000.
				"
			::= { sleEponOnuDMIThresholdEntry 13 }

		
		-- 1.3.6.1.4.1.6296.101.20.3.4.2.1.14
		sleEponOnuDMIThresholdWarnTxPowerHigh OBJECT-TYPE
			SYNTAX Integer32
			MAX-ACCESS read-only
			STATUS current
			DESCRIPTION
				"The Power threshold -40~8,1647 (dBm)
				It must be devided by 10000."
			::= { sleEponOnuDMIThresholdEntry 14 }

		
		-- 1.3.6.1.4.1.6296.101.20.3.4.2.1.15
		sleEponOnuDMIThresholdAlarmTxPowerLow OBJECT-TYPE
			SYNTAX Integer32
			MAX-ACCESS read-only
			STATUS current
			DESCRIPTION
				"The Power threshold -40~8,1647 (dBm)
				It must be devided by 10000.
				"
			::= { sleEponOnuDMIThresholdEntry 15 }

		
		-- 1.3.6.1.4.1.6296.101.20.3.4.2.1.16
		sleEponOnuDMIThresholdAlarmTxPowerHigh OBJECT-TYPE
			SYNTAX Integer32
			MAX-ACCESS read-only
			STATUS current
			DESCRIPTION
				"The Power threshold -40~8,1647 (dBm)
				It must be devided by 10000.
				"
			::= { sleEponOnuDMIThresholdEntry 16 }

		
		-- 1.3.6.1.4.1.6296.101.20.3.4.2.1.17
		sleEponOnuDMIThresholdWarnRxPowerLow OBJECT-TYPE
			SYNTAX Integer32
			MAX-ACCESS read-only
			STATUS current
			DESCRIPTION
				"The Power threshold -40~8,1647 (dBm)
				It must be devided by 10000.
				"
			::= { sleEponOnuDMIThresholdEntry 17 }

		
		-- 1.3.6.1.4.1.6296.101.20.3.4.2.1.18
		sleEponOnuDMIThresholdWarnRxPowerHigh OBJECT-TYPE
			SYNTAX Integer32
			MAX-ACCESS read-only
			STATUS current
			DESCRIPTION
				"The Power threshold -40~8,1647 (dBm)
				It must be devided by 10000.
				"
			::= { sleEponOnuDMIThresholdEntry 18 }

		
		-- 1.3.6.1.4.1.6296.101.20.3.4.2.1.19
		sleEponOnuDMIThresholdAlarmRxPowerLow OBJECT-TYPE
			SYNTAX Integer32
			MAX-ACCESS read-only
			STATUS current
			DESCRIPTION
				"The Power threshold -40~8,1647 (dBm)
				It must be devided by 10000.
				"
			::= { sleEponOnuDMIThresholdEntry 19 }

		
		-- 1.3.6.1.4.1.6296.101.20.3.4.2.1.20
		sleEponOnuDMIThresholdAlarmRxPowerHigh OBJECT-TYPE
			SYNTAX Integer32
			MAX-ACCESS read-only
			STATUS current
			DESCRIPTION
				"The Power threshold -40~8,1647 (dBm)
				It must be devided by 10000.
				"
			::= { sleEponOnuDMIThresholdEntry 20 }

		
		-- 1.3.6.1.4.1.6296.101.20.3.4.3
		sleEponOnuDMIThresholdControl OBJECT IDENTIFIER ::= { sleEponOnuDMI 3 }

		
		-- 1.3.6.1.4.1.6296.101.20.3.4.3.1
		sleEponOnuDMIThresholdControlRequest OBJECT-TYPE
			SYNTAX INTEGER
				{
				setEponOnuDMIThreshold(1),
				noEponOnuDMIThreshold(2)
				}
			MAX-ACCESS read-write
			STATUS current
			DESCRIPTION
				"The request of a user command"
			::= { sleEponOnuDMIThresholdControl 1 }

		
		-- 1.3.6.1.4.1.6296.101.20.3.4.3.2
		sleEponOnuDMIThresholdControlStatus OBJECT-TYPE
			SYNTAX SleControlStatusType
			MAX-ACCESS read-only
			STATUS current
			DESCRIPTION
				"The status of user command"
			::= { sleEponOnuDMIThresholdControl 2 }

		
		-- 1.3.6.1.4.1.6296.101.20.3.4.3.3
		sleEponOnuDMIThresholdControlTimer OBJECT-TYPE
			SYNTAX Gauge32
			MAX-ACCESS read-write
			STATUS current
			DESCRIPTION
				"The maximum time for the manager for a long running user command"
			::= { sleEponOnuDMIThresholdControl 3 }

		
		-- 1.3.6.1.4.1.6296.101.20.3.4.3.4
		sleEponOnuDMIThresholdControlTimeStamp OBJECT-TYPE
			SYNTAX TimeTicks
			MAX-ACCESS read-only
			STATUS current
			DESCRIPTION
				"The time stamp of the last command(end of command)"
			::= { sleEponOnuDMIThresholdControl 4 }

		
		-- 1.3.6.1.4.1.6296.101.20.3.4.3.5
		sleEponOnuDMIThresholdControlReqResult OBJECT-TYPE
			SYNTAX SleControlRequestResultType
			MAX-ACCESS read-only
			STATUS current
			DESCRIPTION
				"The result of the last user command"
			::= { sleEponOnuDMIThresholdControl 5 }

		
		-- 1.3.6.1.4.1.6296.101.20.3.4.3.6
		sleEponOnuDMIThresholdControlOltIndex OBJECT-TYPE
			SYNTAX INTEGER (1..255)
			MAX-ACCESS read-write
			STATUS current
			DESCRIPTION
				"OLT index"
			::= { sleEponOnuDMIThresholdControl 6 }

		
		-- 1.3.6.1.4.1.6296.101.20.3.4.3.7
		sleEponOnuDMIThresholdControlOnuIndex OBJECT-TYPE
			SYNTAX Integer32 (1..64)
			MAX-ACCESS read-write
			STATUS current
			DESCRIPTION
				"ONU index"
			::= { sleEponOnuDMIThresholdControl 7 }

		
		-- 1.3.6.1.4.1.6296.101.20.3.4.3.8
		sleEponOnuDMIThresholdControlMonitorType OBJECT-TYPE
			SYNTAX INTEGER
				{
				temper(1),
				voltage(2),
				txbias(3),
				txpower(4),
				rxpower(5)
				}
			MAX-ACCESS read-write
			STATUS current
			DESCRIPTION
				"Onu DMI monitor type."
			::= { sleEponOnuDMIThresholdControl 8 }

		
		-- 1.3.6.1.4.1.6296.101.20.3.4.3.9
		sleEponOnuDMIThresholdControlMode OBJECT-TYPE
			SYNTAX INTEGER
				{
				warning(1),
				alarm(2)
				}
			MAX-ACCESS read-write
			STATUS current
			DESCRIPTION
				"Onu DMI monitor threshold mode ,alarm or warning."
			::= { sleEponOnuDMIThresholdControl 9 }

		
		-- 1.3.6.1.4.1.6296.101.20.3.4.3.10
		sleEponOnuDMIThresholdControlLowThreshold OBJECT-TYPE
			SYNTAX Integer32
			MAX-ACCESS read-write
			STATUS current
			DESCRIPTION
				"onu DMI monitor low threshold, it must multiplied by 10000 and less than high threshold.
				temper threshold (-128 ~ 127.99 C)
				voltage threshold (0 ~ 6.5535 V)
				txbias threshold (0 ~ 131 mA)
				txpower threshold (-40 ~ 8.1647 dBm)
				rxpower threshold (-40 ~ 8.1647 dBm)"
			::= { sleEponOnuDMIThresholdControl 10 }

		
		-- 1.3.6.1.4.1.6296.101.20.3.4.3.11
		sleEponOnuDMIThresholdControlHighThreshold OBJECT-TYPE
			SYNTAX Integer32
			MAX-ACCESS read-write
			STATUS current
			DESCRIPTION
				"onu DMI monitor high threshold,it must multiplied by 10000 and more than low threshold.
				temper threshold (-128 ~ 127.99 C)
				voltage threshold (0 ~ 6.5535 V)
				txbias threshold (0 ~ 131 mA)
				txpower threshold (-40 ~ 8.1647 dBm)
				rxpower threshold (-40 ~ 8.1647 dBm)"
			::= { sleEponOnuDMIThresholdControl 11 }

		
		-- 1.3.6.1.4.1.6296.101.20.3.4.4
		sleEponOnuDMIThresholdNotification OBJECT IDENTIFIER ::= { sleEponOnuDMI 4 }

		
		-- 1.3.6.1.4.1.6296.101.20.3.4.4.1
		sleEponOnuDMIMonitorThresholdChanged NOTIFICATION-TYPE
			OBJECTS { sleEponOnuDmiThresholdControlRequest, sleEponOnuDmiThresholdControlTimeStamp, sleEponOnuDmiThresholdControlReqResult, sleEponOnuDmiThresholdControlOltIndex, sleEponOnuDmiThresholdControlOnuIndex, 
				sleEponOnuDmiThresholdControlMonitorType, sleEponOnuDmiThresholdControlMode, sleEponOnuDmiThresholdControlLowThreshold, sleEponOnuDmiThresholdControlHighThreshold }
			STATUS current
			DESCRIPTION 
				"Description."
			::= { sleEponOnuDMIThresholdNotification 1 }

		
		-- 1.3.6.1.4.1.6296.101.20.4
		sleEponOnuBridge OBJECT IDENTIFIER ::= { sleEpon 4 }

		
		-- 1.3.6.1.4.1.6296.101.20.4.1
		sleEponOnuVlan OBJECT IDENTIFIER ::= { sleEponOnuBridge 1 }

		
		-- 1.3.6.1.4.1.6296.101.20.4.1.1
		sleEponOnuVlanTable OBJECT-TYPE
			SYNTAX SEQUENCE OF SleEponOnuVlanEntry
			MAX-ACCESS not-accessible
			STATUS current
			DESCRIPTION
				"Description."
			::= { sleEponOnuVlan 1 }

		
		-- 1.3.6.1.4.1.6296.101.20.4.1.1.1
		sleEponOnuVlanEntry OBJECT-TYPE
			SYNTAX SleEponOnuVlanEntry
			MAX-ACCESS not-accessible
			STATUS current
			DESCRIPTION
				"Description."
			INDEX { sleEponOltIndex, sleEponOnuIndex, sleEponOnuVlanIndex }
			::= { sleEponOnuVlanTable 1 }

		
		SleEponOnuVlanEntry ::=
			SEQUENCE { 
				sleEponOnuVlanIndex
					VlanIndex,
				sleEponOnuVlanEgressPorts
					PortList,
				sleEponOnuVlanUntaggedPorts
					PortList
			 }

		-- 1.3.6.1.4.1.6296.101.20.4.1.1.1.1
		sleEponOnuVlanIndex OBJECT-TYPE
			SYNTAX VlanIndex (1..4094)
			MAX-ACCESS read-only
			STATUS current
			DESCRIPTION
				"The index of ONU VLAN"
			::= { sleEponOnuVlanEntry 1 }

		
		-- 1.3.6.1.4.1.6296.101.20.4.1.1.1.2
		sleEponOnuVlanEgressPorts OBJECT-TYPE
			SYNTAX PortList
			MAX-ACCESS read-only
			STATUS current
			DESCRIPTION
				"The set of ports which are transmitting traffic for this ONU VLAN as either tagged or untagged frames."
			::= { sleEponOnuVlanEntry 2 }

		
		-- 1.3.6.1.4.1.6296.101.20.4.1.1.1.3
		sleEponOnuVlanUntaggedPorts OBJECT-TYPE
			SYNTAX PortList
			MAX-ACCESS read-only
			STATUS current
			DESCRIPTION
				"The set of ports which are transmitting traffic for this VLAN as untagged frames"
			::= { sleEponOnuVlanEntry 3 }

		
		-- 1.3.6.1.4.1.6296.101.20.4.2
		sleEponOnuPort OBJECT IDENTIFIER ::= { sleEponOnuBridge 2 }

		
		-- 1.3.6.1.4.1.6296.101.20.4.2.1
		sleEponOnuPortTable OBJECT-TYPE
			SYNTAX SEQUENCE OF SleEponOnuPortEntry
			MAX-ACCESS not-accessible
			STATUS current
			DESCRIPTION
				"Description."
			::= { sleEponOnuPort 1 }

		
		-- 1.3.6.1.4.1.6296.101.20.4.2.1.1
		sleEponOnuPortEntry OBJECT-TYPE
			SYNTAX SleEponOnuPortEntry
			MAX-ACCESS not-accessible
			STATUS current
			DESCRIPTION
				"Description."
			INDEX { sleEponOltIndex, sleEponOnuIndex, sleEponOnuPortIndex }
			::= { sleEponOnuPortTable 1 }

		
		SleEponOnuPortEntry ::=
			SEQUENCE { 
				sleEponOnuPortIndex
					INTEGER,
				sleEponOnuPortAdminStatus
					INTEGER,
				sleEponOnuPortOperStatus
					INTEGER,
				sleEponOnuPortNego
					INTEGER,
				sleEponOnuPortSpeed
					Integer32,
				sleEponOnuPortDuplex
					INTEGER,
				sleEponOnuPortMaxHost
					Integer32,
				sleEponOnuPortPvid
					VlanIndex,
				sleEponOnuPortIngressRateLimitMode
					INTEGER,
				sleEponOnuPortIngressRateLimit
					INTEGER,
				sleEponOnuPortEgressRateLimit
					INTEGER,
				sleEponOnuPortFlowControl
					INTEGER,
				sleEponOnuPortAgingTime
					Integer32,
				sleEponOnuPortForwardMode
					EnableFlag
			 }

		-- 1.3.6.1.4.1.6296.101.20.4.2.1.1.1
		sleEponOnuPortIndex OBJECT-TYPE
			SYNTAX INTEGER (1..256)
			MAX-ACCESS read-only
			STATUS current
			DESCRIPTION
				"The index of the ONU port"
			::= { sleEponOnuPortEntry 1 }

		
		-- 1.3.6.1.4.1.6296.101.20.4.2.1.1.2
		sleEponOnuPortAdminStatus OBJECT-TYPE
			SYNTAX INTEGER
				{
				na(0),
				enable(1),
				disable(2)
				}
			MAX-ACCESS read-only
			STATUS current
			DESCRIPTION
				"The desired state of the ONU port"
			::= { sleEponOnuPortEntry 2 }

		
		-- 1.3.6.1.4.1.6296.101.20.4.2.1.1.3
		sleEponOnuPortOperStatus OBJECT-TYPE
			SYNTAX INTEGER
				{
				na(0),
				enable(1),
				disable(2)
				}
			MAX-ACCESS read-only
			STATUS current
			DESCRIPTION
				"The current operational state of the ONU port"
			::= { sleEponOnuPortEntry 3 }

		
		-- 1.3.6.1.4.1.6296.101.20.4.2.1.1.4
		sleEponOnuPortNego OBJECT-TYPE
			SYNTAX INTEGER
				{
				na(0),
				on(1),
				off(2)
				}
			MAX-ACCESS read-only
			STATUS current
			DESCRIPTION
				"It's auto-negotiation for a port, automatically to match the transmission speed and the duplex mode of the attached device"
			::= { sleEponOnuPortEntry 4 }

		
		-- 1.3.6.1.4.1.6296.101.20.4.2.1.1.5
		sleEponOnuPortSpeed OBJECT-TYPE
			SYNTAX Integer32
			MAX-ACCESS read-only
			STATUS current
			DESCRIPTION
				"It express port speed that configure transmit rate of each port."
			::= { sleEponOnuPortEntry 5 }

		
		-- 1.3.6.1.4.1.6296.101.20.4.2.1.1.6
		sleEponOnuPortDuplex OBJECT-TYPE
			SYNTAX INTEGER
				{
				na(0),
				full(1),
				half(2)
				}
			MAX-ACCESS read-only
			STATUS current
			DESCRIPTION
				"It express half duplex or full duplex mode. Only unidirectional communication is possible on half duplex mode and bi-directional communication is possible on full duplex mode to transmit packet for two ways."
			::= { sleEponOnuPortEntry 6 }

		
		-- 1.3.6.1.4.1.6296.101.20.4.2.1.1.7
		sleEponOnuPortMaxHost OBJECT-TYPE
			SYNTAX Integer32
			MAX-ACCESS read-only
			STATUS current
			DESCRIPTION
				"It can limit the number of users by configuring maximum number of users also named as Max host for each ONU port"
			::= { sleEponOnuPortEntry 7 }

		
		-- 1.3.6.1.4.1.6296.101.20.4.2.1.1.8
		sleEponOnuPortPvid OBJECT-TYPE
			SYNTAX VlanIndex
			MAX-ACCESS read-only
			STATUS current
			DESCRIPTION
				"It is PVID that configure in ONU port"
			::= { sleEponOnuPortEntry 8 }

		
		-- 1.3.6.1.4.1.6296.101.20.4.2.1.1.9
		sleEponOnuPortIngressRateLimitMode OBJECT-TYPE
			SYNTAX INTEGER
				{
				all(0),
				multiBroadUnicast(1),
				multiBroadcast(2),
				broadcast(3)
				}
			MAX-ACCESS read-only
			STATUS current
			DESCRIPTION
				"It is rate limit mode in Ingress"
			::= { sleEponOnuPortEntry 9 }

		
		-- 1.3.6.1.4.1.6296.101.20.4.2.1.1.10
		sleEponOnuPortIngressRateLimit OBJECT-TYPE
			SYNTAX INTEGER (0 | 62..100000)
			MAX-ACCESS read-only
			STATUS current
			DESCRIPTION
				"It is configurable port rate limit in Ingress"
			::= { sleEponOnuPortEntry 10 }

		
		-- 1.3.6.1.4.1.6296.101.20.4.2.1.1.11
		sleEponOnuPortEgressRateLimit OBJECT-TYPE
			SYNTAX INTEGER (0 | 62..100000)
			MAX-ACCESS read-only
			STATUS current
			DESCRIPTION
				"It is configurable port rate limit in Egress"
			::= { sleEponOnuPortEntry 11 }

		
		-- 1.3.6.1.4.1.6296.101.20.4.2.1.1.12
		sleEponOnuPortFlowControl OBJECT-TYPE
			SYNTAX INTEGER
				{
				none(0),
				on(1),
				off(2)
				}
			MAX-ACCESS read-only
			STATUS current
			DESCRIPTION
				"Description."
			::= { sleEponOnuPortEntry 12 }

		
		-- 1.3.6.1.4.1.6296.101.20.4.2.1.1.13
		sleEponOnuPortAgingTime OBJECT-TYPE
			SYNTAX Integer32
			MAX-ACCESS read-only
			STATUS current
			DESCRIPTION
				"onu max-host aging time."
			::= { sleEponOnuPortEntry 13 }

		
		-- 1.3.6.1.4.1.6296.101.20.4.2.1.1.14
		sleEponOnuPortForwardMode OBJECT-TYPE
			SYNTAX EnableFlag
			MAX-ACCESS read-write
			STATUS current
			DESCRIPTION
				"onu max-host forward mode."
			::= { sleEponOnuPortEntry 14 }

		
		-- 1.3.6.1.4.1.6296.101.20.4.2.2
		sleEponOnuPortControl OBJECT IDENTIFIER ::= { sleEponOnuPort 2 }

		
		-- 1.3.6.1.4.1.6296.101.20.4.2.2.1
		sleEponOnuPortControlRequest OBJECT-TYPE
			SYNTAX INTEGER { setEponOnuPortReset(1) }
			MAX-ACCESS read-write
			STATUS current
			DESCRIPTION
				"The request of a user command"
			::= { sleEponOnuPortControl 1 }

		
		-- 1.3.6.1.4.1.6296.101.20.4.2.2.2
		sleEponOnuPortControlStatus OBJECT-TYPE
			SYNTAX SleControlStatusType
			MAX-ACCESS read-only
			STATUS current
			DESCRIPTION
				"The status of user command"
			::= { sleEponOnuPortControl 2 }

		
		-- 1.3.6.1.4.1.6296.101.20.4.2.2.3
		sleEponOnuPortControlTimer OBJECT-TYPE
			SYNTAX Gauge32
			MAX-ACCESS read-write
			STATUS current
			DESCRIPTION
				"The maximum time for the manager for a long running user command"
			::= { sleEponOnuPortControl 3 }

		
		-- 1.3.6.1.4.1.6296.101.20.4.2.2.4
		sleEponOnuPortControlTimeStamp OBJECT-TYPE
			SYNTAX TimeTicks
			MAX-ACCESS read-only
			STATUS current
			DESCRIPTION
				"The time stamp of the last command(end of command)"
			::= { sleEponOnuPortControl 4 }

		
		-- 1.3.6.1.4.1.6296.101.20.4.2.2.5
		sleEponOnuPortControlReqResult OBJECT-TYPE
			SYNTAX SleControlRequestResultType
			MAX-ACCESS read-only
			STATUS current
			DESCRIPTION
				"The result of the last user command"
			::= { sleEponOnuPortControl 5 }

		
		-- 1.3.6.1.4.1.6296.101.20.4.2.2.6
		sleEponOnuPortControlOltIndex OBJECT-TYPE
			SYNTAX INTEGER (1..512)
			MAX-ACCESS read-write
			STATUS current
			DESCRIPTION
				"OLT port Index"
			::= { sleEponOnuPortControl 6 }

		
		-- 1.3.6.1.4.1.6296.101.20.4.2.2.7
		sleEponOnuPortControlOnuIndex OBJECT-TYPE
			SYNTAX INTEGER (1..64)
			MAX-ACCESS read-write
			STATUS current
			DESCRIPTION
				"ONU Index"
			::= { sleEponOnuPortControl 7 }

		
		-- 1.3.6.1.4.1.6296.101.20.4.2.2.8
		sleEponOnuPortControlPortIndex OBJECT-TYPE
			SYNTAX INTEGER (1..256)
			MAX-ACCESS read-write
			STATUS current
			DESCRIPTION
				"The index of the ONU port"
			::= { sleEponOnuPortControl 8 }

		
		-- 1.3.6.1.4.1.6296.101.20.4.2.3
		sleEponOnuPortNotification OBJECT IDENTIFIER ::= { sleEponOnuPort 3 }

		
		-- 1.3.6.1.4.1.6296.101.20.4.2.3.1
		sleEponOnuPortReset NOTIFICATION-TYPE
			OBJECTS { sleEponOnuPortControlRequest, sleEponOnuPortControlTimeStamp, sleEponOnuPortControlReqResult, sleEponOnuPortControlOltIndex, sleEponOnuPortControlOnuIndex, 
				sleEponOnuPortControlPortIndex }
			STATUS current
			DESCRIPTION 
				"Description."
			::= { sleEponOnuPortNotification 1 }

		
		-- 1.3.6.1.4.1.6296.101.20.4.3
		sleEponOnuFdb OBJECT IDENTIFIER ::= { sleEponOnuBridge 3 }

		
		-- 1.3.6.1.4.1.6296.101.20.4.3.1
		sleEponOnuFdbTable OBJECT-TYPE
			SYNTAX SEQUENCE OF SleEponOnuFdbEntry
			MAX-ACCESS not-accessible
			STATUS current
			DESCRIPTION
				"Description."
			::= { sleEponOnuFdb 1 }

		
		-- 1.3.6.1.4.1.6296.101.20.4.3.1.1
		sleEponOnuFdbEntry OBJECT-TYPE
			SYNTAX SleEponOnuFdbEntry
			MAX-ACCESS not-accessible
			STATUS current
			DESCRIPTION
				"Description."
			INDEX { sleEponOltIndex, sleEponOnuIndex, sleEponOnuFdbMacAddress }
			::= { sleEponOnuFdbTable 1 }

		
		SleEponOnuFdbEntry ::=
			SEQUENCE { 
				sleEponOnuFdbMacAddress
					MacAddress,
				sleEponOnuFdbType
					INTEGER,
				sleEponOnuFdbPermission
					INTEGER
			 }

		-- 1.3.6.1.4.1.6296.101.20.4.3.1.1.1
		sleEponOnuFdbMacAddress OBJECT-TYPE
			SYNTAX MacAddress
			MAX-ACCESS read-only
			STATUS current
			DESCRIPTION
				"The fdb address of ONT"
			::= { sleEponOnuFdbEntry 1 }

		
		-- 1.3.6.1.4.1.6296.101.20.4.3.1.1.2
		sleEponOnuFdbType OBJECT-TYPE
			SYNTAX INTEGER
				{
				local(0),
				static(1),
				dynamic(2)
				}
			MAX-ACCESS read-only
			STATUS current
			DESCRIPTION
				"The type of fdb address."
			::= { sleEponOnuFdbEntry 2 }

		
		-- 1.3.6.1.4.1.6296.101.20.4.3.1.1.3
		sleEponOnuFdbPermission OBJECT-TYPE
			SYNTAX INTEGER
				{
				deny(0),
				permit(1)
				}
			MAX-ACCESS read-only
			STATUS current
			DESCRIPTION
				"Description."
			::= { sleEponOnuFdbEntry 3 }

		
		-- 1.3.6.1.4.1.6296.101.20.4.3.2
		sleEponOnuFdbControl OBJECT IDENTIFIER ::= { sleEponOnuFdb 2 }

		
		-- 1.3.6.1.4.1.6296.101.20.4.3.2.1
		sleEponOnuFdbControlRequest OBJECT-TYPE
			SYNTAX INTEGER { clearOltMac(1) }
			MAX-ACCESS read-write
			STATUS current
			DESCRIPTION
				"Description."
			::= { sleEponOnuFdbControl 1 }

		
		-- 1.3.6.1.4.1.6296.101.20.4.3.2.2
		sleEponOnuFdbControlStatus OBJECT-TYPE
			SYNTAX SleControlStatusType
			MAX-ACCESS read-only
			STATUS current
			DESCRIPTION
				"Description."
			::= { sleEponOnuFdbControl 2 }

		
		-- 1.3.6.1.4.1.6296.101.20.4.3.2.3
		sleEponOnuFdbControlTimer OBJECT-TYPE
			SYNTAX Gauge32
			MAX-ACCESS read-write
			STATUS current
			DESCRIPTION
				"Description."
			::= { sleEponOnuFdbControl 3 }

		
		-- 1.3.6.1.4.1.6296.101.20.4.3.2.4
		sleEponOnuFdbControlTimeStamp OBJECT-TYPE
			SYNTAX TimeTicks
			MAX-ACCESS read-only
			STATUS current
			DESCRIPTION
				"Description."
			::= { sleEponOnuFdbControl 4 }

		
		-- 1.3.6.1.4.1.6296.101.20.4.3.2.5
		sleEponOnuFdbControlReqResult OBJECT-TYPE
			SYNTAX SleControlRequestResultType
			MAX-ACCESS read-only
			STATUS current
			DESCRIPTION
				"Description."
			::= { sleEponOnuFdbControl 5 }

		
		-- 1.3.6.1.4.1.6296.101.20.4.3.2.6
		sleEponOnuFdbControlOltIndex OBJECT-TYPE
			SYNTAX INTEGER (1..512)
			MAX-ACCESS read-write
			STATUS current
			DESCRIPTION
				"Description."
			::= { sleEponOnuFdbControl 6 }

		
		-- 1.3.6.1.4.1.6296.101.20.4.3.2.7
		sleEponOnuFdbControlOnuIndex OBJECT-TYPE
			SYNTAX INTEGER (1..64)
			MAX-ACCESS read-write
			STATUS current
			DESCRIPTION
				"Description."
			::= { sleEponOnuFdbControl 7 }

		
		-- 1.3.6.1.4.1.6296.101.20.4.3.2.8
		sleEponOnuFdbControlType OBJECT-TYPE
			SYNTAX INTEGER
				{
				dynamic(1),
				static(2),
				all(3)
				}
			MAX-ACCESS read-write
			STATUS current
			DESCRIPTION
				"Description."
			::= { sleEponOnuFdbControl 8 }

		
		-- 1.3.6.1.4.1.6296.101.20.4.3.3
		sleEponOnuFdbNotification OBJECT IDENTIFIER ::= { sleEponOnuFdb 3 }

		
		-- 1.3.6.1.4.1.6296.101.20.4.3.3.1
		sleEponOnuFdbMacCleared NOTIFICATION-TYPE
			OBJECTS { sleEponOnuFdbControlRequest, sleEponOnuFdbControlTimeStamp, sleEponOnuFdbControlReqResult, sleEponOnuFdbControlOltIndex, sleEponOnuFdbControlOnuIndex, 
				sleEponOnuFdbControlType }
			STATUS current
			DESCRIPTION 
				"Description."
			::= { sleEponOnuFdbNotification 1 }

		
		-- 1.3.6.1.4.1.6296.101.20.4.4
		sleEponOnuUserMac OBJECT IDENTIFIER ::= { sleEponOnuBridge 4 }

		
		-- 1.3.6.1.4.1.6296.101.20.4.4.1
		sleEponOnuUserMacTable OBJECT-TYPE
			SYNTAX SEQUENCE OF SleEponOnuUserMacEntry
			MAX-ACCESS not-accessible
			STATUS current
			DESCRIPTION
				"Description."
			::= { sleEponOnuUserMac 1 }

		
		-- 1.3.6.1.4.1.6296.101.20.4.4.1.1
		sleEponOnuUserMacEntry OBJECT-TYPE
			SYNTAX SleEponOnuUserMacEntry
			MAX-ACCESS not-accessible
			STATUS current
			DESCRIPTION
				"Description."
			INDEX { sleEponOltIndex, sleEponOnuIndex, sleEponOnuUserMacIndex }
			::= { sleEponOnuUserMacTable 1 }

		
		SleEponOnuUserMacEntry ::=
			SEQUENCE { 
				sleEponOnuUserMacIndex
					INTEGER,
				sleEponOnuUserMacMacAddress
					MacAddress,
				sleEponOnuUserMacUsedTime
					TimeTicks
			 }

		-- 1.3.6.1.4.1.6296.101.20.4.4.1.1.1
		sleEponOnuUserMacIndex OBJECT-TYPE
			SYNTAX INTEGER (1..8)
			MAX-ACCESS read-only
			STATUS current
			DESCRIPTION
				"Description."
			::= { sleEponOnuUserMacEntry 1 }

		
		-- 1.3.6.1.4.1.6296.101.20.4.4.1.1.2
		sleEponOnuUserMacMacAddress OBJECT-TYPE
			SYNTAX MacAddress
			MAX-ACCESS read-only
			STATUS current
			DESCRIPTION
				"Description."
			::= { sleEponOnuUserMacEntry 2 }

		
		-- 1.3.6.1.4.1.6296.101.20.4.4.1.1.3
		sleEponOnuUserMacUsedTime OBJECT-TYPE
			SYNTAX TimeTicks
			MAX-ACCESS read-only
			STATUS current
			DESCRIPTION
				"Description."
			::= { sleEponOnuUserMacEntry 3 }

		
		-- 1.3.6.1.4.1.6296.101.20.4.5
		sleEponOnuSubscriber OBJECT IDENTIFIER ::= { sleEponOnuBridge 5 }

		
		-- 1.3.6.1.4.1.6296.101.20.4.5.1
		sleEponOnuSubscriberCurrentTable OBJECT-TYPE
			SYNTAX SEQUENCE OF SleEponOnuSubscriberCurrentEntry
			MAX-ACCESS not-accessible
			STATUS current
			DESCRIPTION
				"Description."
			::= { sleEponOnuSubscriber 1 }

		
		-- 1.3.6.1.4.1.6296.101.20.4.5.1.1
		sleEponOnuSubscriberCurrentEntry OBJECT-TYPE
			SYNTAX SleEponOnuSubscriberCurrentEntry
			MAX-ACCESS not-accessible
			STATUS current
			DESCRIPTION
				"Description."
			INDEX { sleEponOltIndex, sleEponOnuIndex, sleEponOnuSubscriberCurrentIpAddress }
			::= { sleEponOnuSubscriberCurrentTable 1 }

		
		SleEponOnuSubscriberCurrentEntry ::=
			SEQUENCE { 
				sleEponOnuSubscriberCurrentIpAddress
					IpAddress,
				sleEponOnuSubscriberCurrentMacAddress
					MacAddress,
				sleEponOnuSubscriberCurrentPort
					INTEGER,
				sleEponOnuSubscriberCurrentTime
					Gauge32
			 }

		-- 1.3.6.1.4.1.6296.101.20.4.5.1.1.1
		sleEponOnuSubscriberCurrentIpAddress OBJECT-TYPE
			SYNTAX IpAddress
			MAX-ACCESS read-only
			STATUS current
			DESCRIPTION
				"Description."
			::= { sleEponOnuSubscriberCurrentEntry 1 }

		
		-- 1.3.6.1.4.1.6296.101.20.4.5.1.1.2
		sleEponOnuSubscriberCurrentMacAddress OBJECT-TYPE
			SYNTAX MacAddress
			MAX-ACCESS read-only
			STATUS current
			DESCRIPTION
				"Description."
			::= { sleEponOnuSubscriberCurrentEntry 2 }

		
		-- 1.3.6.1.4.1.6296.101.20.4.5.1.1.3
		sleEponOnuSubscriberCurrentPort OBJECT-TYPE
			SYNTAX INTEGER (1..256)
			MAX-ACCESS read-only
			STATUS current
			DESCRIPTION
				"Description."
			::= { sleEponOnuSubscriberCurrentEntry 3 }

		
		-- 1.3.6.1.4.1.6296.101.20.4.5.1.1.4
		sleEponOnuSubscriberCurrentTime OBJECT-TYPE
			SYNTAX Gauge32
			MAX-ACCESS read-only
			STATUS current
			DESCRIPTION
				"Description."
			::= { sleEponOnuSubscriberCurrentEntry 4 }

		
		-- 1.3.6.1.4.1.6296.101.20.4.5.2
		sleEponOnuSubscriberHistoryTable OBJECT-TYPE
			SYNTAX SEQUENCE OF SleEponOnuSubscriberHistoryEntry
			MAX-ACCESS not-accessible
			STATUS current
			DESCRIPTION
				"Description."
			::= { sleEponOnuSubscriber 2 }

		
		-- 1.3.6.1.4.1.6296.101.20.4.5.2.1
		sleEponOnuSubscriberHistoryEntry OBJECT-TYPE
			SYNTAX SleEponOnuSubscriberHistoryEntry
			MAX-ACCESS not-accessible
			STATUS current
			DESCRIPTION
				"Description."
			INDEX { sleEponOltIndex, sleEponOnuIndex, sleEponOnuSubscriberHistoryTime, sleEponOnuSubscriberHistoryIpAddress }
			::= { sleEponOnuSubscriberHistoryTable 1 }

		
		SleEponOnuSubscriberHistoryEntry ::=
			SEQUENCE { 
				sleEponOnuSubscriberHistoryIpAddress
					IpAddress,
				sleEponOnuSubscriberHistoryMacAddress
					MacAddress,
				sleEponOnuSubscriberHistoryPort
					INTEGER,
				sleEponOnuSubscriberHistoryTime
					Gauge32
			 }

		-- 1.3.6.1.4.1.6296.101.20.4.5.2.1.1
		sleEponOnuSubscriberHistoryIpAddress OBJECT-TYPE
			SYNTAX IpAddress
			MAX-ACCESS read-only
			STATUS current
			DESCRIPTION
				"Description."
			::= { sleEponOnuSubscriberHistoryEntry 1 }

		
		-- 1.3.6.1.4.1.6296.101.20.4.5.2.1.2
		sleEponOnuSubscriberHistoryMacAddress OBJECT-TYPE
			SYNTAX MacAddress
			MAX-ACCESS read-only
			STATUS current
			DESCRIPTION
				"Description."
			::= { sleEponOnuSubscriberHistoryEntry 2 }

		
		-- 1.3.6.1.4.1.6296.101.20.4.5.2.1.3
		sleEponOnuSubscriberHistoryPort OBJECT-TYPE
			SYNTAX INTEGER (1..256)
			MAX-ACCESS read-only
			STATUS current
			DESCRIPTION
				"Description."
			::= { sleEponOnuSubscriberHistoryEntry 3 }

		
		-- 1.3.6.1.4.1.6296.101.20.4.5.2.1.4
		sleEponOnuSubscriberHistoryTime OBJECT-TYPE
			SYNTAX Gauge32 (1..65535)
			MAX-ACCESS read-only
			STATUS current
			DESCRIPTION
				"Description."
			::= { sleEponOnuSubscriberHistoryEntry 4 }

		
		-- 1.3.6.1.4.1.6296.101.20.4.5.3
		sleEponOnuSubscriberControl OBJECT IDENTIFIER ::= { sleEponOnuSubscriber 3 }

		
		-- 1.3.6.1.4.1.6296.101.20.4.5.3.1
		sleEponOnuSubscriberControlRequest OBJECT-TYPE
			SYNTAX INTEGER
				{
				clearSubscriberHistoryOlt(1),
				clearSubscriberHistoryOnu(2)
				}
			MAX-ACCESS read-write
			STATUS current
			DESCRIPTION
				"Description."
			::= { sleEponOnuSubscriberControl 1 }

		
		-- 1.3.6.1.4.1.6296.101.20.4.5.3.2
		sleEponOnuSubscriberControlStatus OBJECT-TYPE
			SYNTAX SleControlStatusType
			MAX-ACCESS read-only
			STATUS current
			DESCRIPTION
				"Description."
			::= { sleEponOnuSubscriberControl 2 }

		
		-- 1.3.6.1.4.1.6296.101.20.4.5.3.3
		sleEponOnuSubscriberControlTimer OBJECT-TYPE
			SYNTAX Gauge32
			MAX-ACCESS read-write
			STATUS current
			DESCRIPTION
				"Description."
			::= { sleEponOnuSubscriberControl 3 }

		
		-- 1.3.6.1.4.1.6296.101.20.4.5.3.4
		sleEponOnuSubscriberControlTimeStamp OBJECT-TYPE
			SYNTAX Counter64
			MAX-ACCESS read-only
			STATUS current
			DESCRIPTION
				"Description."
			::= { sleEponOnuSubscriberControl 4 }

		
		-- 1.3.6.1.4.1.6296.101.20.4.5.3.5
		sleEponOnuSubscriberControlReqResult OBJECT-TYPE
			SYNTAX Integer32
			MAX-ACCESS read-write
			STATUS current
			DESCRIPTION
				"Description."
			::= { sleEponOnuSubscriberControl 5 }

		
		-- 1.3.6.1.4.1.6296.101.20.4.5.3.6
		sleEponOnuSubscriberControlOltIndex OBJECT-TYPE
			SYNTAX INTEGER (1..512)
			MAX-ACCESS read-write
			STATUS current
			DESCRIPTION
				"Description."
			::= { sleEponOnuSubscriberControl 6 }

		
		-- 1.3.6.1.4.1.6296.101.20.4.5.3.7
		sleEponOnuSubscriberControlOnuIndex OBJECT-TYPE
			SYNTAX INTEGER (1..64)
			MAX-ACCESS read-write
			STATUS current
			DESCRIPTION
				"Description."
			::= { sleEponOnuSubscriberControl 7 }

		
		-- 1.3.6.1.4.1.6296.101.20.4.5.4
		sleEponOnuSubscriberNotification OBJECT IDENTIFIER ::= { sleEponOnuSubscriber 4 }

		
		-- 1.3.6.1.4.1.6296.101.20.4.5.4.1
		sleEponOnuSubscriberHistoryOltCleared NOTIFICATION-TYPE
			OBJECTS { sleEponOnuSubscriberControlRequest, sleEponOnuSubscriberControlTimeStamp, sleEponOnuSubscriberControlReqResult, sleEponOnuSubscriberControlOltIndex }
			STATUS current
			DESCRIPTION 
				"Description."
			::= { sleEponOnuSubscriberNotification 1 }

		
		-- 1.3.6.1.4.1.6296.101.20.4.5.4.2
		sleEponOnuSubscriberHistroyOnuCleared NOTIFICATION-TYPE
			OBJECTS { sleEponOnuSubscriberControlRequest, sleEponOnuSubscriberControlTimeStamp, sleEponOnuSubscriberControlReqResult, sleEponOnuSubscriberControlOltIndex, sleEponOnuSubscriberControlOnuIndex
				 }
			STATUS current
			DESCRIPTION 
				"Description."
			::= { sleEponOnuSubscriberNotification 2 }

		
		-- 1.3.6.1.4.1.6296.101.20.4.6
		sleEponOnuMacTable OBJECT IDENTIFIER ::= { sleEponOnuBridge 6 }

		
		-- 1.3.6.1.4.1.6296.101.20.4.6.1
		sleEponOnuMacTableTable OBJECT-TYPE
			SYNTAX SEQUENCE OF SleEponOnuMacTableEntry
			MAX-ACCESS not-accessible
			STATUS current
			DESCRIPTION
				"Description."
			::= { sleEponOnuMacTable 1 }

		
		-- 1.3.6.1.4.1.6296.101.20.4.6.1.1
		sleEponOnuMacTableEntry OBJECT-TYPE
			SYNTAX SleEponOnuMacTableEntry
			MAX-ACCESS not-accessible
			STATUS current
			DESCRIPTION
				"Description."
			INDEX { sleEponOltIndex, sleEponOnuIndex, sleEponOnuFdbMacAddress }
			::= { sleEponOnuMacTableTable 1 }

		
		SleEponOnuMacTableEntry ::=
			SEQUENCE { 
				sleEponOnuMacTableDynamicMacAddress
					MacAddress,
				sleEponOnuMacTableStaticMacAddress
					MacAddress
			 }

		-- 1.3.6.1.4.1.6296.101.20.4.6.1.1.1
		sleEponOnuMacTableDynamicMacAddress OBJECT-TYPE
			SYNTAX MacAddress
			MAX-ACCESS read-only
			STATUS current
			DESCRIPTION
				"The fdb address of ONT"
			::= { sleEponOnuMacTableEntry 1 }

		
		-- 1.3.6.1.4.1.6296.101.20.4.6.1.1.2
		sleEponOnuMacTableStaticMacAddress OBJECT-TYPE
			SYNTAX MacAddress
			MAX-ACCESS read-only
			STATUS current
			DESCRIPTION
				"The fdb address of ONT"
			::= { sleEponOnuMacTableEntry 2 }

		
		-- 1.3.6.1.4.1.6296.101.20.5
		sleEponProfile OBJECT IDENTIFIER ::= { sleEpon 5 }

		
		-- 1.3.6.1.4.1.6296.101.20.5.1
		sleEponProfileBase OBJECT IDENTIFIER ::= { sleEponProfile 1 }

		
		-- 1.3.6.1.4.1.6296.101.20.5.1.1
		sleEponProfileTable OBJECT-TYPE
			SYNTAX SEQUENCE OF SleEponProfileEntry
			MAX-ACCESS not-accessible
			STATUS current
			DESCRIPTION
				"Description."
			::= { sleEponProfileBase 1 }

		
		-- 1.3.6.1.4.1.6296.101.20.5.1.1.1
		sleEponProfileEntry OBJECT-TYPE
			SYNTAX SleEponProfileEntry
			MAX-ACCESS not-accessible
			STATUS current
			DESCRIPTION
				"Description."
			INDEX { sleEponProfileIndex }
			::= { sleEponProfileTable 1 }

		
		SleEponProfileEntry ::=
			SEQUENCE { 
				sleEponProfileIndex
					INTEGER,
				sleEponProfileName
					OCTET STRING,
				sleEponProfileDPDownMaxBandwidth
					INTEGER,
				sleEponProfileDPDownMaxBurstSize
					INTEGER,
				sleEponProfileDPP2pMaxBandwidth
					INTEGER,
				sleEponProfileDPP2pMaxBurstSize
					INTEGER,
				sleEponProfileSlaGuaranteedBandwidth
					INTEGER,
				sleEponProfileSlaBestEffortBandwidth
					INTEGER,
				sleEponProfileSlaPlatoClass
					INTEGER,
				sleEponProfileSlaPlatoMinBandwidth1m
					INTEGER,
				sleEponProfileSlaPlatoMinBandwdith64k
					INTEGER,
				sleEponProfileSlaPlatoMaxBandwidth1m
					INTEGER,
				sleEponProfileSlaPlatoMaxBandwidth64k
					INTEGER,
				sleEponProfileSlaPlatoDelayLevel
					INTEGER,
				sleEponProfileExtendMtu
					EnableFlag,
				sleEponProfileIgmpFilter
					EnableFlag,
				sleEponProfileIgmpSnooping
					EnableFlag,
				sleEponProfileSTPenable
					EnableFlag,
				sleEponProfileSubscriberInfoCollection
					EnableFlag,
				sleEponProfileLoopDetectStatus
					EnableFlag,
				sleEponProfileLoopDetectBlockTimer
					INTEGER,
				sleEponProfileLoopDetectSendingpacket
					INTEGER,
				sleEponProfileSipMgPort
					INTEGER,
				sleEponProfileSipProxyServer
					OCTET STRING,
				sleEponProfileSipProxyServerPort
					INTEGER,
				sleEponProfileSipBackupProxyServer
					OCTET STRING,
				sleEponProfileSipBackupProxyServerPort
					INTEGER,
				sleEponProfileSipActiveServer
					OCTET STRING,
				sleEponProfileSipRegisterServer
					OCTET STRING,
				sleEponProfileSipRegisterServerPort
					INTEGER,
				sleEponProfileSipBackupRegisterServer
					OCTET STRING,
				sleEponProfileSipBackupRegisterServerPort
					INTEGER,
				sleEponProfileSipOutBindServer
					OCTET STRING,
				sleEponProfileSipOutBindServerPort
					INTEGER,
				sleEponProfileSipRegisterInterval
					INTEGER,
				sleEponProfileSipHeartBeatSwitch
					EnableFlag,
				sleEponProfileSipHeartBeatCycle
					INTEGER,
				sleEponProfileSipHeartBeatCount
					INTEGER,
				sleEponProfileSipDNS1Server
					OCTET STRING,
				sleEponProfileSipDNS2Server
					OCTET STRING,
				sleEponProfileVoiceT38enable
					EnableFlag,
				sleEponProfileModemControl
					EnableFlag,
				sleEponProfileDHCPEnable
					Integer32,
				sleEponProfileMacLearnStatus
					OCTET STRING
			 }

		-- 1.3.6.1.4.1.6296.101.20.5.1.1.1.1
		sleEponProfileIndex OBJECT-TYPE
			SYNTAX INTEGER (1..32)
			MAX-ACCESS read-only
			STATUS current
			DESCRIPTION
				"Profile Index"
			::= { sleEponProfileEntry 1 }

		
		-- 1.3.6.1.4.1.6296.101.20.5.1.1.1.2
		sleEponProfileName OBJECT-TYPE
			SYNTAX OCTET STRING (SIZE (1..64))
			MAX-ACCESS read-only
			STATUS current
			DESCRIPTION
				"Profile name"
			::= { sleEponProfileEntry 2 }

		
		-- 1.3.6.1.4.1.6296.101.20.5.1.1.1.3
		sleEponProfileDPDownMaxBandwidth OBJECT-TYPE
			SYNTAX INTEGER (0 | 1..1000000)
			UNITS "kbps"
			MAX-ACCESS read-only
			STATUS current
			DESCRIPTION
				"Download policy Down Max Bandwidth 
				
				"
			::= { sleEponProfileEntry 3 }

		
		-- 1.3.6.1.4.1.6296.101.20.5.1.1.1.4
		sleEponProfileDPDownMaxBurstSize OBJECT-TYPE
			SYNTAX INTEGER (0 | 128..8388479)
			UNITS "byte"
			MAX-ACCESS read-only
			STATUS current
			DESCRIPTION
				"Download policy Down Max Burst Size 
				
				"
			::= { sleEponProfileEntry 4 }

		
		-- 1.3.6.1.4.1.6296.101.20.5.1.1.1.5
		sleEponProfileDPP2pMaxBandwidth OBJECT-TYPE
			SYNTAX INTEGER (0 | 1..1000000)
			UNITS "kbps"
			MAX-ACCESS read-only
			STATUS current
			DESCRIPTION
				"Download policy P2P Max Bandwidth "
			::= { sleEponProfileEntry 5 }

		
		-- 1.3.6.1.4.1.6296.101.20.5.1.1.1.6
		sleEponProfileDPP2pMaxBurstSize OBJECT-TYPE
			SYNTAX INTEGER (0 | 128..8388479)
			UNITS "byte"
			MAX-ACCESS read-only
			STATUS current
			DESCRIPTION
				"Download policy P2P Max Burst Size "
			::= { sleEponProfileEntry 6 }

		
		-- 1.3.6.1.4.1.6296.101.20.5.1.1.1.7
		sleEponProfileSlaGuaranteedBandwidth OBJECT-TYPE
			SYNTAX INTEGER (43..65535)
			UNITS "TQ"
			MAX-ACCESS read-only
			STATUS current
			DESCRIPTION
				"SLA-internal Guranteed Bandwidth"
			DEFVAL { 85 }
			::= { sleEponProfileEntry 7 }

		
		-- 1.3.6.1.4.1.6296.101.20.5.1.1.1.8
		sleEponProfileSlaBestEffortBandwidth OBJECT-TYPE
			SYNTAX INTEGER (43..65535)
			UNITS "TQ"
			MAX-ACCESS read-only
			STATUS current
			DESCRIPTION
				"SLA-internal Best effort Bandwidth"
			DEFVAL { 85 }
			::= { sleEponProfileEntry 8 }

		
		-- 1.3.6.1.4.1.6296.101.20.5.1.1.1.9
		sleEponProfileSlaPlatoClass OBJECT-TYPE
			SYNTAX INTEGER (0..7)
			MAX-ACCESS read-only
			STATUS current
			DESCRIPTION
				"SLA-Plato Class"
			DEFVAL { 1 }
			::= { sleEponProfileEntry 9 }

		
		-- 1.3.6.1.4.1.6296.101.20.5.1.1.1.10
		sleEponProfileSlaPlatoMinBandwidth1m OBJECT-TYPE
			SYNTAX INTEGER (1..1000)
			UNITS "Mbps"
			MAX-ACCESS read-only
			STATUS current
			DESCRIPTION
				"SLA-Plato Minimum Bandwidth_1m"
			DEFVAL { '1'b }
			::= { sleEponProfileEntry 10 }

		
		-- 1.3.6.1.4.1.6296.101.20.5.1.1.1.11
		sleEponProfileSlaPlatoMinBandwdith64k OBJECT-TYPE
			SYNTAX INTEGER (0..1024)
			UNITS "64Kbps"
			MAX-ACCESS read-only
			STATUS current
			DESCRIPTION
				"SLA-plato Minimum Bandwidth_64k"
			DEFVAL { '0'b }
			::= { sleEponProfileEntry 11 }

		
		-- 1.3.6.1.4.1.6296.101.20.5.1.1.1.12
		sleEponProfileSlaPlatoMaxBandwidth1m OBJECT-TYPE
			SYNTAX INTEGER (1..1000)
			UNITS "Mbps"
			MAX-ACCESS read-only
			STATUS current
			DESCRIPTION
				"SLA-plato Max bandwidth_1m"
			DEFVAL { 2 }
			::= { sleEponProfileEntry 12 }

		
		-- 1.3.6.1.4.1.6296.101.20.5.1.1.1.13
		sleEponProfileSlaPlatoMaxBandwidth64k OBJECT-TYPE
			SYNTAX INTEGER (0..1024)
			UNITS "64Kbps"
			MAX-ACCESS read-only
			STATUS current
			DESCRIPTION
				"SLA-plato Max bandwidth_64k"
			DEFVAL { 0 }
			::= { sleEponProfileEntry 13 }

		
		-- 1.3.6.1.4.1.6296.101.20.5.1.1.1.14
		sleEponProfileSlaPlatoDelayLevel OBJECT-TYPE
			SYNTAX INTEGER (1..2)
			MAX-ACCESS read-only
			STATUS current
			DESCRIPTION
				"SLA-plato Delay  level"
			DEFVAL { 1 }
			::= { sleEponProfileEntry 14 }

		
		-- 1.3.6.1.4.1.6296.101.20.5.1.1.1.15
		sleEponProfileExtendMtu OBJECT-TYPE
			SYNTAX EnableFlag
			MAX-ACCESS read-only
			STATUS current
			DESCRIPTION
				"Description."
			::= { sleEponProfileEntry 15 }

		
		-- 1.3.6.1.4.1.6296.101.20.5.1.1.1.16
		sleEponProfileIgmpFilter OBJECT-TYPE
			SYNTAX EnableFlag
			MAX-ACCESS read-only
			STATUS current
			DESCRIPTION
				"Description."
			::= { sleEponProfileEntry 16 }

		
		-- 1.3.6.1.4.1.6296.101.20.5.1.1.1.17
		sleEponProfileIgmpSnooping OBJECT-TYPE
			SYNTAX EnableFlag
			MAX-ACCESS read-only
			STATUS current
			DESCRIPTION
				"Description."
			::= { sleEponProfileEntry 17 }

		
		-- 1.3.6.1.4.1.6296.101.20.5.1.1.1.18
		sleEponProfileSTPenable OBJECT-TYPE
			SYNTAX EnableFlag
			MAX-ACCESS read-only
			STATUS current
			DESCRIPTION
				"Description."
			::= { sleEponProfileEntry 18 }

		
		-- 1.3.6.1.4.1.6296.101.20.5.1.1.1.19
		sleEponProfileSubscriberInfoCollection OBJECT-TYPE
			SYNTAX EnableFlag
			MAX-ACCESS read-only
			STATUS current
			DESCRIPTION
				"Description."
			::= { sleEponProfileEntry 19 }

		
		-- 1.3.6.1.4.1.6296.101.20.5.1.1.1.20
		sleEponProfileLoopDetectStatus OBJECT-TYPE
			SYNTAX EnableFlag
			MAX-ACCESS read-only
			STATUS current
			DESCRIPTION
				"Description."
			::= { sleEponProfileEntry 20 }

		
		-- 1.3.6.1.4.1.6296.101.20.5.1.1.1.21
		sleEponProfileLoopDetectBlockTimer OBJECT-TYPE
			SYNTAX INTEGER (0 | 10..86400)
			MAX-ACCESS read-only
			STATUS current
			DESCRIPTION
				"Description."
			::= { sleEponProfileEntry 21 }

		
		-- 1.3.6.1.4.1.6296.101.20.5.1.1.1.22
		sleEponProfileLoopDetectSendingpacket OBJECT-TYPE
			SYNTAX INTEGER (0 | 1..60)
			MAX-ACCESS read-only
			STATUS current
			DESCRIPTION
				"Description."
			::= { sleEponProfileEntry 22 }

		
		-- 1.3.6.1.4.1.6296.101.20.5.1.1.1.23
		sleEponProfileSipMgPort OBJECT-TYPE
			SYNTAX INTEGER
			MAX-ACCESS read-only
			STATUS current
			DESCRIPTION
				"Description."
			::= { sleEponProfileEntry 23 }

		
		-- 1.3.6.1.4.1.6296.101.20.5.1.1.1.24
		sleEponProfileSipProxyServer OBJECT-TYPE
			SYNTAX OCTET STRING (SIZE (0..64))
			MAX-ACCESS read-only
			STATUS current
			DESCRIPTION
				"Description."
			::= { sleEponProfileEntry 24 }

		
		-- 1.3.6.1.4.1.6296.101.20.5.1.1.1.25
		sleEponProfileSipProxyServerPort OBJECT-TYPE
			SYNTAX INTEGER
			MAX-ACCESS read-only
			STATUS current
			DESCRIPTION
				"Description."
			::= { sleEponProfileEntry 25 }

		
		-- 1.3.6.1.4.1.6296.101.20.5.1.1.1.26
		sleEponProfileSipBackupProxyServer OBJECT-TYPE
			SYNTAX OCTET STRING (SIZE (0..64))
			MAX-ACCESS read-only
			STATUS current
			DESCRIPTION
				"Description."
			::= { sleEponProfileEntry 26 }

		
		-- 1.3.6.1.4.1.6296.101.20.5.1.1.1.27
		sleEponProfileSipBackupProxyServerPort OBJECT-TYPE
			SYNTAX INTEGER
			MAX-ACCESS read-only
			STATUS current
			DESCRIPTION
				"Description."
			::= { sleEponProfileEntry 27 }

		
		-- 1.3.6.1.4.1.6296.101.20.5.1.1.1.28
		sleEponProfileSipActiveServer OBJECT-TYPE
			SYNTAX OCTET STRING (SIZE (0..64))
			MAX-ACCESS read-only
			STATUS current
			DESCRIPTION
				"Description."
			::= { sleEponProfileEntry 28 }

		
		-- 1.3.6.1.4.1.6296.101.20.5.1.1.1.29
		sleEponProfileSipRegisterServer OBJECT-TYPE
			SYNTAX OCTET STRING (SIZE (0..64))
			MAX-ACCESS read-only
			STATUS current
			DESCRIPTION
				"Description."
			::= { sleEponProfileEntry 29 }

		
		-- 1.3.6.1.4.1.6296.101.20.5.1.1.1.30
		sleEponProfileSipRegisterServerPort OBJECT-TYPE
			SYNTAX INTEGER
			MAX-ACCESS read-only
			STATUS current
			DESCRIPTION
				"Description."
			::= { sleEponProfileEntry 30 }

		
		-- 1.3.6.1.4.1.6296.101.20.5.1.1.1.31
		sleEponProfileSipBackupRegisterServer OBJECT-TYPE
			SYNTAX OCTET STRING (SIZE (0..64))
			MAX-ACCESS read-only
			STATUS current
			DESCRIPTION
				"Description."
			::= { sleEponProfileEntry 31 }

		
		-- 1.3.6.1.4.1.6296.101.20.5.1.1.1.32
		sleEponProfileSipBackupRegisterServerPort OBJECT-TYPE
			SYNTAX INTEGER
			MAX-ACCESS read-only
			STATUS current
			DESCRIPTION
				"Description."
			::= { sleEponProfileEntry 32 }

		
		-- 1.3.6.1.4.1.6296.101.20.5.1.1.1.33
		sleEponProfileSipOutBindServer OBJECT-TYPE
			SYNTAX OCTET STRING (SIZE (0..64))
			MAX-ACCESS read-only
			STATUS current
			DESCRIPTION
				"Description."
			::= { sleEponProfileEntry 33 }

		
		-- 1.3.6.1.4.1.6296.101.20.5.1.1.1.34
		sleEponProfileSipOutBindServerPort OBJECT-TYPE
			SYNTAX INTEGER
			MAX-ACCESS read-only
			STATUS current
			DESCRIPTION
				"Description."
			::= { sleEponProfileEntry 34 }

		
		-- 1.3.6.1.4.1.6296.101.20.5.1.1.1.35
		sleEponProfileSipRegisterInterval OBJECT-TYPE
			SYNTAX INTEGER
			MAX-ACCESS read-only
			STATUS current
			DESCRIPTION
				"Description."
			::= { sleEponProfileEntry 35 }

		
		-- 1.3.6.1.4.1.6296.101.20.5.1.1.1.36
		sleEponProfileSipHeartBeatSwitch OBJECT-TYPE
			SYNTAX EnableFlag
			MAX-ACCESS read-only
			STATUS current
			DESCRIPTION
				"Description."
			::= { sleEponProfileEntry 36 }

		
		-- 1.3.6.1.4.1.6296.101.20.5.1.1.1.37
		sleEponProfileSipHeartBeatCycle OBJECT-TYPE
			SYNTAX INTEGER
			MAX-ACCESS read-only
			STATUS current
			DESCRIPTION
				"Description."
			::= { sleEponProfileEntry 37 }

		
		-- 1.3.6.1.4.1.6296.101.20.5.1.1.1.38
		sleEponProfileSipHeartBeatCount OBJECT-TYPE
			SYNTAX INTEGER
			MAX-ACCESS read-only
			STATUS current
			DESCRIPTION
				"Description."
			::= { sleEponProfileEntry 38 }

		
		-- 1.3.6.1.4.1.6296.101.20.5.1.1.1.39
		sleEponProfileSipDNS1Server OBJECT-TYPE
			SYNTAX OCTET STRING (SIZE (0..64))
			MAX-ACCESS read-only
			STATUS current
			DESCRIPTION
				"Description."
			::= { sleEponProfileEntry 39 }

		
		-- 1.3.6.1.4.1.6296.101.20.5.1.1.1.40
		sleEponProfileSipDNS2Server OBJECT-TYPE
			SYNTAX OCTET STRING (SIZE (0..64))
			MAX-ACCESS read-only
			STATUS current
			DESCRIPTION
				"Description."
			::= { sleEponProfileEntry 40 }

		
		-- 1.3.6.1.4.1.6296.101.20.5.1.1.1.41
		sleEponProfileVoiceT38enable OBJECT-TYPE
			SYNTAX EnableFlag
			MAX-ACCESS read-only
			STATUS current
			DESCRIPTION
				"Description."
			::= { sleEponProfileEntry 41 }

		
		-- 1.3.6.1.4.1.6296.101.20.5.1.1.1.42
		sleEponProfileModemControl OBJECT-TYPE
			SYNTAX EnableFlag
			MAX-ACCESS read-only
			STATUS current
			DESCRIPTION
				"Description."
			::= { sleEponProfileEntry 42 }

		
		-- 1.3.6.1.4.1.6296.101.20.5.1.1.1.43
		sleEponProfileDHCPEnable OBJECT-TYPE
			SYNTAX Integer32
			MAX-ACCESS read-only
			STATUS current
			DESCRIPTION
				"dhcp enable"
			::= { sleEponProfileEntry 43 }

		
		-- 1.3.6.1.4.1.6296.101.20.5.1.1.1.44
		sleEponProfileMacLearnStatus OBJECT-TYPE
			SYNTAX OCTET STRING
			MAX-ACCESS read-only
			STATUS current
			DESCRIPTION
				"mac learn status : enable or disable"
			::= { sleEponProfileEntry 44 }

		
		-- 1.3.6.1.4.1.6296.101.20.5.1.2
		sleEponProfileControl OBJECT IDENTIFIER ::= { sleEponProfileBase 2 }

		
		-- 1.3.6.1.4.1.6296.101.20.5.1.2.1
		sleEponProfileControlRequest OBJECT-TYPE
			SYNTAX INTEGER
				{
				createProfile(1),
				modifyProfile(2),
				destroyProfile(3),
				modifyProfileMtu(4),
				modifyProfileIgmp(5),
				modifyProfileSTP(6),
				createDefaultProfile(7),
				modifyProfileSubscriber(8),
				modifyProfileLoopDetect(9),
				modifyProfileSipConfig(10),
				modifyProfileModemConfig(11),
				modifyProfileDHCP(12),
				modifyProfileMacLearn(13)
				}
			MAX-ACCESS read-write
			STATUS current
			DESCRIPTION
				"The request of a user command"
			::= { sleEponProfileControl 1 }

		
		-- 1.3.6.1.4.1.6296.101.20.5.1.2.2
		sleEponProfileControlStatus OBJECT-TYPE
			SYNTAX SleControlStatusType
			MAX-ACCESS read-only
			STATUS current
			DESCRIPTION
				"The status of user command"
			::= { sleEponProfileControl 2 }

		
		-- 1.3.6.1.4.1.6296.101.20.5.1.2.3
		sleEponProfileControlTimer OBJECT-TYPE
			SYNTAX Gauge32
			MAX-ACCESS read-write
			STATUS current
			DESCRIPTION
				"The maximum time for the manager for a long running user command"
			::= { sleEponProfileControl 3 }

		
		-- 1.3.6.1.4.1.6296.101.20.5.1.2.4
		sleEponProfileControlTimeStamp OBJECT-TYPE
			SYNTAX TimeTicks
			MAX-ACCESS read-only
			STATUS current
			DESCRIPTION
				"The time stamp of the last command(end of command)"
			::= { sleEponProfileControl 4 }

		
		-- 1.3.6.1.4.1.6296.101.20.5.1.2.5
		sleEponProfileControlReqResult OBJECT-TYPE
			SYNTAX SleControlRequestResultType
			MAX-ACCESS read-only
			STATUS current
			DESCRIPTION
				"The result of the last user command"
			::= { sleEponProfileControl 5 }

		
		-- 1.3.6.1.4.1.6296.101.20.5.1.2.6
		sleEponProfileControlIndex OBJECT-TYPE
			SYNTAX INTEGER (1..32)
			MAX-ACCESS read-write
			STATUS current
			DESCRIPTION
				"Profile index"
			::= { sleEponProfileControl 6 }

		
		-- 1.3.6.1.4.1.6296.101.20.5.1.2.7
		sleEponProfileControlName OBJECT-TYPE
			SYNTAX OCTET STRING (SIZE (1..64))
			MAX-ACCESS read-write
			STATUS current
			DESCRIPTION
				"Profile name"
			::= { sleEponProfileControl 7 }

		
		-- 1.3.6.1.4.1.6296.101.20.5.1.2.8
		sleEponProfileControlDPDownMaxBandwidth OBJECT-TYPE
			SYNTAX INTEGER (0 | 1..1000000)
			UNITS "kbps"
			MAX-ACCESS read-write
			STATUS current
			DESCRIPTION
				"Download policy Down Max Bandwidth "
			::= { sleEponProfileControl 8 }

		
		-- 1.3.6.1.4.1.6296.101.20.5.1.2.9
		sleEponProfileControlDPDownMaxBurstSize OBJECT-TYPE
			SYNTAX INTEGER (0 | 128..8388479)
			UNITS "byte"
			MAX-ACCESS read-write
			STATUS current
			DESCRIPTION
				"Download policy Down Max Burst Size"
			::= { sleEponProfileControl 9 }

		
		-- 1.3.6.1.4.1.6296.101.20.5.1.2.10
		sleEponProfileControlDPP2pMaxBandwidth OBJECT-TYPE
			SYNTAX INTEGER (0 | 1..1000000)
			UNITS "kbps"
			MAX-ACCESS read-write
			STATUS current
			DESCRIPTION
				"Download policy P2P Max Bandwidth"
			::= { sleEponProfileControl 10 }

		
		-- 1.3.6.1.4.1.6296.101.20.5.1.2.11
		sleEponProfileControlDPP2pMaxBurstSize OBJECT-TYPE
			SYNTAX INTEGER (0 | 128..8388479)
			UNITS "byte"
			MAX-ACCESS read-write
			STATUS current
			DESCRIPTION
				"Download policy P2P Max Burst Size "
			::= { sleEponProfileControl 11 }

		
		-- 1.3.6.1.4.1.6296.101.20.5.1.2.12
		sleEponProfileControlSlaGuaranteedBandwidth OBJECT-TYPE
			SYNTAX INTEGER (43..65535)
			UNITS "TQ"
			MAX-ACCESS read-write
			STATUS current
			DESCRIPTION
				"SLA-internal Guranteed Bandwidth"
			DEFVAL { 85 }
			::= { sleEponProfileControl 12 }

		
		-- 1.3.6.1.4.1.6296.101.20.5.1.2.13
		sleEponProfileControlSlaBestEffortBandwidth OBJECT-TYPE
			SYNTAX INTEGER (43..65535)
			UNITS "TQ"
			MAX-ACCESS read-write
			STATUS current
			DESCRIPTION
				"SLA-internal Best effort Bandwidth"
			DEFVAL { 85 }
			::= { sleEponProfileControl 13 }

		
		-- 1.3.6.1.4.1.6296.101.20.5.1.2.14
		sleEponProfileControlSlaPlatoClass OBJECT-TYPE
			SYNTAX INTEGER (0..7)
			MAX-ACCESS read-write
			STATUS current
			DESCRIPTION
				"SLA-Plato Class"
			::= { sleEponProfileControl 14 }

		
		-- 1.3.6.1.4.1.6296.101.20.5.1.2.15
		sleEponProfileControlSlaPlatoGuaranteedBandwidth1m OBJECT-TYPE
			SYNTAX INTEGER (1..1000)
			UNITS "Mbps"
			MAX-ACCESS read-write
			STATUS current
			DESCRIPTION
				"SLA-Plato Minimum Bandwidth_1m"
			DEFVAL { 1 }
			::= { sleEponProfileControl 15 }

		
		-- 1.3.6.1.4.1.6296.101.20.5.1.2.16
		sleEponProfileControlSlaPlatoGuaranteedBandwdith64k OBJECT-TYPE
			SYNTAX INTEGER (0..1024)
			UNITS "64Kbps"
			MAX-ACCESS read-write
			STATUS current
			DESCRIPTION
				"SLA-plato Minimum Bandwidth_64k"
			DEFVAL { 0 }
			::= { sleEponProfileControl 16 }

		
		-- 1.3.6.1.4.1.6296.101.20.5.1.2.17
		sleEponProfileControlSlaPlatoBestEffortBandwidth1m OBJECT-TYPE
			SYNTAX INTEGER (1..1000)
			UNITS "Mbps"
			MAX-ACCESS read-write
			STATUS current
			DESCRIPTION
				"SLA-plato Max bandwidth_1m"
			DEFVAL { 2 }
			::= { sleEponProfileControl 17 }

		
		-- 1.3.6.1.4.1.6296.101.20.5.1.2.18
		sleEponProfileControlSlaPlatoBestEffortBandwidth64k OBJECT-TYPE
			SYNTAX INTEGER (0..1024)
			UNITS "64Kbps"
			MAX-ACCESS read-write
			STATUS current
			DESCRIPTION
				"SLA-plato Max bandwidth_64k"
			DEFVAL { 0 }
			::= { sleEponProfileControl 18 }

		
		-- 1.3.6.1.4.1.6296.101.20.5.1.2.19
		sleEponProfileControlSlaPlatoDelayLevel OBJECT-TYPE
			SYNTAX INTEGER (1..2)
			MAX-ACCESS read-write
			STATUS current
			DESCRIPTION
				"SLA-plato Delay  level"
			DEFVAL { 1 }
			::= { sleEponProfileControl 19 }

		
		-- 1.3.6.1.4.1.6296.101.20.5.1.2.20
		sleEponProfileControlExtendMtu OBJECT-TYPE
			SYNTAX EnableFlag
			MAX-ACCESS read-write
			STATUS current
			DESCRIPTION
				"Description."
			::= { sleEponProfileControl 20 }

		
		-- 1.3.6.1.4.1.6296.101.20.5.1.2.21
		sleEponProfileControlIgmpFilter OBJECT-TYPE
			SYNTAX EnableFlag
			MAX-ACCESS read-write
			STATUS current
			DESCRIPTION
				"Description."
			::= { sleEponProfileControl 21 }

		
		-- 1.3.6.1.4.1.6296.101.20.5.1.2.22
		sleEponProfileControlSnooping OBJECT-TYPE
			SYNTAX EnableFlag
			MAX-ACCESS read-write
			STATUS current
			DESCRIPTION
				"Description."
			::= { sleEponProfileControl 22 }

		
		-- 1.3.6.1.4.1.6296.101.20.5.1.2.23
		sleEponProfileControlSTPenable OBJECT-TYPE
			SYNTAX EnableFlag
			MAX-ACCESS read-write
			STATUS current
			DESCRIPTION
				"Description."
			::= { sleEponProfileControl 23 }

		
		-- 1.3.6.1.4.1.6296.101.20.5.1.2.24
		sleEponProfileControlSubscriberInfoCollection OBJECT-TYPE
			SYNTAX EnableFlag
			MAX-ACCESS read-write
			STATUS current
			DESCRIPTION
				"Description."
			::= { sleEponProfileControl 24 }

		
		-- 1.3.6.1.4.1.6296.101.20.5.1.2.25
		sleEponProfileControlLoopDetectStatus OBJECT-TYPE
			SYNTAX EnableFlag
			MAX-ACCESS read-write
			STATUS current
			DESCRIPTION
				"Description."
			::= { sleEponProfileControl 25 }

		
		-- 1.3.6.1.4.1.6296.101.20.5.1.2.26
		sleEponProfileControlLoopDetectBlockTimer OBJECT-TYPE
			SYNTAX INTEGER (0 | 10..86400)
			MAX-ACCESS read-write
			STATUS current
			DESCRIPTION
				"Description."
			::= { sleEponProfileControl 26 }

		
		-- 1.3.6.1.4.1.6296.101.20.5.1.2.27
		sleEponProfileControlLoopDetectSendingpacket OBJECT-TYPE
			SYNTAX INTEGER (0 | 1..60)
			MAX-ACCESS read-write
			STATUS current
			DESCRIPTION
				"Description."
			::= { sleEponProfileControl 27 }

		
		-- 1.3.6.1.4.1.6296.101.20.5.1.2.28
		sleEponProfileControlSipMgPort OBJECT-TYPE
			SYNTAX INTEGER
			MAX-ACCESS read-write
			STATUS current
			DESCRIPTION
				"Description."
			::= { sleEponProfileControl 28 }

		
		-- 1.3.6.1.4.1.6296.101.20.5.1.2.29
		sleEponProfileControlSipProxyServer OBJECT-TYPE
			SYNTAX OCTET STRING (SIZE (0..64))
			MAX-ACCESS read-write
			STATUS current
			DESCRIPTION
				"Description."
			::= { sleEponProfileControl 29 }

		
		-- 1.3.6.1.4.1.6296.101.20.5.1.2.30
		sleEponProfileControlSipProxyServerPort OBJECT-TYPE
			SYNTAX INTEGER
			MAX-ACCESS read-write
			STATUS current
			DESCRIPTION
				"Description."
			::= { sleEponProfileControl 30 }

		
		-- 1.3.6.1.4.1.6296.101.20.5.1.2.31
		sleEponProfileControlSipBackupProxyServer OBJECT-TYPE
			SYNTAX OCTET STRING (SIZE (0..64))
			MAX-ACCESS read-write
			STATUS current
			DESCRIPTION
				"Description."
			::= { sleEponProfileControl 31 }

		
		-- 1.3.6.1.4.1.6296.101.20.5.1.2.32
		sleEponProfileControlSipBackupProxyServerPort OBJECT-TYPE
			SYNTAX INTEGER
			MAX-ACCESS read-write
			STATUS current
			DESCRIPTION
				"Description."
			::= { sleEponProfileControl 32 }

		
		-- 1.3.6.1.4.1.6296.101.20.5.1.2.33
		sleEponProfileControlSipActiveServer OBJECT-TYPE
			SYNTAX OCTET STRING (SIZE (0..64))
			MAX-ACCESS read-write
			STATUS current
			DESCRIPTION
				"Description."
			::= { sleEponProfileControl 33 }

		
		-- 1.3.6.1.4.1.6296.101.20.5.1.2.34
		sleEponProfileControlSipRegisterServer OBJECT-TYPE
			SYNTAX OCTET STRING (SIZE (0..64))
			MAX-ACCESS read-write
			STATUS current
			DESCRIPTION
				"Description."
			::= { sleEponProfileControl 34 }

		
		-- 1.3.6.1.4.1.6296.101.20.5.1.2.35
		sleEponProfileControlSipRegisterServerPort OBJECT-TYPE
			SYNTAX INTEGER
			MAX-ACCESS read-write
			STATUS current
			DESCRIPTION
				"Description."
			::= { sleEponProfileControl 35 }

		
		-- 1.3.6.1.4.1.6296.101.20.5.1.2.36
		sleEponProfileControlSipBackupRegisterServer OBJECT-TYPE
			SYNTAX OCTET STRING (SIZE (0..64))
			MAX-ACCESS read-write
			STATUS current
			DESCRIPTION
				"Description."
			::= { sleEponProfileControl 36 }

		
		-- 1.3.6.1.4.1.6296.101.20.5.1.2.37
		sleEponProfileControlSipBackupRegisterServerPort OBJECT-TYPE
			SYNTAX INTEGER
			MAX-ACCESS read-write
			STATUS current
			DESCRIPTION
				"Description."
			::= { sleEponProfileControl 37 }

		
		-- 1.3.6.1.4.1.6296.101.20.5.1.2.38
		sleEponProfileControlSipOutBindServer OBJECT-TYPE
			SYNTAX OCTET STRING (SIZE (0..64))
			MAX-ACCESS read-write
			STATUS current
			DESCRIPTION
				"Description."
			::= { sleEponProfileControl 38 }

		
		-- 1.3.6.1.4.1.6296.101.20.5.1.2.39
		sleEponProfileControlSipOutBindServerPort OBJECT-TYPE
			SYNTAX INTEGER
			MAX-ACCESS read-write
			STATUS current
			DESCRIPTION
				"Description."
			::= { sleEponProfileControl 39 }

		
		-- 1.3.6.1.4.1.6296.101.20.5.1.2.40
		sleEponProfileControlSipRegisterInterval OBJECT-TYPE
			SYNTAX INTEGER
			MAX-ACCESS read-write
			STATUS current
			DESCRIPTION
				"Description."
			::= { sleEponProfileControl 40 }

		
		-- 1.3.6.1.4.1.6296.101.20.5.1.2.41
		sleEponProfileControlSipHeartBeatSwitch OBJECT-TYPE
			SYNTAX EnableFlag
			MAX-ACCESS read-write
			STATUS current
			DESCRIPTION
				"Description."
			::= { sleEponProfileControl 41 }

		
		-- 1.3.6.1.4.1.6296.101.20.5.1.2.42
		sleEponProfileControlSipHeartBeatCycle OBJECT-TYPE
			SYNTAX INTEGER
			MAX-ACCESS read-write
			STATUS current
			DESCRIPTION
				"Description."
			::= { sleEponProfileControl 42 }

		
		-- 1.3.6.1.4.1.6296.101.20.5.1.2.43
		sleEponProfileControlSipHeartBeatCount OBJECT-TYPE
			SYNTAX INTEGER
			MAX-ACCESS read-write
			STATUS current
			DESCRIPTION
				"Description."
			::= { sleEponProfileControl 43 }

		
		-- 1.3.6.1.4.1.6296.101.20.5.1.2.44
		sleEponProfileControlSipDNS1Server OBJECT-TYPE
			SYNTAX OCTET STRING (SIZE (0..64))
			MAX-ACCESS read-write
			STATUS current
			DESCRIPTION
				"Description."
			::= { sleEponProfileControl 44 }

		
		-- 1.3.6.1.4.1.6296.101.20.5.1.2.45
		sleEponProfileControlSipDNS2Server OBJECT-TYPE
			SYNTAX OCTET STRING (SIZE (0..64))
			MAX-ACCESS read-write
			STATUS current
			DESCRIPTION
				"Description."
			::= { sleEponProfileControl 45 }

		
		-- 1.3.6.1.4.1.6296.101.20.5.1.2.46
		sleEponProfileControlVoiceT38enable OBJECT-TYPE
			SYNTAX EnableFlag
			MAX-ACCESS read-write
			STATUS current
			DESCRIPTION
				"Description."
			::= { sleEponProfileControl 46 }

		
		-- 1.3.6.1.4.1.6296.101.20.5.1.2.47
		sleEponProfileControlModemControl OBJECT-TYPE
			SYNTAX EnableFlag
			MAX-ACCESS read-write
			STATUS current
			DESCRIPTION
				"Description."
			::= { sleEponProfileControl 47 }

		
		-- 1.3.6.1.4.1.6296.101.20.5.1.2.48
		sleEponProfileControlDHCPEnable OBJECT-TYPE
			SYNTAX Integer32
			MAX-ACCESS read-write
			STATUS current
			DESCRIPTION
				"dhcp enable"
			::= { sleEponProfileControl 48 }

		
		-- 1.3.6.1.4.1.6296.101.20.5.1.2.49
		sleEponProfileControlMacLearnStatus OBJECT-TYPE
			SYNTAX EnableFlag
			MAX-ACCESS read-write
			STATUS current
			DESCRIPTION
				"mac learn : enbale 1 , diable 2"
			DEFVAL { enable }
			::= { sleEponProfileControl 49 }

		
		-- 1.3.6.1.4.1.6296.101.20.5.1.3
		sleEponProfileNotification OBJECT IDENTIFIER ::= { sleEponProfileBase 3 }

		
		-- 1.3.6.1.4.1.6296.101.20.5.1.3.1
		sleEponProfileCreated NOTIFICATION-TYPE
			OBJECTS { sleEponProfileControlRequest, sleEponProfileControlTimeStamp, sleEponProfileControlReqResult, sleEponProfileControlIndex, sleEponProfileControlName
				 }
			STATUS current
			DESCRIPTION 
				"Description."
			::= { sleEponProfileNotification 1 }

		
		-- 1.3.6.1.4.1.6296.101.20.5.1.3.2
		sleEponProfileModified NOTIFICATION-TYPE
			OBJECTS { sleEponProfileControlRequest, sleEponProfileControlTimeStamp, sleEponProfileControlReqResult, sleEponProfileControlIndex, sleEponProfileControlName
				 }
			STATUS current
			DESCRIPTION 
				"Description."
			::= { sleEponProfileNotification 2 }

		
		-- 1.3.6.1.4.1.6296.101.20.5.1.3.3
		sleEponProfileDestroyed NOTIFICATION-TYPE
			OBJECTS { sleEponProfileControlRequest, sleEponProfileControlTimeStamp, sleEponProfileControlReqResult, sleEponProfileControlIndex, sleEponProfileControlName
				 }
			STATUS current
			DESCRIPTION 
				"Description."
			::= { sleEponProfileNotification 3 }

		
		-- 1.3.6.1.4.1.6296.101.20.5.1.3.4
		sleEponProfileExtendMtuChanged NOTIFICATION-TYPE
			OBJECTS { sleEponProfileControlRequest, sleEponProfileControlTimeStamp, sleEponProfileControlReqResult, sleEponProfileControlIndex, sleEponProfileControlName, 
				sleEponProfileControlExtendMtu }
			STATUS current
			DESCRIPTION 
				"Description."
			::= { sleEponProfileNotification 4 }

		
		-- 1.3.6.1.4.1.6296.101.20.5.1.3.5
		sleEponProfileIgmpChanged NOTIFICATION-TYPE
			OBJECTS { sleEponProfileControlRequest, sleEponProfileControlTimeStamp, sleEponProfileControlReqResult, sleEponProfileControlIndex, sleEponProfileControlName, 
				sleEponProfileControlIgmpFilter, sleEponProfileControlSnooping }
			STATUS current
			DESCRIPTION 
				"Description."
			::= { sleEponProfileNotification 5 }

		
		-- 1.3.6.1.4.1.6296.101.20.5.1.3.6
		sleEponProfileSTPChanged NOTIFICATION-TYPE
			OBJECTS { sleEponProfileControlRequest, sleEponProfileControlTimeStamp, sleEponProfileControlReqResult, sleEponProfileControlIndex, sleEponProfileControlName, 
				sleEponProfileControlSTPenable }
			STATUS current
			DESCRIPTION 
				"Description."
			::= { sleEponProfileNotification 6 }

		
		-- 1.3.6.1.4.1.6296.101.20.5.1.3.7
		sleEponProfileDefaultProfileCreated NOTIFICATION-TYPE
			OBJECTS { sleEponProfileQueueControlRequest, sleEponProfileQueueControlTimeStamp, sleEponProfileQueueControlReqResult }
			STATUS current
			DESCRIPTION 
				"Description."
			::= { sleEponProfileNotification 7 }

		
		-- 1.3.6.1.4.1.6296.101.20.5.1.3.8
		sleEponProfileSubscriberChanged NOTIFICATION-TYPE
			OBJECTS { sleEponProfileControlRequest, sleEponProfileControlTimeStamp, sleEponProfileControlReqResult, sleEponProfileControlIndex, sleEponProfileControlName, 
				sleEponProfileControlSubscriberInfoCollection }
			STATUS current
			DESCRIPTION 
				"Description."
			::= { sleEponProfileNotification 8 }

		
		-- 1.3.6.1.4.1.6296.101.20.5.1.3.9
		sleEponProfileLoopDetectChanged NOTIFICATION-TYPE
			OBJECTS { sleEponProfileControlRequest, sleEponProfileControlTimeStamp, sleEponProfileControlReqResult, sleEponProfileControlIndex, sleEponProfileControlName, 
				sleEponProfileControlLoopDetectStatus, sleEponProfileControlLoopDetectBlockTimer, sleEponProfileControlLoopDetectSendingpacket }
			STATUS current
			DESCRIPTION 
				"Description."
			::= { sleEponProfileNotification 9 }

		
		-- 1.3.6.1.4.1.6296.101.20.5.1.3.10
		sleEponProfileSipConfigChanged NOTIFICATION-TYPE
			OBJECTS { sleEponProfileControlRequest, sleEponProfileControlTimeStamp, sleEponProfileControlReqResult, sleEponProfileControlIndex, sleEponProfileControlName, 
				sleEponProfileControlSipMgPort, sleEponProfileControlSipProxyServer, sleEponProfileControlSipProxyServerPort, sleEponProfileControlSipBackupProxyServer, sleEponProfileControlSipBackupProxyServerPort, 
				sleEponProfileControlSipActiveServer, sleEponProfileControlSipRegisterServer, sleEponProfileControlSipRegisterServerPort, sleEponProfileControlSipBackupRegisterServer, sleEponProfileControlSipBackupRegisterServerPort, 
				sleEponProfileControlSipOutBindServer, sleEponProfileControlSipOutBindServerPort, sleEponProfileControlSipRegisterInterval, sleEponProfileControlSipHeartBeatSwitch, sleEponProfileControlSipHeartBeatCycle, 
				sleEponProfileControlSipHeartBeatCount, sleEponProfileControlSipDNS1Server, sleEponProfileControlSipDNS2Server }
			STATUS current
			DESCRIPTION 
				"Description."
			::= { sleEponProfileNotification 10 }

		
		-- 1.3.6.1.4.1.6296.101.20.5.1.3.11
		sleEponProfileModemConfigChanged NOTIFICATION-TYPE
			OBJECTS { sleEponProfileControlRequest, sleEponProfileControlTimeStamp, sleEponProfileControlReqResult, sleEponProfileControlIndex, sleEponProfileControlName, 
				sleEponProfileControlVoiceT38enable, sleEponProfileControlModemControl }
			STATUS current
			DESCRIPTION 
				"Description."
			::= { sleEponProfileNotification 11 }

		
		-- 1.3.6.1.4.1.6296.101.20.5.1.3.12
		sleEponProfileDHCPChanged NOTIFICATION-TYPE
			STATUS current
			DESCRIPTION 
				"Description."
			::= { sleEponProfileNotification 12 }

		
		-- 1.3.6.1.4.1.6296.101.20.5.1.3.13
		sleEponProfileModemMacLearnChanged NOTIFICATION-TYPE
			OBJECTS { sleEponProfileControlRequest, sleEponProfileControlTimeStamp, sleEponProfileControlReqResult, sleEponProfileControlMacLearnStatus }
			STATUS current
			DESCRIPTION 
				"mac learn status changed trap"
			::= { sleEponProfileNotification 13 }

		
		-- 1.3.6.1.4.1.6296.101.20.5.1.4
		sleEponProfileIgmpSnoopingTable OBJECT-TYPE
			SYNTAX SEQUENCE OF SleEponProfileIgmpSnoopingEntry
			MAX-ACCESS not-accessible
			STATUS current
			DESCRIPTION
				"Description."
			::= { sleEponProfileBase 4 }

		
		-- 1.3.6.1.4.1.6296.101.20.5.1.4.1
		sleEponProfileIgmpSnoopingEntry OBJECT-TYPE
			SYNTAX SleEponProfileIgmpSnoopingEntry
			MAX-ACCESS not-accessible
			STATUS current
			DESCRIPTION
				"Description."
			INDEX { sleEponProfileIndex, sleEponProfileIgmpSnoopingIndex }
			::= { sleEponProfileIgmpSnoopingTable 1 }

		
		SleEponProfileIgmpSnoopingEntry ::=
			SEQUENCE { 
				sleEponProfileIgmpSnoopingIndex
					Integer32,
				sleEponProfileIgmpSnoopingState
					EnableFlag,
				sleEponProfileIgmpSnoopingMaxch
					Integer32,
				sleEponProfileIgmpSnoopingTagVlan
					Integer32
			 }

		-- 1.3.6.1.4.1.6296.101.20.5.1.4.1.1
		sleEponProfileIgmpSnoopingIndex OBJECT-TYPE
			SYNTAX Integer32 (1..5)
			MAX-ACCESS read-only
			STATUS current
			DESCRIPTION
				"Igmp snooping count."
			::= { sleEponProfileIgmpSnoopingEntry 1 }

		
		-- 1.3.6.1.4.1.6296.101.20.5.1.4.1.2
		sleEponProfileIgmpSnoopingState OBJECT-TYPE
			SYNTAX EnableFlag
			MAX-ACCESS read-only
			STATUS current
			DESCRIPTION
				"Description."
			::= { sleEponProfileIgmpSnoopingEntry 2 }

		
		-- 1.3.6.1.4.1.6296.101.20.5.1.4.1.3
		sleEponProfileIgmpSnoopingMaxch OBJECT-TYPE
			SYNTAX Integer32 (1..255)
			MAX-ACCESS read-only
			STATUS current
			DESCRIPTION
				"Maximum number of channels."
			::= { sleEponProfileIgmpSnoopingEntry 3 }

		
		-- 1.3.6.1.4.1.6296.101.20.5.1.4.1.4
		sleEponProfileIgmpSnoopingTagVlan OBJECT-TYPE
			SYNTAX Integer32 (1..4096)
			MAX-ACCESS read-write
			STATUS current
			DESCRIPTION
				"Igmp snooping tag vlan id."
			::= { sleEponProfileIgmpSnoopingEntry 4 }

		
		-- 1.3.6.1.4.1.6296.101.20.5.1.5
		sleEponProfileIgmpSnoopingControl OBJECT IDENTIFIER ::= { sleEponProfileBase 5 }

		
		-- 1.3.6.1.4.1.6296.101.20.5.1.5.1
		sleEponProfileIgmpSnoopingControlRequest OBJECT-TYPE
			SYNTAX INTEGER { modifyProfileIgmpSnooping(1) }
			MAX-ACCESS read-write
			STATUS current
			DESCRIPTION
				"The request of a user command"
			::= { sleEponProfileIgmpSnoopingControl 1 }

		
		-- 1.3.6.1.4.1.6296.101.20.5.1.5.2
		sleEponProfileIgmpSnoopingControlStatus OBJECT-TYPE
			SYNTAX SleControlStatusType
			MAX-ACCESS read-only
			STATUS current
			DESCRIPTION
				"The status of user command"
			::= { sleEponProfileIgmpSnoopingControl 2 }

		
		-- 1.3.6.1.4.1.6296.101.20.5.1.5.3
		sleEponProfileIgmpSnoopingControlTimer OBJECT-TYPE
			SYNTAX Gauge32
			MAX-ACCESS read-write
			STATUS current
			DESCRIPTION
				"The maximum time for the manager for a long running user command"
			::= { sleEponProfileIgmpSnoopingControl 3 }

		
		-- 1.3.6.1.4.1.6296.101.20.5.1.5.4
		sleEponProfileIgmpSnoopingControlTimeStamp OBJECT-TYPE
			SYNTAX TimeTicks
			MAX-ACCESS read-only
			STATUS current
			DESCRIPTION
				"The time stamp of the last command(end of command)"
			::= { sleEponProfileIgmpSnoopingControl 4 }

		
		-- 1.3.6.1.4.1.6296.101.20.5.1.5.5
		sleEponProfileIgmpSnoopingControlReqResult OBJECT-TYPE
			SYNTAX SleControlRequestResultType
			MAX-ACCESS read-only
			STATUS current
			DESCRIPTION
				"The result of the last user command"
			::= { sleEponProfileIgmpSnoopingControl 5 }

		
		-- 1.3.6.1.4.1.6296.101.20.5.1.5.6
		sleEponProfileIgmpSnoopingControlProfileIndex OBJECT-TYPE
			SYNTAX INTEGER (1..32)
			MAX-ACCESS read-write
			STATUS current
			DESCRIPTION
				"Profile index"
			::= { sleEponProfileIgmpSnoopingControl 6 }

		
		-- 1.3.6.1.4.1.6296.101.20.5.1.5.7
		sleEponProfileIgmpSnoopingControlState OBJECT-TYPE
			SYNTAX EnableFlag
			MAX-ACCESS read-write
			STATUS current
			DESCRIPTION
				"enable(1), disable(2)."
			::= { sleEponProfileIgmpSnoopingControl 7 }

		
		-- 1.3.6.1.4.1.6296.101.20.5.1.5.8
		sleEponProfileIgmpSnoopingControlMaxch OBJECT-TYPE
			SYNTAX Integer32 (1..255)
			MAX-ACCESS read-write
			STATUS current
			DESCRIPTION
				"Maximum number of channels."
			DEFVAL { 255 }
			::= { sleEponProfileIgmpSnoopingControl 8 }

		
		-- 1.3.6.1.4.1.6296.101.20.5.1.5.9
		sleEponProfileIgmpSnoopingControlTagVlan OBJECT-TYPE
			SYNTAX Integer32 (1..4096)
			MAX-ACCESS read-write
			STATUS current
			DESCRIPTION
				"Igmp snooping tag vlan id."
			::= { sleEponProfileIgmpSnoopingControl 9 }

		
		-- 1.3.6.1.4.1.6296.101.20.5.1.6
		sleEponProfileIgmpSnoopingNotification OBJECT IDENTIFIER ::= { sleEponProfileBase 6 }

		
		-- 1.3.6.1.4.1.6296.101.20.5.1.6.1
		sleEponProfileIgmpSnoopingChanged NOTIFICATION-TYPE
			OBJECTS { sleEponProfileIgmpSnoopingControlRequest, sleEponProfileIgmpSnoopingControlTimeStamp, sleEponProfileIgmpSnoopingControlReqResult, sleEponProfileIgmpSnoopingControlProfileName, sleEponProfileIgmpSnoopingControlState, 
				sleEponProfileIgmpSnoopingControlMaxch, sleEponProfileIgmpSnoopingControlTagVlan }
			STATUS current
			DESCRIPTION 
				"Description."
			::= { sleEponProfileIgmpSnoopingNotification 1 }

		
		-- 1.3.6.1.4.1.6296.101.20.5.1.7
		sleEponProfileOnuRuleTable OBJECT-TYPE
			SYNTAX SEQUENCE OF SleEponProfileOnuRuleEntry
			MAX-ACCESS not-accessible
			STATUS current
			DESCRIPTION
				"Description."
			::= { sleEponProfileBase 7 }

		
		-- 1.3.6.1.4.1.6296.101.20.5.1.7.1
		sleEponProfileOnuRuleEntry OBJECT-TYPE
			SYNTAX SleEponProfileOnuRuleEntry
			MAX-ACCESS not-accessible
			STATUS current
			DESCRIPTION
				"Profile Onu rule table."
			INDEX { sleEponProfileIndex, sleEponOnuProfileOnuRuleIndex }
			::= { sleEponProfileOnuRuleTable 1 }

		
		SleEponProfileOnuRuleEntry ::=
			SEQUENCE { 
				sleEponOnuProfileOnuRuleIndex
					INTEGER,
				sleEponProfileOnuRuleName
					OCTET STRING
			 }

		-- 1.3.6.1.4.1.6296.101.20.5.1.7.1.1
		sleEponOnuProfileOnuRuleIndex OBJECT-TYPE
			SYNTAX INTEGER (0..24)
			MAX-ACCESS read-only
			STATUS current
			DESCRIPTION
				"Onu rule index."
			::= { sleEponProfileOnuRuleEntry 1 }

		
		-- 1.3.6.1.4.1.6296.101.20.5.1.7.1.2
		sleEponProfileOnuRuleName OBJECT-TYPE
			SYNTAX OCTET STRING
			MAX-ACCESS read-only
			STATUS current
			DESCRIPTION
				"Rule name."
			::= { sleEponProfileOnuRuleEntry 2 }

		
		-- 1.3.6.1.4.1.6296.101.20.5.1.8
		sleEponProfileOnuRuleControl OBJECT IDENTIFIER ::= { sleEponProfileBase 8 }

		
		-- 1.3.6.1.4.1.6296.101.20.5.1.8.1
		sleEponProfileOnuRuleControlRequest OBJECT-TYPE
			SYNTAX INTEGER
				{
				applyProfileOnuRule(1),
				noApplyProfileOnuRule(2)
				}
			MAX-ACCESS read-write
			STATUS current
			DESCRIPTION
				"The request of a user command"
			::= { sleEponProfileOnuRuleControl 1 }

		
		-- 1.3.6.1.4.1.6296.101.20.5.1.8.2
		sleEponProfileOnuRuleControlStatus OBJECT-TYPE
			SYNTAX SleControlStatusType
			MAX-ACCESS read-only
			STATUS current
			DESCRIPTION
				"The status of user command"
			::= { sleEponProfileOnuRuleControl 2 }

		
		-- 1.3.6.1.4.1.6296.101.20.5.1.8.3
		sleEponProfileOnuRuleControlTimer OBJECT-TYPE
			SYNTAX Gauge32
			MAX-ACCESS read-write
			STATUS current
			DESCRIPTION
				"The maximum time for the manager for a long running user command"
			::= { sleEponProfileOnuRuleControl 3 }

		
		-- 1.3.6.1.4.1.6296.101.20.5.1.8.4
		sleEponProfileOnuRuleControlTimeStamp OBJECT-TYPE
			SYNTAX TimeTicks
			MAX-ACCESS read-only
			STATUS current
			DESCRIPTION
				"The time stamp of the last command(end of command)"
			::= { sleEponProfileOnuRuleControl 4 }

		
		-- 1.3.6.1.4.1.6296.101.20.5.1.8.5
		sleEponProfleOnuRuleControlReqResult OBJECT-TYPE
			SYNTAX SleControlRequestResultType
			MAX-ACCESS read-write
			STATUS current
			DESCRIPTION
				"The result of the last user command"
			::= { sleEponProfileOnuRuleControl 5 }

		
		-- 1.3.6.1.4.1.6296.101.20.5.1.8.6
		sleEponProfileOnuRuleControlProfileIndex OBJECT-TYPE
			SYNTAX INTEGER (1..32)
			MAX-ACCESS read-write
			STATUS current
			DESCRIPTION
				"Profile Index"
			::= { sleEponProfileOnuRuleControl 6 }

		
		-- 1.3.6.1.4.1.6296.101.20.5.1.8.7
		sleEponProfileOnuRuleControlName OBJECT-TYPE
			SYNTAX OCTET STRING
			MAX-ACCESS read-write
			STATUS current
			DESCRIPTION
				"Rule name."
			::= { sleEponProfileOnuRuleControl 7 }

		
		-- 1.3.6.1.4.1.6296.101.20.5.1.9
		sleEponProfileOnuRuleNotification OBJECT IDENTIFIER ::= { sleEponProfileBase 9 }

		
		-- 1.3.6.1.4.1.6296.101.20.5.1.9.1
		sleEponProfileOnuRuleChanged NOTIFICATION-TYPE
			OBJECTS { sleEponProfileOnuRuleControlRequest, sleEponProfileOnuRuleControlTimeStamp, sleEponProfleOnuRuleControlReqResult, sleEponProfileOnuRuleControlName }
			STATUS current
			DESCRIPTION 
				"Create or delete rule."
			::= { sleEponProfileOnuRuleNotification 1 }

		
		-- 1.3.6.1.4.1.6296.101.20.5.2
		sleEponProfileQueue OBJECT IDENTIFIER ::= { sleEponProfile 2 }

		
		-- 1.3.6.1.4.1.6296.101.20.5.2.1
		sleEponProfileQueueTable OBJECT-TYPE
			SYNTAX SEQUENCE OF SleEponProfileQueueEntry
			MAX-ACCESS not-accessible
			STATUS current
			DESCRIPTION
				"Description."
			::= { sleEponProfileQueue 1 }

		
		-- 1.3.6.1.4.1.6296.101.20.5.2.1.1
		sleEponProfileQueueEntry OBJECT-TYPE
			SYNTAX SleEponProfileQueueEntry
			MAX-ACCESS not-accessible
			STATUS current
			DESCRIPTION
				"Description."
			INDEX { sleEponProfileIndex, sleEponProfileQueueIndex }
			::= { sleEponProfileQueueTable 1 }

		
		SleEponProfileQueueEntry ::=
			SEQUENCE { 
				sleEponProfileQueueIndex
					INTEGER,
				sleEponProfileQueueQPUpQueue
					INTEGER,
				sleEponProfileQueueQPUpMaxBandwidth
					INTEGER,
				sleEponProfileQueueQPUpMAxBurstSize
					INTEGER,
				sleEponProfileQueueQPDownQueue
					INTEGER,
				sleEponProfileQueueQPDownMaxBandwidth
					INTEGER,
				sleEponProfileQueueQPDownMAxBurstSize
					INTEGER,
				sleEponProfileQueueQLimitUpBlockSize
					INTEGER,
				sleEponProfileQueueQLimitDownBlockSize
					INTEGER
			 }

		-- 1.3.6.1.4.1.6296.101.20.5.2.1.1.1
		sleEponProfileQueueIndex OBJECT-TYPE
			SYNTAX INTEGER (1..8)
			MAX-ACCESS read-only
			STATUS current
			DESCRIPTION
				"Profile Queue index "
			::= { sleEponProfileQueueEntry 1 }

		
		-- 1.3.6.1.4.1.6296.101.20.5.2.1.1.2
		sleEponProfileQueueQPUpQueue OBJECT-TYPE
			SYNTAX INTEGER (0..7)
			MAX-ACCESS read-only
			STATUS current
			DESCRIPTION
				"Upstream queue number"
			::= { sleEponProfileQueueEntry 2 }

		
		-- 1.3.6.1.4.1.6296.101.20.5.2.1.1.3
		sleEponProfileQueueQPUpMaxBandwidth OBJECT-TYPE
			SYNTAX INTEGER (0 | 100..1000000)
			UNITS "kbps"
			MAX-ACCESS read-only
			STATUS current
			DESCRIPTION
				"Upstream queue max bandwidth"
			::= { sleEponProfileQueueEntry 3 }

		
		-- 1.3.6.1.4.1.6296.101.20.5.2.1.1.4
		sleEponProfileQueueQPUpMAxBurstSize OBJECT-TYPE
			SYNTAX INTEGER (0 | 2..16777214)
			UNITS "byte"
			MAX-ACCESS read-only
			STATUS current
			DESCRIPTION
				"Upstream queue max burst size"
			::= { sleEponProfileQueueEntry 4 }

		
		-- 1.3.6.1.4.1.6296.101.20.5.2.1.1.5
		sleEponProfileQueueQPDownQueue OBJECT-TYPE
			SYNTAX INTEGER (0..7)
			MAX-ACCESS read-only
			STATUS current
			DESCRIPTION
				"Downstream queue number"
			::= { sleEponProfileQueueEntry 5 }

		
		-- 1.3.6.1.4.1.6296.101.20.5.2.1.1.6
		sleEponProfileQueueQPDownMaxBandwidth OBJECT-TYPE
			SYNTAX INTEGER (0 | 100..1000000)
			UNITS "kbps"
			MAX-ACCESS read-only
			STATUS current
			DESCRIPTION
				"Downtream queue max bandwidth"
			::= { sleEponProfileQueueEntry 6 }

		
		-- 1.3.6.1.4.1.6296.101.20.5.2.1.1.7
		sleEponProfileQueueQPDownMAxBurstSize OBJECT-TYPE
			SYNTAX INTEGER (0 | 2..16777214)
			UNITS "byte"
			MAX-ACCESS read-only
			STATUS current
			DESCRIPTION
				"Downtream queue max burst size"
			::= { sleEponProfileQueueEntry 7 }

		
		-- 1.3.6.1.4.1.6296.101.20.5.2.1.1.8
		sleEponProfileQueueQLimitUpBlockSize OBJECT-TYPE
			SYNTAX INTEGER (-1 | 0..9215)
			MAX-ACCESS read-only
			STATUS current
			DESCRIPTION
				"Description."
			::= { sleEponProfileQueueEntry 8 }

		
		-- 1.3.6.1.4.1.6296.101.20.5.2.1.1.9
		sleEponProfileQueueQLimitDownBlockSize OBJECT-TYPE
			SYNTAX INTEGER (-1 | 0..9215)
			MAX-ACCESS read-only
			STATUS current
			DESCRIPTION
				"Description."
			::= { sleEponProfileQueueEntry 9 }

		
		-- 1.3.6.1.4.1.6296.101.20.5.2.2
		sleEponProfileQueueControl OBJECT IDENTIFIER ::= { sleEponProfileQueue 2 }

		
		-- 1.3.6.1.4.1.6296.101.20.5.2.2.1
		sleEponProfileQueueControlRequest OBJECT-TYPE
			SYNTAX INTEGER
				{
				modifyProfileQuuePolicyUp(1),
				modifyProfileQuuePolicyDown(2),
				modifyProfileQueueLimit(3)
				}
			MAX-ACCESS read-write
			STATUS current
			DESCRIPTION
				"The request of a user command"
			::= { sleEponProfileQueueControl 1 }

		
		-- 1.3.6.1.4.1.6296.101.20.5.2.2.2
		sleEponProfileQueueControlStatus OBJECT-TYPE
			SYNTAX SleControlStatusType
			MAX-ACCESS read-only
			STATUS current
			DESCRIPTION
				"The status of user command"
			::= { sleEponProfileQueueControl 2 }

		
		-- 1.3.6.1.4.1.6296.101.20.5.2.2.3
		sleEponProfileQueueControlTimer OBJECT-TYPE
			SYNTAX Gauge32
			MAX-ACCESS read-write
			STATUS current
			DESCRIPTION
				"The maximum time for the manager for a long running user command"
			::= { sleEponProfileQueueControl 3 }

		
		-- 1.3.6.1.4.1.6296.101.20.5.2.2.4
		sleEponProfileQueueControlTimeStamp OBJECT-TYPE
			SYNTAX TimeTicks
			MAX-ACCESS read-only
			STATUS current
			DESCRIPTION
				"The time stamp of the last command(end of command)"
			::= { sleEponProfileQueueControl 4 }

		
		-- 1.3.6.1.4.1.6296.101.20.5.2.2.5
		sleEponProfileQueueControlReqResult OBJECT-TYPE
			SYNTAX SleControlRequestResultType
			MAX-ACCESS read-only
			STATUS current
			DESCRIPTION
				"The result of the last user command"
			::= { sleEponProfileQueueControl 5 }

		
		-- 1.3.6.1.4.1.6296.101.20.5.2.2.6
		sleEponProfileQueueControlProfileIndex OBJECT-TYPE
			SYNTAX INTEGER (1..32)
			MAX-ACCESS read-write
			STATUS current
			DESCRIPTION
				"Profile Index"
			::= { sleEponProfileQueueControl 6 }

		
		-- 1.3.6.1.4.1.6296.101.20.5.2.2.7
		sleEponProfileQueueControlQueueIndex OBJECT-TYPE
			SYNTAX INTEGER (1..8)
			MAX-ACCESS read-write
			STATUS current
			DESCRIPTION
				"Profile Queue index "
			::= { sleEponProfileQueueControl 7 }

		
		-- 1.3.6.1.4.1.6296.101.20.5.2.2.8
		sleEponProfileQueueControlQPUpQueue OBJECT-TYPE
			SYNTAX INTEGER (0..7)
			MAX-ACCESS read-write
			STATUS current
			DESCRIPTION
				"Upstream queue number"
			::= { sleEponProfileQueueControl 8 }

		
		-- 1.3.6.1.4.1.6296.101.20.5.2.2.9
		sleEponProfileQueueControlQPUpMaxBandwidth OBJECT-TYPE
			SYNTAX INTEGER (0 | 100..1000000)
			UNITS "kbps"
			MAX-ACCESS read-write
			STATUS current
			DESCRIPTION
				"Upstream queue max bandwidth"
			::= { sleEponProfileQueueControl 9 }

		
		-- 1.3.6.1.4.1.6296.101.20.5.2.2.10
		sleEponProfileQueueControlQPUpMAxBurstSize OBJECT-TYPE
			SYNTAX INTEGER (0 | 2..16777214)
			UNITS "byte"
			MAX-ACCESS read-write
			STATUS current
			DESCRIPTION
				"Upstream queue max burst size"
			::= { sleEponProfileQueueControl 10 }

		
		-- 1.3.6.1.4.1.6296.101.20.5.2.2.11
		sleEponProfileQueueControlQPDownQueue OBJECT-TYPE
			SYNTAX INTEGER (0..7)
			MAX-ACCESS read-write
			STATUS current
			DESCRIPTION
				"Downstream queue number"
			::= { sleEponProfileQueueControl 11 }

		
		-- 1.3.6.1.4.1.6296.101.20.5.2.2.12
		sleEponProfileQueueControlQPDownMaxBandwidth OBJECT-TYPE
			SYNTAX INTEGER (0 | 100..1000000)
			UNITS "kbps"
			MAX-ACCESS read-write
			STATUS current
			DESCRIPTION
				"Downtream queue max bandwidth"
			::= { sleEponProfileQueueControl 12 }

		
		-- 1.3.6.1.4.1.6296.101.20.5.2.2.13
		sleEponProfileQueueControlQPDownMAxBurstSize OBJECT-TYPE
			SYNTAX INTEGER (0 | 2..16777214)
			UNITS "byte"
			MAX-ACCESS read-write
			STATUS current
			DESCRIPTION
				"Downtream queue max burst size"
			::= { sleEponProfileQueueControl 13 }

		
		-- 1.3.6.1.4.1.6296.101.20.5.2.2.14
		sleEponProfileQueueControlLimitFlag OBJECT-TYPE
			SYNTAX INTEGER
				{
				up(1),
				down(2)
				}
			MAX-ACCESS read-write
			STATUS current
			DESCRIPTION
				"Description."
			::= { sleEponProfileQueueControl 14 }

		
		-- 1.3.6.1.4.1.6296.101.20.5.2.2.15
		sleEponProfileQueueControlBlockSize0 OBJECT-TYPE
			SYNTAX INTEGER (-1 | 0..9215)
			MAX-ACCESS read-write
			STATUS current
			DESCRIPTION
				"Description."
			::= { sleEponProfileQueueControl 15 }

		
		-- 1.3.6.1.4.1.6296.101.20.5.2.2.16
		sleEponProfileQueueControlBlockSize1 OBJECT-TYPE
			SYNTAX INTEGER (-1 | 0..9215)
			MAX-ACCESS read-write
			STATUS current
			DESCRIPTION
				"Description."
			::= { sleEponProfileQueueControl 16 }

		
		-- 1.3.6.1.4.1.6296.101.20.5.2.2.17
		sleEponProfileQueueControlBlockSize2 OBJECT-TYPE
			SYNTAX INTEGER (-1 | 0..9215)
			MAX-ACCESS read-write
			STATUS current
			DESCRIPTION
				"Description."
			::= { sleEponProfileQueueControl 17 }

		
		-- 1.3.6.1.4.1.6296.101.20.5.2.2.18
		sleEponProfileQueueControlBlockSize3 OBJECT-TYPE
			SYNTAX INTEGER (-1 | 0..9215)
			MAX-ACCESS read-write
			STATUS current
			DESCRIPTION
				"Description."
			::= { sleEponProfileQueueControl 18 }

		
		-- 1.3.6.1.4.1.6296.101.20.5.2.2.19
		sleEponProfileQueueControlBlockSize4 OBJECT-TYPE
			SYNTAX INTEGER (-1 | 0..9152)
			MAX-ACCESS read-write
			STATUS current
			DESCRIPTION
				"Description."
			::= { sleEponProfileQueueControl 19 }

		
		-- 1.3.6.1.4.1.6296.101.20.5.2.2.20
		sleEponProfileQueueControlBlockSize5 OBJECT-TYPE
			SYNTAX INTEGER (-1 | 0..9152)
			MAX-ACCESS read-write
			STATUS current
			DESCRIPTION
				"Description."
			::= { sleEponProfileQueueControl 20 }

		
		-- 1.3.6.1.4.1.6296.101.20.5.2.2.21
		sleEponProfileQueueControlBlockSize6 OBJECT-TYPE
			SYNTAX INTEGER (-1 | 0..9152)
			MAX-ACCESS read-write
			STATUS current
			DESCRIPTION
				"Description."
			::= { sleEponProfileQueueControl 21 }

		
		-- 1.3.6.1.4.1.6296.101.20.5.2.2.22
		sleEponProfileQueueControlBlockSize7 OBJECT-TYPE
			SYNTAX INTEGER (-1 | 0..9152)
			MAX-ACCESS read-write
			STATUS current
			DESCRIPTION
				"Description."
			::= { sleEponProfileQueueControl 22 }

		
		-- 1.3.6.1.4.1.6296.101.20.5.2.3
		sleEponProfileQueueNotification OBJECT IDENTIFIER ::= { sleEponProfileQueue 3 }

		
		-- 1.3.6.1.4.1.6296.101.20.5.2.3.1
		sleEponProfileQueueModifyQueuePolicy NOTIFICATION-TYPE
			OBJECTS { sleEponProfileQueueControlRequest, sleEponProfileQueueControlTimeStamp, sleEponProfileQueueControlReqResult, sleEponProfileQueueControlProfileIndex, sleEponProfileQueueControlQueueIndex
				 }
			STATUS current
			DESCRIPTION 
				"Description."
			::= { sleEponProfileQueueNotification 1 }

		
		-- 1.3.6.1.4.1.6296.101.20.5.2.3.2
		sleEponProfileQueueModifyQueueLimit NOTIFICATION-TYPE
			OBJECTS { sleEponProfileQueueControlRequest, sleEponProfileQueueControlTimeStamp, sleEponProfileQueueControlReqResult, sleEponProfileQueueControlProfileIndex, sleEponProfileQueueControlLimitFlag, 
				sleEponProfileQueueControlBlockSize0, sleEponProfileQueueControlBlockSize1, sleEponProfileQueueControlBlockSize2, sleEponProfileQueueControlBlockSize3, sleEponProfileQueueControlBlockSize4, 
				sleEponProfileQueueControlBlockSize5, sleEponProfileQueueControlBlockSize6, sleEponProfileQueueControlBlockSize7 }
			STATUS current
			DESCRIPTION 
				"Description."
			::= { sleEponProfileQueueNotification 2 }

		
		-- 1.3.6.1.4.1.6296.101.20.5.3
		sleEponProfileVlan OBJECT IDENTIFIER ::= { sleEponProfile 3 }

		
		-- 1.3.6.1.4.1.6296.101.20.5.3.1
		sleEponProfileVlanTable OBJECT-TYPE
			SYNTAX SEQUENCE OF SleEponProfileVlanEntry
			MAX-ACCESS not-accessible
			STATUS current
			DESCRIPTION
				"Description."
			::= { sleEponProfileVlan 1 }

		
		-- 1.3.6.1.4.1.6296.101.20.5.3.1.1
		sleEponProfileVlanEntry OBJECT-TYPE
			SYNTAX SleEponProfileVlanEntry
			MAX-ACCESS not-accessible
			STATUS current
			DESCRIPTION
				"Description."
			INDEX { sleEponProfileIndex, sleEponProfileVlanIndex }
			::= { sleEponProfileVlanTable 1 }

		
		SleEponProfileVlanEntry ::=
			SEQUENCE { 
				sleEponProfileVlanIndex
					VlanIndex,
				sleEponProfileVlanEgressPorts
					PortList,
				sleEponProfileVlanUntaggedPorts
					PortList
			 }

		-- 1.3.6.1.4.1.6296.101.20.5.3.1.1.1
		sleEponProfileVlanIndex OBJECT-TYPE
			SYNTAX VlanIndex (1..4094)
			MAX-ACCESS read-only
			STATUS current
			DESCRIPTION
				"The index of ONU VLAN"
			::= { sleEponProfileVlanEntry 1 }

		
		-- 1.3.6.1.4.1.6296.101.20.5.3.1.1.2
		sleEponProfileVlanEgressPorts OBJECT-TYPE
			SYNTAX PortList
			MAX-ACCESS read-only
			STATUS current
			DESCRIPTION
				"The set of ports which are transmitting traffic for this ONU VLAN as either tagged or untagged frames."
			::= { sleEponProfileVlanEntry 2 }

		
		-- 1.3.6.1.4.1.6296.101.20.5.3.1.1.3
		sleEponProfileVlanUntaggedPorts OBJECT-TYPE
			SYNTAX PortList
			MAX-ACCESS read-only
			STATUS current
			DESCRIPTION
				"The set of ports which are transmitting traffic for this VLAN as untagged frames"
			::= { sleEponProfileVlanEntry 3 }

		
		-- 1.3.6.1.4.1.6296.101.20.5.3.2
		sleEponProfileVlanControl OBJECT IDENTIFIER ::= { sleEponProfileVlan 2 }

		
		-- 1.3.6.1.4.1.6296.101.20.5.3.2.1
		sleEponProfileVlanControlRequest OBJECT-TYPE
			SYNTAX INTEGER
				{
				createVlan(1),
				destroyVlan(2),
				setAddVlanProfile(3)
				}
			MAX-ACCESS read-write
			STATUS current
			DESCRIPTION
				"The request of a user command"
			::= { sleEponProfileVlanControl 1 }

		
		-- 1.3.6.1.4.1.6296.101.20.5.3.2.2
		sleEponProfileVlanControlStatus OBJECT-TYPE
			SYNTAX SleControlStatusType
			MAX-ACCESS read-only
			STATUS current
			DESCRIPTION
				"The status of user command"
			::= { sleEponProfileVlanControl 2 }

		
		-- 1.3.6.1.4.1.6296.101.20.5.3.2.3
		sleEponProfileVlanControlTimer OBJECT-TYPE
			SYNTAX Gauge32
			MAX-ACCESS read-write
			STATUS current
			DESCRIPTION
				"The maximum time for the manager for a long running user command"
			::= { sleEponProfileVlanControl 3 }

		
		-- 1.3.6.1.4.1.6296.101.20.5.3.2.4
		sleEponProfileVlanControlTimeStamp OBJECT-TYPE
			SYNTAX TimeTicks
			MAX-ACCESS read-only
			STATUS current
			DESCRIPTION
				"The time stamp of the last command(end of command)"
			::= { sleEponProfileVlanControl 4 }

		
		-- 1.3.6.1.4.1.6296.101.20.5.3.2.5
		sleEponProfileVlanControlReqResult OBJECT-TYPE
			SYNTAX SleControlRequestResultType
			MAX-ACCESS read-only
			STATUS current
			DESCRIPTION
				"The result of the last user command"
			::= { sleEponProfileVlanControl 5 }

		
		-- 1.3.6.1.4.1.6296.101.20.5.3.2.6
		sleEponProfileVlanControlProfileIndex OBJECT-TYPE
			SYNTAX INTEGER (1..32)
			MAX-ACCESS read-write
			STATUS current
			DESCRIPTION
				"Description."
			::= { sleEponProfileVlanControl 6 }

		
		-- 1.3.6.1.4.1.6296.101.20.5.3.2.7
		sleEponProfileVlanControlVlanIndex OBJECT-TYPE
			SYNTAX VlanIndex
			MAX-ACCESS read-write
			STATUS current
			DESCRIPTION
				"The index of ONU VLAN"
			::= { sleEponProfileVlanControl 7 }

		
		-- 1.3.6.1.4.1.6296.101.20.5.3.2.8
		sleEponProfileVlanControlVlanEgressPorts OBJECT-TYPE
			SYNTAX PortList
			MAX-ACCESS read-write
			STATUS current
			DESCRIPTION
				"The set of ports which are transmitting traffic for this ONU VLAN as either tagged or untagged frames."
			::= { sleEponProfileVlanControl 8 }

		
		-- 1.3.6.1.4.1.6296.101.20.5.3.2.9
		sleEponProfileVlanControlVlanUntaggedPorts OBJECT-TYPE
			SYNTAX PortList
			MAX-ACCESS read-write
			STATUS current
			DESCRIPTION
				"The set of ports which are transmitting traffic for this VLAN as untagged frames"
			::= { sleEponProfileVlanControl 9 }

		
		-- 1.3.6.1.4.1.6296.101.20.5.3.3
		sleEponProfileVlanNotification OBJECT IDENTIFIER ::= { sleEponProfileVlan 3 }

		
		-- 1.3.6.1.4.1.6296.101.20.5.3.3.1
		sleEponProfileVlanCreated NOTIFICATION-TYPE
			OBJECTS { sleEponProfileVlanControlRequest, sleEponProfileVlanControlTimeStamp, sleEponProfileVlanControlReqResult, sleEponProfileControlIndex, sleEponProfileControlName, 
				sleEponProfileVlanControlVlanIndex }
			STATUS current
			DESCRIPTION 
				"Description."
			::= { sleEponProfileVlanNotification 1 }

		
		-- 1.3.6.1.4.1.6296.101.20.5.3.3.2
		sleEponProfileVlanDestroyed NOTIFICATION-TYPE
			OBJECTS { sleEponProfileVlanControlRequest, sleEponProfileVlanControlTimeStamp, sleEponProfileVlanControlReqResult, sleEponProfileControlIndex, sleEponProfileControlName, 
				sleEponProfileVlanControlVlanIndex }
			STATUS current
			DESCRIPTION 
				"Description."
			::= { sleEponProfileVlanNotification 2 }

		
		-- 1.3.6.1.4.1.6296.101.20.5.3.3.3
		sleEponProfileVlanProfileChanged NOTIFICATION-TYPE
			OBJECTS { sleEponProfileVlanControlRequest, sleEponProfileVlanControlTimeStamp, sleEponProfileVlanControlReqResult, sleEponProfileControlIndex, sleEponProfileControlName, 
				sleEponProfileVlanControlVlanIndex, sleEponProfileVlanControlVlanEgressPorts, sleEponProfileVlanControlVlanUntaggedPorts }
			STATUS current
			DESCRIPTION 
				"Description."
			::= { sleEponProfileVlanNotification 3 }

		
		-- 1.3.6.1.4.1.6296.101.20.5.4
		sleEponProfilePort OBJECT IDENTIFIER ::= { sleEponProfile 4 }

		
		-- 1.3.6.1.4.1.6296.101.20.5.4.1
		sleEponProfilePortTable OBJECT-TYPE
			SYNTAX SEQUENCE OF SleEponProfilePortEntry
			MAX-ACCESS not-accessible
			STATUS current
			DESCRIPTION
				"Description."
			::= { sleEponProfilePort 1 }

		
		-- 1.3.6.1.4.1.6296.101.20.5.4.1.1
		sleEponProfilePortEntry OBJECT-TYPE
			SYNTAX SleEponProfilePortEntry
			MAX-ACCESS not-accessible
			STATUS current
			DESCRIPTION
				"Description."
			INDEX { sleEponProfileIndex, sleEponProfilePortIndex }
			::= { sleEponProfilePortTable 1 }

		
		SleEponProfilePortEntry ::=
			SEQUENCE { 
				sleEponProfilePortIndex
					INTEGER,
				sleEponProfilePortAdminStatus
					INTEGER,
				sleEponProfilePortNego
					INTEGER,
				sleEponProfilePortSpeed
					INTEGER,
				sleEponProfilePortduplex
					INTEGER,
				sleEponProfilePortMaxHost
					Integer32,
				sleEponProfilePortPvid
					VlanIndex,
				sleEponProfilePortIngressRateLimitMode
					INTEGER,
				sleEponProfilePortIngressRateLimit
					INTEGER,
				sleEponProfilePortEgressRateLimit
					INTEGER,
				sleEponProfilePortFlowControl
					INTEGER,
				sleEponProfilePortIsolationStatus
					EnableFlag,
				sleEponProfilePortMaxHostAgingTime
					INTEGER
			 }

		-- 1.3.6.1.4.1.6296.101.20.5.4.1.1.1
		sleEponProfilePortIndex OBJECT-TYPE
			SYNTAX INTEGER (1..256)
			MAX-ACCESS read-only
			STATUS current
			DESCRIPTION
				"The index of the ONU port"
			::= { sleEponProfilePortEntry 1 }

		
		-- 1.3.6.1.4.1.6296.101.20.5.4.1.1.2
		sleEponProfilePortAdminStatus OBJECT-TYPE
			SYNTAX INTEGER
				{
				enable(1),
				disable(2)
				}
			MAX-ACCESS read-only
			STATUS current
			DESCRIPTION
				"The desired state of the ONU port"
			::= { sleEponProfilePortEntry 2 }

		
		-- 1.3.6.1.4.1.6296.101.20.5.4.1.1.3
		sleEponProfilePortNego OBJECT-TYPE
			SYNTAX INTEGER
				{
				on(1),
				off(2)
				}
			MAX-ACCESS read-only
			STATUS current
			DESCRIPTION
				"The current operational state of the ONU port"
			::= { sleEponProfilePortEntry 3 }

		
		-- 1.3.6.1.4.1.6296.101.20.5.4.1.1.4
		sleEponProfilePortSpeed OBJECT-TYPE
			SYNTAX INTEGER (10 | 100 | 1000)
			UNITS "Mbits/sec"
			MAX-ACCESS read-only
			STATUS current
			DESCRIPTION
				"It's auto-negotiation for a port, automatically to match the transmission speed and the duplex mode of the attached device"
			::= { sleEponProfilePortEntry 4 }

		
		-- 1.3.6.1.4.1.6296.101.20.5.4.1.1.5
		sleEponProfilePortduplex OBJECT-TYPE
			SYNTAX INTEGER
				{
				full(1),
				half(2)
				}
			MAX-ACCESS read-only
			STATUS current
			DESCRIPTION
				"It express port speed that configure transmit rate of each port."
			::= { sleEponProfilePortEntry 5 }

		
		-- 1.3.6.1.4.1.6296.101.20.5.4.1.1.6
		sleEponProfilePortMaxHost OBJECT-TYPE
			SYNTAX Integer32
			MAX-ACCESS read-only
			STATUS current
			DESCRIPTION
				"It express half duplex or full duplex mode. Only unidirectional communication is possible on half duplex mode and bi-directional communication is possible on full duplex mode to transmit packet for two ways."
			::= { sleEponProfilePortEntry 6 }

		
		-- 1.3.6.1.4.1.6296.101.20.5.4.1.1.7
		sleEponProfilePortPvid OBJECT-TYPE
			SYNTAX VlanIndex
			MAX-ACCESS read-only
			STATUS current
			DESCRIPTION
				"It is PVID that configure in ONU port"
			::= { sleEponProfilePortEntry 7 }

		
		-- 1.3.6.1.4.1.6296.101.20.5.4.1.1.8
		sleEponProfilePortIngressRateLimitMode OBJECT-TYPE
			SYNTAX INTEGER
				{
				all(0),
				multiBroadUnicast(1),
				multiBroadcast(2),
				broadcast(3)
				}
			MAX-ACCESS read-only
			STATUS current
			DESCRIPTION
				"It is rate limit mode in Ingress
				0  Limit all frames
				 1  Limit multicast, broadcast and flooded unicast frame
				 2  Limit multicast, broadcast frame
				 3  Limit broadcast frame only"
			::= { sleEponProfilePortEntry 8 }

		
		-- 1.3.6.1.4.1.6296.101.20.5.4.1.1.9
		sleEponProfilePortIngressRateLimit OBJECT-TYPE
			SYNTAX INTEGER (0 | 62..100000)
			MAX-ACCESS read-only
			STATUS current
			DESCRIPTION
				"It is configurable port rate limit in Ingress
				The value of 0 is unlimit
				"
			DEFVAL { 0 }
			::= { sleEponProfilePortEntry 9 }

		
		-- 1.3.6.1.4.1.6296.101.20.5.4.1.1.10
		sleEponProfilePortEgressRateLimit OBJECT-TYPE
			SYNTAX INTEGER (0 | 62..100000)
			MAX-ACCESS read-only
			STATUS current
			DESCRIPTION
				"It is configurable port rate limit in Egress
				The value of 0 is unlimit
				"
			DEFVAL { 0 }
			::= { sleEponProfilePortEntry 10 }

		
		-- 1.3.6.1.4.1.6296.101.20.5.4.1.1.11
		sleEponProfilePortFlowControl OBJECT-TYPE
			SYNTAX INTEGER
				{
				on(1),
				off(2)
				}
			MAX-ACCESS read-only
			STATUS current
			DESCRIPTION
				"Description."
			::= { sleEponProfilePortEntry 11 }

		
		-- 1.3.6.1.4.1.6296.101.20.5.4.1.1.12
		sleEponProfilePortIsolationStatus OBJECT-TYPE
			SYNTAX EnableFlag
			MAX-ACCESS read-only
			STATUS current
			DESCRIPTION
				"Description."
			::= { sleEponProfilePortEntry 12 }

		
		-- 1.3.6.1.4.1.6296.101.20.5.4.1.1.13
		sleEponProfilePortMaxHostAgingTime OBJECT-TYPE
			SYNTAX INTEGER (10..300)
			MAX-ACCESS read-write
			STATUS current
			DESCRIPTION
				"Max Host Aging Time."
			::= { sleEponProfilePortEntry 13 }

		
		-- 1.3.6.1.4.1.6296.101.20.5.4.2
		sleEponProfilePortControl OBJECT IDENTIFIER ::= { sleEponProfilePort 2 }

		
		-- 1.3.6.1.4.1.6296.101.20.5.4.2.1
		sleEponProfilePortControlRequest OBJECT-TYPE
			SYNTAX INTEGER
				{
				setPortAdminStatus(1),
				setPortNego(2),
				setPortSpeed(3),
				setPortDuplex(4),
				setPortMaxHost(5),
				setPortPvid(6),
				setPortRateLimit(7),
				setPortFlowControl(8),
				setPortIsolation(9),
				setPortMaxHostAgingTime(10),
				noMaxHost(11)
				}
			MAX-ACCESS read-write
			STATUS current
			DESCRIPTION
				"The request of a user command"
			::= { sleEponProfilePortControl 1 }

		
		-- 1.3.6.1.4.1.6296.101.20.5.4.2.2
		sleEponProfilePortControlStatus OBJECT-TYPE
			SYNTAX SleControlStatusType
			MAX-ACCESS read-only
			STATUS current
			DESCRIPTION
				"The status of user command"
			::= { sleEponProfilePortControl 2 }

		
		-- 1.3.6.1.4.1.6296.101.20.5.4.2.3
		sleEponProfilePortControlTimer OBJECT-TYPE
			SYNTAX Gauge32
			MAX-ACCESS read-write
			STATUS current
			DESCRIPTION
				"The maximum time for the manager for a long running user command"
			::= { sleEponProfilePortControl 3 }

		
		-- 1.3.6.1.4.1.6296.101.20.5.4.2.4
		sleEponProfilePortControlTimeStamp OBJECT-TYPE
			SYNTAX TimeTicks
			MAX-ACCESS read-only
			STATUS current
			DESCRIPTION
				"The time stamp of the last command(end of command)"
			::= { sleEponProfilePortControl 4 }

		
		-- 1.3.6.1.4.1.6296.101.20.5.4.2.5
		sleEponProfilePortControlReqResult OBJECT-TYPE
			SYNTAX SleControlRequestResultType
			MAX-ACCESS read-only
			STATUS current
			DESCRIPTION
				"The result of the last user command"
			::= { sleEponProfilePortControl 5 }

		
		-- 1.3.6.1.4.1.6296.101.20.5.4.2.6
		sleEponProfilePortControlProfileIndex OBJECT-TYPE
			SYNTAX INTEGER (1..32)
			MAX-ACCESS read-write
			STATUS current
			DESCRIPTION
				"Description."
			::= { sleEponProfilePortControl 6 }

		
		-- 1.3.6.1.4.1.6296.101.20.5.4.2.7
		sleEponProfilePortControlPortIndex OBJECT-TYPE
			SYNTAX INTEGER (1..256)
			MAX-ACCESS read-write
			STATUS current
			DESCRIPTION
				"Description."
			::= { sleEponProfilePortControl 7 }

		
		-- 1.3.6.1.4.1.6296.101.20.5.4.2.8
		sleEponProfilePortControlAdminStatus OBJECT-TYPE
			SYNTAX INTEGER
				{
				enable(1),
				disable(2)
				}
			MAX-ACCESS read-write
			STATUS current
			DESCRIPTION
				"Description."
			DEFVAL { 0 }
			::= { sleEponProfilePortControl 8 }

		
		-- 1.3.6.1.4.1.6296.101.20.5.4.2.9
		sleEponProfilePortControlNego OBJECT-TYPE
			SYNTAX INTEGER
				{
				on(1),
				off(2)
				}
			MAX-ACCESS read-write
			STATUS current
			DESCRIPTION
				"Description."
			DEFVAL { 1 }
			::= { sleEponProfilePortControl 9 }

		
		-- 1.3.6.1.4.1.6296.101.20.5.4.2.10
		sleEponProfilePortControlSpeed OBJECT-TYPE
			SYNTAX INTEGER (10 | 100 | 1000)
			UNITS "Mbits/sec"
			MAX-ACCESS read-write
			STATUS current
			DESCRIPTION
				"Description."
			::= { sleEponProfilePortControl 10 }

		
		-- 1.3.6.1.4.1.6296.101.20.5.4.2.11
		sleEponProfilePortControlDuplex OBJECT-TYPE
			SYNTAX INTEGER
				{
				full(1),
				half(2)
				}
			MAX-ACCESS read-write
			STATUS current
			DESCRIPTION
				"Description."
			DEFVAL { 1 }
			::= { sleEponProfilePortControl 11 }

		
		-- 1.3.6.1.4.1.6296.101.20.5.4.2.12
		sleEponProfilePortControlMaxHost OBJECT-TYPE
			SYNTAX Integer32
			MAX-ACCESS read-write
			STATUS current
			DESCRIPTION
				"Description."
			::= { sleEponProfilePortControl 12 }

		
		-- 1.3.6.1.4.1.6296.101.20.5.4.2.13
		sleEponProfilePortControlPvid OBJECT-TYPE
			SYNTAX VlanIndex
			MAX-ACCESS read-write
			STATUS current
			DESCRIPTION
				"It is PVID that configure in ONU port"
			DEFVAL { '1'b }
			::= { sleEponProfilePortControl 13 }

		
		-- 1.3.6.1.4.1.6296.101.20.5.4.2.14
		sleEponProfilePortControlIngressRateLimitMode OBJECT-TYPE
			SYNTAX INTEGER
				{
				all(0),
				multiBroadUnicast(1),
				multiBroadcast(2),
				broadcast(3)
				}
			MAX-ACCESS read-write
			STATUS current
			DESCRIPTION
				"It is rate limit mode in Ingress 
				0  Limit all frames
				  1  Limit multicast, broadcast and flooded unicast frame
				  2  Limit multicast, broadcast frame
				  3  Limit broadcast frame only"
			DEFVAL { 0 }
			::= { sleEponProfilePortControl 14 }

		
		-- 1.3.6.1.4.1.6296.101.20.5.4.2.15
		sleEponProfilePortControlIngressRateLimit OBJECT-TYPE
			SYNTAX INTEGER (62..100000)
			MAX-ACCESS read-write
			STATUS current
			DESCRIPTION
				"It is configurable port rate limit in Ingress
				The value of 0 is unlimit
				"
			DEFVAL { 0 }
			::= { sleEponProfilePortControl 15 }

		
		-- 1.3.6.1.4.1.6296.101.20.5.4.2.16
		sleEponProfilePortControlEgressRateLimit OBJECT-TYPE
			SYNTAX INTEGER (62..100000)
			MAX-ACCESS read-write
			STATUS current
			DESCRIPTION
				"It is configurable port rate limit in Egress
				The value of 0 is unlimit
				"
			DEFVAL { 0 }
			::= { sleEponProfilePortControl 16 }

		
		-- 1.3.6.1.4.1.6296.101.20.5.4.2.17
		sleEponProfilePortControlFlowControl OBJECT-TYPE
			SYNTAX INTEGER
				{
				on(1),
				off(2)
				}
			MAX-ACCESS read-write
			STATUS current
			DESCRIPTION
				"Description."
			::= { sleEponProfilePortControl 17 }

		
		-- 1.3.6.1.4.1.6296.101.20.5.4.2.18
		sleEponProfilePortControlIsolationStatus OBJECT-TYPE
			SYNTAX EnableFlag
			MAX-ACCESS read-write
			STATUS current
			DESCRIPTION
				"Description."
			::= { sleEponProfilePortControl 18 }

		
		-- 1.3.6.1.4.1.6296.101.20.5.4.2.19
		sleEponProfilePortControlMaxHostAgingTime OBJECT-TYPE
			SYNTAX INTEGER (10..300)
			MAX-ACCESS read-write
			STATUS current
			DESCRIPTION
				"Max Host Aging Time."
			::= { sleEponProfilePortControl 19 }

		
		-- 1.3.6.1.4.1.6296.101.20.5.4.3
		sleEponProfilePortNotification OBJECT IDENTIFIER ::= { sleEponProfilePort 3 }

		
		-- 1.3.6.1.4.1.6296.101.20.5.4.3.1
		sleEponProfilePortAdminStatusChanged NOTIFICATION-TYPE
			OBJECTS { sleEponProfilePortControlRequest, sleEponProfilePortControlTimeStamp, sleEponProfilePortControlReqResult, sleEponProfilePortControlProfileIndex, sleEponProfileControlName, 
				sleEponProfilePortControlPortIndex, sleEponProfilePortControlAdminStatus }
			STATUS current
			DESCRIPTION 
				"Description."
			::= { sleEponProfilePortNotification 1 }

		
		-- 1.3.6.1.4.1.6296.101.20.5.4.3.2
		sleEponProfilePortNegoChanged NOTIFICATION-TYPE
			OBJECTS { sleEponProfilePortControlRequest, sleEponProfilePortControlTimeStamp, sleEponProfilePortControlReqResult, sleEponProfilePortControlProfileIndex, sleEponProfilePortControlPortIndex, 
				sleEponProfilePortControlNego, sleEponProfileControlName }
			STATUS current
			DESCRIPTION 
				"Description."
			::= { sleEponProfilePortNotification 2 }

		
		-- 1.3.6.1.4.1.6296.101.20.5.4.3.3
		sleEponProfilePortSpeedChanged NOTIFICATION-TYPE
			OBJECTS { sleEponProfilePortControlRequest, sleEponProfilePortControlTimeStamp, sleEponProfilePortControlReqResult, sleEponProfilePortControlProfileIndex, sleEponProfileControlName, 
				sleEponProfilePortControlPortIndex, sleEponProfilePortControlSpeed }
			STATUS current
			DESCRIPTION 
				"Description."
			::= { sleEponProfilePortNotification 3 }

		
		-- 1.3.6.1.4.1.6296.101.20.5.4.3.4
		sleEponProfilePortDuplexChanged NOTIFICATION-TYPE
			OBJECTS { sleEponProfilePortControlRequest, sleEponProfilePortControlTimeStamp, sleEponProfilePortControlReqResult, sleEponProfilePortControlProfileIndex, sleEponProfileControlName, 
				sleEponProfilePortControlPortIndex, sleEponProfilePortControlDuplex }
			STATUS current
			DESCRIPTION 
				"Description."
			::= { sleEponProfilePortNotification 4 }

		
		-- 1.3.6.1.4.1.6296.101.20.5.4.3.5
		sleEponProfilePortMaxHostChanged NOTIFICATION-TYPE
			OBJECTS { sleEponProfilePortControlRequest, sleEponProfilePortControlTimeStamp, sleEponProfilePortControlReqResult, sleEponProfilePortControlProfileIndex, sleEponProfileControlName, 
				sleEponProfilePortControlPortIndex, sleEponProfilePortControlMaxHost }
			STATUS current
			DESCRIPTION 
				"Description."
			::= { sleEponProfilePortNotification 5 }

		
		-- 1.3.6.1.4.1.6296.101.20.5.4.3.6
		sleEponProfilePortPvidChanged NOTIFICATION-TYPE
			OBJECTS { sleEponProfilePortControlRequest, sleEponProfilePortControlTimeStamp, sleEponProfilePortControlReqResult, sleEponProfilePortControlProfileIndex, sleEponProfileControlName, 
				sleEponProfilePortControlPortIndex, sleEponProfilePortControlPvid }
			STATUS current
			DESCRIPTION 
				"Description."
			::= { sleEponProfilePortNotification 6 }

		
		-- 1.3.6.1.4.1.6296.101.20.5.4.3.7
		sleEponProfilePortRateLimitChanged NOTIFICATION-TYPE
			OBJECTS { sleEponProfilePortControlRequest, sleEponProfilePortControlTimeStamp, sleEponProfilePortControlReqResult, sleEponProfilePortControlProfileIndex, sleEponProfileControlName, 
				sleEponProfilePortControlPortIndex, sleEponProfilePortControlIngressRateLimitMode, sleEponProfilePortControlIngressRateLimit, sleEponProfilePortControlEgressRateLimit }
			STATUS current
			DESCRIPTION 
				"Description."
			::= { sleEponProfilePortNotification 7 }

		
		-- 1.3.6.1.4.1.6296.101.20.5.4.3.8
		sleEponProfilePortFlowControlChanged NOTIFICATION-TYPE
			OBJECTS { sleEponProfilePortControlRequest, sleEponProfilePortControlTimeStamp, sleEponProfilePortControlReqResult, sleEponProfilePortControlProfileIndex, sleEponProfileControlName, 
				sleEponProfilePortControlPortIndex, sleEponProfilePortControlFlowControl }
			STATUS current
			DESCRIPTION 
				"Description."
			::= { sleEponProfilePortNotification 8 }

		
		-- 1.3.6.1.4.1.6296.101.20.5.4.3.9
		sleEponProfilePortIsolationChanged NOTIFICATION-TYPE
			OBJECTS { sleEponProfilePortControlRequest, sleEponProfilePortControlTimeStamp, sleEponProfilePortControlReqResult, sleEponProfilePortControlProfileIndex, sleEponProfilePortControlPortIndex, 
				sleEponProfilePortControlIsolationStatus }
			STATUS current
			DESCRIPTION 
				"Description."
			::= { sleEponProfilePortNotification 9 }

		
		-- 1.3.6.1.4.1.6296.101.20.5.5
		sleEponProfileClassification OBJECT IDENTIFIER ::= { sleEponProfile 5 }

		
		-- 1.3.6.1.4.1.6296.101.20.5.5.1
		sleEponProfileClassificationTable OBJECT-TYPE
			SYNTAX SEQUENCE OF SleEponProfileClassificationEntry
			MAX-ACCESS not-accessible
			STATUS current
			DESCRIPTION
				"Description."
			::= { sleEponProfileClassification 1 }

		
		-- 1.3.6.1.4.1.6296.101.20.5.5.1.1
		sleEponProfileClassificationEntry OBJECT-TYPE
			SYNTAX SleEponProfileClassificationEntry
			MAX-ACCESS not-accessible
			STATUS current
			DESCRIPTION
				"Description."
			INDEX { sleEponProfileIndex, sleEponProfileClassificationIndex }
			::= { sleEponProfileClassificationTable 1 }

		
		SleEponProfileClassificationEntry ::=
			SEQUENCE { 
				sleEponProfileClassificationIndex
					INTEGER,
				sleEponProfileClassificationMatchAction
					INTEGER,
				sleEponProfileClassificationQueue
					INTEGER
			 }

		-- 1.3.6.1.4.1.6296.101.20.5.5.1.1.1
		sleEponProfileClassificationIndex OBJECT-TYPE
			SYNTAX INTEGER (1..256)
			MAX-ACCESS read-only
			STATUS current
			DESCRIPTION
				"Description."
			::= { sleEponProfileClassificationEntry 1 }

		
		-- 1.3.6.1.4.1.6296.101.20.5.5.1.1.2
		sleEponProfileClassificationMatchAction OBJECT-TYPE
			SYNTAX INTEGER
				{
				permit(1),
				deny(2),
				notUse(3)
				}
			MAX-ACCESS read-only
			STATUS current
			DESCRIPTION
				"Description."
			::= { sleEponProfileClassificationEntry 2 }

		
		-- 1.3.6.1.4.1.6296.101.20.5.5.1.1.3
		sleEponProfileClassificationQueue OBJECT-TYPE
			SYNTAX INTEGER (-1 | 0..7)
			MAX-ACCESS read-only
			STATUS current
			DESCRIPTION
				"The value of -1 is all of the queue"
			::= { sleEponProfileClassificationEntry 3 }

		
		-- 1.3.6.1.4.1.6296.101.20.5.5.2
		sleEponProfileClassificationControl OBJECT IDENTIFIER ::= { sleEponProfileClassification 2 }

		
		-- 1.3.6.1.4.1.6296.101.20.5.5.2.1
		sleEponProfileClassificationControlRequest OBJECT-TYPE
			SYNTAX INTEGER
				{
				createClassification(1),
				destroyClassification(2)
				}
			MAX-ACCESS read-write
			STATUS current
			DESCRIPTION
				"Description."
			::= { sleEponProfileClassificationControl 1 }

		
		-- 1.3.6.1.4.1.6296.101.20.5.5.2.2
		sleEponProfileClassificationControlStatus OBJECT-TYPE
			SYNTAX SleControlStatusType
			MAX-ACCESS read-only
			STATUS current
			DESCRIPTION
				"Description."
			::= { sleEponProfileClassificationControl 2 }

		
		-- 1.3.6.1.4.1.6296.101.20.5.5.2.3
		sleEponProfileClassificationControlTimer OBJECT-TYPE
			SYNTAX Gauge32
			MAX-ACCESS read-write
			STATUS current
			DESCRIPTION
				"Description."
			::= { sleEponProfileClassificationControl 3 }

		
		-- 1.3.6.1.4.1.6296.101.20.5.5.2.4
		sleEponProfileClassificationControlTimeStamp OBJECT-TYPE
			SYNTAX TimeTicks
			MAX-ACCESS read-only
			STATUS current
			DESCRIPTION
				"Description."
			::= { sleEponProfileClassificationControl 4 }

		
		-- 1.3.6.1.4.1.6296.101.20.5.5.2.5
		sleEponProfileClassificationControlReqResult OBJECT-TYPE
			SYNTAX SleControlRequestResultType
			MAX-ACCESS read-only
			STATUS current
			DESCRIPTION
				"Description."
			::= { sleEponProfileClassificationControl 5 }

		
		-- 1.3.6.1.4.1.6296.101.20.5.5.2.6
		sleEponProfileClassificationControlProfileIndex OBJECT-TYPE
			SYNTAX INTEGER (1..32)
			MAX-ACCESS read-write
			STATUS current
			DESCRIPTION
				"Description."
			::= { sleEponProfileClassificationControl 6 }

		
		-- 1.3.6.1.4.1.6296.101.20.5.5.2.7
		sleEponProfileClassificationControlClassificationIndex OBJECT-TYPE
			SYNTAX INTEGER (1..256)
			MAX-ACCESS read-write
			STATUS current
			DESCRIPTION
				"Description."
			::= { sleEponProfileClassificationControl 7 }

		
		-- 1.3.6.1.4.1.6296.101.20.5.5.2.8
		sleEponProfileClassificationControlMatchAction OBJECT-TYPE
			SYNTAX INTEGER
				{
				permit(1),
				deny(2),
				notUse(3)
				}
			MAX-ACCESS read-write
			STATUS current
			DESCRIPTION
				"Description."
			::= { sleEponProfileClassificationControl 8 }

		
		-- 1.3.6.1.4.1.6296.101.20.5.5.2.9
		sleEponProfileClassificationControlQueue OBJECT-TYPE
			SYNTAX INTEGER (-1 | 0..7)
			MAX-ACCESS read-write
			STATUS current
			DESCRIPTION
				"Description."
			::= { sleEponProfileClassificationControl 9 }

		
		-- 1.3.6.1.4.1.6296.101.20.5.5.3
		sleEponProfileClassificationNotification OBJECT IDENTIFIER ::= { sleEponProfileClassification 3 }

		
		-- 1.3.6.1.4.1.6296.101.20.5.5.3.1
		sleEponProfileClassificationCreated NOTIFICATION-TYPE
			OBJECTS { sleEponProfileClassificationControlRequest, sleEponProfileClassificationControlTimeStamp, sleEponProfileClassificationControlReqResult, sleEponProfileClassificationControlProfileIndex, sleEponProfileClassificationControlClassificationIndex, 
				sleEponProfileClassificationControlMatchAction, sleEponProfileClassificationControlQueue }
			STATUS current
			DESCRIPTION 
				"Description."
			::= { sleEponProfileClassificationNotification 1 }

		
		-- 1.3.6.1.4.1.6296.101.20.5.5.3.2
		sleEponProfileClassificationDestroyed NOTIFICATION-TYPE
			OBJECTS { sleEponProfileClassificationControlRequest, sleEponProfileClassificationControlTimeStamp, sleEponProfileClassificationControlReqResult, sleEponProfileClassificationControlProfileIndex, sleEponProfileControlName, 
				sleEponProfileClassificationControlClassificationIndex, sleEponOnuClassificationControlName }
			STATUS current
			DESCRIPTION 
				"Description."
			::= { sleEponProfileClassificationNotification 2 }

		
		-- 1.3.6.1.4.1.6296.101.20.5.6
		sleEponProfileUNIQueue OBJECT IDENTIFIER ::= { sleEponProfile 6 }

		
		-- 1.3.6.1.4.1.6296.101.20.5.6.1
		sleEponProfileUNIQueueTable OBJECT-TYPE
			SYNTAX SEQUENCE OF SleEponProfileUNIQueueEntry
			MAX-ACCESS not-accessible
			STATUS current
			DESCRIPTION
				"Description."
			::= { sleEponProfileUNIQueue 1 }

		
		-- 1.3.6.1.4.1.6296.101.20.5.6.1.1
		sleEponProfileUNIQueueEntry OBJECT-TYPE
			SYNTAX SleEponProfileUNIQueueEntry
			MAX-ACCESS not-accessible
			STATUS current
			DESCRIPTION
				"Description."
			INDEX { sleEponProfileIndex }
			::= { sleEponProfileUNIQueueTable 1 }

		
		SleEponProfileUNIQueueEntry ::=
			SEQUENCE { 
				sleEponProfileUNIQueueUpMaxBandwidth
					INTEGER,
				sleEponProfileUNIQueueUpMaxBurstSize
					INTEGER,
				sleEponProfileUNIQueueDownMaxBandwidth
					INTEGER,
				sleEponProfileUNIQueueDownMaxBurstSize
					INTEGER
			 }

		-- 1.3.6.1.4.1.6296.101.20.5.6.1.1.1
		sleEponProfileUNIQueueUpMaxBandwidth OBJECT-TYPE
			SYNTAX INTEGER (100..1000000)
			UNITS "kbps"
			MAX-ACCESS read-only
			STATUS current
			DESCRIPTION
				"Description."
			::= { sleEponProfileUNIQueueEntry 1 }

		
		-- 1.3.6.1.4.1.6296.101.20.5.6.1.1.2
		sleEponProfileUNIQueueUpMaxBurstSize OBJECT-TYPE
			SYNTAX INTEGER (128..16777214)
			UNITS "byte"
			MAX-ACCESS read-only
			STATUS current
			DESCRIPTION
				"Description."
			::= { sleEponProfileUNIQueueEntry 2 }

		
		-- 1.3.6.1.4.1.6296.101.20.5.6.1.1.3
		sleEponProfileUNIQueueDownMaxBandwidth OBJECT-TYPE
			SYNTAX INTEGER (100..1000000)
			UNITS "kbps"
			MAX-ACCESS read-only
			STATUS current
			DESCRIPTION
				"Description."
			::= { sleEponProfileUNIQueueEntry 3 }

		
		-- 1.3.6.1.4.1.6296.101.20.5.6.1.1.4
		sleEponProfileUNIQueueDownMaxBurstSize OBJECT-TYPE
			SYNTAX INTEGER (128..16777214)
			MAX-ACCESS read-only
			STATUS current
			DESCRIPTION
				"Description."
			::= { sleEponProfileUNIQueueEntry 4 }

		
		-- 1.3.6.1.4.1.6296.101.20.5.6.2
		sleEponProfileUNIQueueControl OBJECT IDENTIFIER ::= { sleEponProfileUNIQueue 2 }

		
		-- 1.3.6.1.4.1.6296.101.20.5.6.2.1
		sleEponProfileUNIQueueControlRequest OBJECT-TYPE
			SYNTAX INTEGER
				{
				modifyProfileUNIQuuePolicyUp(1),
				modifyProfileUNIQuuePolicyDown(2)
				}
			MAX-ACCESS read-write
			STATUS current
			DESCRIPTION
				"Description."
			::= { sleEponProfileUNIQueueControl 1 }

		
		-- 1.3.6.1.4.1.6296.101.20.5.6.2.2
		sleEponProfileUNIQueueControlStatus OBJECT-TYPE
			SYNTAX SleControlStatusType
			MAX-ACCESS read-only
			STATUS current
			DESCRIPTION
				"Description."
			::= { sleEponProfileUNIQueueControl 2 }

		
		-- 1.3.6.1.4.1.6296.101.20.5.6.2.3
		sleEponProfileUNIQueueControlTimer OBJECT-TYPE
			SYNTAX Gauge32
			MAX-ACCESS read-write
			STATUS current
			DESCRIPTION
				"Description."
			::= { sleEponProfileUNIQueueControl 3 }

		
		-- 1.3.6.1.4.1.6296.101.20.5.6.2.4
		sleEponProfileUNIQueueControlTimeStamp OBJECT-TYPE
			SYNTAX TimeTicks
			MAX-ACCESS read-only
			STATUS current
			DESCRIPTION
				"Description."
			::= { sleEponProfileUNIQueueControl 4 }

		
		-- 1.3.6.1.4.1.6296.101.20.5.6.2.5
		sleEponProfileUNIQueueControlReqResult OBJECT-TYPE
			SYNTAX SleControlRequestResultType
			MAX-ACCESS read-only
			STATUS current
			DESCRIPTION
				"Description."
			::= { sleEponProfileUNIQueueControl 5 }

		
		-- 1.3.6.1.4.1.6296.101.20.5.6.2.6
		sleEponProfileUNIQueueControlProfileIndex OBJECT-TYPE
			SYNTAX INTEGER (1..32)
			MAX-ACCESS read-write
			STATUS current
			DESCRIPTION
				"Description."
			::= { sleEponProfileUNIQueueControl 6 }

		
		-- 1.3.6.1.4.1.6296.101.20.5.6.2.7
		sleEponProfileUNIQueueControlUpMaxBandwidth OBJECT-TYPE
			SYNTAX INTEGER (0 | 100..1000000)
			UNITS "kbps"
			MAX-ACCESS read-write
			STATUS current
			DESCRIPTION
				"Description."
			::= { sleEponProfileUNIQueueControl 7 }

		
		-- 1.3.6.1.4.1.6296.101.20.5.6.2.8
		sleEponProfileUNIQueueControlUpMaxBurstSize OBJECT-TYPE
			SYNTAX INTEGER (0 | 128..16777214)
			UNITS "byte"
			MAX-ACCESS read-write
			STATUS current
			DESCRIPTION
				"Description."
			::= { sleEponProfileUNIQueueControl 8 }

		
		-- 1.3.6.1.4.1.6296.101.20.5.6.2.9
		sleEponProfileUNIQueueControlDownMaxBandwidth OBJECT-TYPE
			SYNTAX INTEGER (0 | 100..1000000)
			UNITS "kbps"
			MAX-ACCESS read-write
			STATUS current
			DESCRIPTION
				"Description."
			::= { sleEponProfileUNIQueueControl 9 }

		
		-- 1.3.6.1.4.1.6296.101.20.5.6.2.10
		sleEponProfileUNIQueueControlDownMaxBurstSize OBJECT-TYPE
			SYNTAX INTEGER (0 | 128..16777214)
			UNITS "byte"
			MAX-ACCESS read-write
			STATUS current
			DESCRIPTION
				"Description."
			::= { sleEponProfileUNIQueueControl 10 }

		
		-- 1.3.6.1.4.1.6296.101.20.5.6.3
		sleEponProfileUNIQueueNotification OBJECT IDENTIFIER ::= { sleEponProfileUNIQueue 3 }

		
		-- 1.3.6.1.4.1.6296.101.20.5.6.3.1
		sleEponProfileUNIQueueModifyQueuePolicy NOTIFICATION-TYPE
			OBJECTS { sleEponProfileUNIQueueControlRequest, sleEponProfileUNIQueueControlTimeStamp, sleEponProfileUNIQueueControlReqResult, sleEponProfileUNIQueueControlProfileIndex }
			STATUS current
			DESCRIPTION 
				"Description."
			::= { sleEponProfileUNIQueueNotification 1 }

		
		-- 1.3.6.1.4.1.6296.101.20.6
		sleEponAlarm OBJECT IDENTIFIER ::= { sleEpon 6 }

		
		-- 1.3.6.1.4.1.6296.101.20.6.1
		sleEponAlarmTable OBJECT-TYPE
			SYNTAX SEQUENCE OF SleEponAlarmEntry
			MAX-ACCESS not-accessible
			STATUS current
			DESCRIPTION
				"Description."
			::= { sleEponAlarm 1 }

		
		-- 1.3.6.1.4.1.6296.101.20.6.1.1
		sleEponAlarmEntry OBJECT-TYPE
			SYNTAX SleEponAlarmEntry
			MAX-ACCESS not-accessible
			STATUS current
			DESCRIPTION
				"Description."
			INDEX { sleEponOltIndex }
			::= { sleEponAlarmTable 1 }

		
		SleEponAlarmEntry ::=
			SEQUENCE { 
				sleEponAlarmBadEncryption
					EnableFlag,
				sleEponAlarmDyingGasp
					EnableFlag,
				sleEponAlarmLlidMismatch
					EnableFlag,
				sleEponAlarmOnuRegistrationError
					EnableFlag,
				sleEponAlarmTooManyOnuRegistration
					EnableFlag,
				sleEponAlarmOpticSignalError
					EnableFlag,
				sleEponAlarmStandardLinkFault
					EnableFlag,
				sleEponAlarmLossOfSignal
					EnableFlag,
				sleEponAlarmTransmitFail
					EnableFlag,
				sleEponAlarmMacLearningOverflow
					EnableFlag,
				sleEponAlarmLoopback
					EnableFlag,
				sleEponAlarmStandardDyingGasp
					EnableFlag,
				sleEponAlarmExternalDyingGasp
					EnableFlag,
				sleEponAlarmStandardCriticalEvent
					EnableFlag,
				sleEponAlarmExternalCriticalEvent
					EnableFlag,
				sleEponAlarmEponStandbyLos
					EnableFlag
			 }

		-- 1.3.6.1.4.1.6296.101.20.6.1.1.1
		sleEponAlarmBadEncryption OBJECT-TYPE
			SYNTAX EnableFlag
			MAX-ACCESS read-only
			STATUS current
			DESCRIPTION
				"alarm type: Bad encryption"
			DEFVAL { enable }
			::= { sleEponAlarmEntry 1 }

		
		-- 1.3.6.1.4.1.6296.101.20.6.1.1.2
		sleEponAlarmDyingGasp OBJECT-TYPE
			SYNTAX EnableFlag
			MAX-ACCESS read-only
			STATUS current
			DESCRIPTION
				"alarm type: Dying gasp"
			DEFVAL { enable }
			::= { sleEponAlarmEntry 2 }

		
		-- 1.3.6.1.4.1.6296.101.20.6.1.1.3
		sleEponAlarmLlidMismatch OBJECT-TYPE
			SYNTAX EnableFlag
			MAX-ACCESS read-only
			STATUS current
			DESCRIPTION
				"alarm type: llid mismatch"
			DEFVAL { enable }
			::= { sleEponAlarmEntry 3 }

		
		-- 1.3.6.1.4.1.6296.101.20.6.1.1.4
		sleEponAlarmOnuRegistrationError OBJECT-TYPE
			SYNTAX EnableFlag
			MAX-ACCESS read-only
			STATUS current
			DESCRIPTION
				"alarm type: onu registration error"
			DEFVAL { enable }
			::= { sleEponAlarmEntry 4 }

		
		-- 1.3.6.1.4.1.6296.101.20.6.1.1.5
		sleEponAlarmTooManyOnuRegistration OBJECT-TYPE
			SYNTAX EnableFlag
			MAX-ACCESS read-only
			STATUS current
			DESCRIPTION
				"alarm type: too many onu registration"
			DEFVAL { enable }
			::= { sleEponAlarmEntry 5 }

		
		-- 1.3.6.1.4.1.6296.101.20.6.1.1.6
		sleEponAlarmOpticSignalError OBJECT-TYPE
			SYNTAX EnableFlag
			MAX-ACCESS read-only
			STATUS current
			DESCRIPTION
				"alarm type: onu optical signal error"
			DEFVAL { enable }
			::= { sleEponAlarmEntry 6 }

		
		-- 1.3.6.1.4.1.6296.101.20.6.1.1.7
		sleEponAlarmStandardLinkFault OBJECT-TYPE
			SYNTAX EnableFlag
			MAX-ACCESS read-only
			STATUS current
			DESCRIPTION
				"alarm type: link falult"
			DEFVAL { enable }
			::= { sleEponAlarmEntry 7 }

		
		-- 1.3.6.1.4.1.6296.101.20.6.1.1.8
		sleEponAlarmLossOfSignal OBJECT-TYPE
			SYNTAX EnableFlag
			MAX-ACCESS read-only
			STATUS current
			DESCRIPTION
				"alarm type:loss of signal."
			DEFVAL { enable }
			::= { sleEponAlarmEntry 8 }

		
		-- 1.3.6.1.4.1.6296.101.20.6.1.1.9
		sleEponAlarmTransmitFail OBJECT-TYPE
			SYNTAX EnableFlag
			MAX-ACCESS read-only
			STATUS current
			DESCRIPTION
				"alarm type: transmit fail."
			DEFVAL { enable }
			::= { sleEponAlarmEntry 9 }

		
		-- 1.3.6.1.4.1.6296.101.20.6.1.1.10
		sleEponAlarmMacLearningOverflow OBJECT-TYPE
			SYNTAX EnableFlag
			MAX-ACCESS read-only
			STATUS current
			DESCRIPTION
				"alarm type: mac learning overflow."
			DEFVAL { enable }
			::= { sleEponAlarmEntry 10 }

		
		-- 1.3.6.1.4.1.6296.101.20.6.1.1.11
		sleEponAlarmLoopback OBJECT-TYPE
			SYNTAX EnableFlag
			MAX-ACCESS read-write
			STATUS current
			DESCRIPTION
				"alarm type: loopback."
			DEFVAL { enable }
			::= { sleEponAlarmEntry 11 }

		
		-- 1.3.6.1.4.1.6296.101.20.6.1.1.12
		sleEponAlarmStandardDyingGasp OBJECT-TYPE
			SYNTAX EnableFlag
			MAX-ACCESS read-only
			STATUS current
			DESCRIPTION
				"alarm type:standard dying gasp."
			DEFVAL { enable }
			::= { sleEponAlarmEntry 12 }

		
		-- 1.3.6.1.4.1.6296.101.20.6.1.1.13
		sleEponAlarmExternalDyingGasp OBJECT-TYPE
			SYNTAX EnableFlag
			MAX-ACCESS read-only
			STATUS current
			DESCRIPTION
				"alarm type :external dying gasp."
			DEFVAL { enable }
			::= { sleEponAlarmEntry 13 }

		
		-- 1.3.6.1.4.1.6296.101.20.6.1.1.14
		sleEponAlarmStandardCriticalEvent OBJECT-TYPE
			SYNTAX EnableFlag
			MAX-ACCESS read-only
			STATUS current
			DESCRIPTION
				"alarm type:standard critical event.
				"
			DEFVAL { enable }
			::= { sleEponAlarmEntry 14 }

		
		-- 1.3.6.1.4.1.6296.101.20.6.1.1.15
		sleEponAlarmExternalCriticalEvent OBJECT-TYPE
			SYNTAX EnableFlag
			MAX-ACCESS read-only
			STATUS current
			DESCRIPTION
				"alarm type:external critical event."
			DEFVAL { enable }
			::= { sleEponAlarmEntry 15 }

		
		-- 1.3.6.1.4.1.6296.101.20.6.1.1.16
		sleEponAlarmEponStandbyLos OBJECT-TYPE
			SYNTAX EnableFlag
			MAX-ACCESS read-only
			STATUS current
			DESCRIPTION
				"alarm type: epon standby lose."
			DEFVAL { enable }
			::= { sleEponAlarmEntry 16 }

		
		-- 1.3.6.1.4.1.6296.101.20.6.2
		sleEponAlarmControl OBJECT IDENTIFIER ::= { sleEponAlarm 2 }

		
		-- 1.3.6.1.4.1.6296.101.20.6.2.1
		sleEponAlarmControlRequest OBJECT-TYPE
			SYNTAX INTEGER
				{
				setEponAlarmProfile(1),
				setEponAlarm(2)
				}
			MAX-ACCESS read-write
			STATUS current
			DESCRIPTION
				"The request of a user command"
			::= { sleEponAlarmControl 1 }

		
		-- 1.3.6.1.4.1.6296.101.20.6.2.2
		sleEponAlarmControlStatus OBJECT-TYPE
			SYNTAX SleControlStatusType
			MAX-ACCESS read-only
			STATUS current
			DESCRIPTION
				"The status of user command"
			::= { sleEponAlarmControl 2 }

		
		-- 1.3.6.1.4.1.6296.101.20.6.2.3
		sleEponAlarmControlTimer OBJECT-TYPE
			SYNTAX Gauge32
			MAX-ACCESS read-write
			STATUS current
			DESCRIPTION
				"The maximum time for the manager for a long running user command"
			::= { sleEponAlarmControl 3 }

		
		-- 1.3.6.1.4.1.6296.101.20.6.2.4
		sleEponAlarmControlTimeStamp OBJECT-TYPE
			SYNTAX TimeTicks
			MAX-ACCESS read-only
			STATUS current
			DESCRIPTION
				"The time stamp of the last command(end of command)"
			::= { sleEponAlarmControl 4 }

		
		-- 1.3.6.1.4.1.6296.101.20.6.2.5
		sleEponAlarmControlReqResult OBJECT-TYPE
			SYNTAX SleControlRequestResultType
			MAX-ACCESS read-only
			STATUS current
			DESCRIPTION
				"The result of the last user command"
			::= { sleEponAlarmControl 5 }

		
		-- 1.3.6.1.4.1.6296.101.20.6.2.6
		sleEponAlarmControlOltIndex OBJECT-TYPE
			SYNTAX Integer32
			MAX-ACCESS read-write
			STATUS current
			DESCRIPTION
				"OLT index"
			::= { sleEponAlarmControl 6 }

		
		-- 1.3.6.1.4.1.6296.101.20.6.2.7
		sleEponAlarmControlBadEncryption OBJECT-TYPE
			SYNTAX EnableFlag
			MAX-ACCESS read-write
			STATUS current
			DESCRIPTION
				"disable(1), enable(2)"
			DEFVAL { enable }
			::= { sleEponAlarmControl 7 }

		
		-- 1.3.6.1.4.1.6296.101.20.6.2.8
		sleEponAlarmControlDyingGasp OBJECT-TYPE
			SYNTAX EnableFlag
			MAX-ACCESS read-write
			STATUS current
			DESCRIPTION
				"disable(1), enable(2)"
			DEFVAL { enable }
			::= { sleEponAlarmControl 8 }

		
		-- 1.3.6.1.4.1.6296.101.20.6.2.9
		sleEponAlarmControlLlidMismatch OBJECT-TYPE
			SYNTAX EnableFlag
			MAX-ACCESS read-write
			STATUS current
			DESCRIPTION
				"disable(1), enable(2)"
			DEFVAL { enable }
			::= { sleEponAlarmControl 9 }

		
		-- 1.3.6.1.4.1.6296.101.20.6.2.10
		sleEponAlarmControlOnuRegistrationError OBJECT-TYPE
			SYNTAX EnableFlag
			MAX-ACCESS read-write
			STATUS current
			DESCRIPTION
				"disable(1), enable(2)"
			DEFVAL { enable }
			::= { sleEponAlarmControl 10 }

		
		-- 1.3.6.1.4.1.6296.101.20.6.2.11
		sleEponAlarmControlTooManyOnuRegistration OBJECT-TYPE
			SYNTAX EnableFlag
			MAX-ACCESS read-write
			STATUS current
			DESCRIPTION
				"disable(1), enable(2)"
			DEFVAL { enable }
			::= { sleEponAlarmControl 11 }

		
		-- 1.3.6.1.4.1.6296.101.20.6.2.12
		sleEponAlarmControlOpticSignalError OBJECT-TYPE
			SYNTAX EnableFlag
			MAX-ACCESS read-write
			STATUS current
			DESCRIPTION
				"disable(1), enable(2)"
			DEFVAL { enable }
			::= { sleEponAlarmControl 12 }

		
		-- 1.3.6.1.4.1.6296.101.20.6.2.13
		sleEponAlarmControlStandardLinkFault OBJECT-TYPE
			SYNTAX EnableFlag
			MAX-ACCESS read-write
			STATUS current
			DESCRIPTION
				"disable(1), enable(2)"
			DEFVAL { enable }
			::= { sleEponAlarmControl 13 }

		
		-- 1.3.6.1.4.1.6296.101.20.6.2.14
		sleEponAlarmControlLossOfSignal OBJECT-TYPE
			SYNTAX EnableFlag
			MAX-ACCESS read-write
			STATUS current
			DESCRIPTION
				"disable(1), enable(2)"
			DEFVAL { enable }
			::= { sleEponAlarmControl 14 }

		
		-- 1.3.6.1.4.1.6296.101.20.6.2.15
		sleEponAlarmControlTransmitFail OBJECT-TYPE
			SYNTAX EnableFlag
			MAX-ACCESS read-write
			STATUS current
			DESCRIPTION
				"disable(1), enable(2)"
			DEFVAL { enable }
			::= { sleEponAlarmControl 15 }

		
		-- 1.3.6.1.4.1.6296.101.20.6.2.16
		sleEponAlarmControlMacLearningOverflow OBJECT-TYPE
			SYNTAX EnableFlag
			MAX-ACCESS read-write
			STATUS current
			DESCRIPTION
				"disable(1), enable(2)"
			DEFVAL { enable }
			::= { sleEponAlarmControl 16 }

		
		-- 1.3.6.1.4.1.6296.101.20.6.2.17
		sleEponAlarmControlLoopback OBJECT-TYPE
			SYNTAX EnableFlag
			MAX-ACCESS read-write
			STATUS current
			DESCRIPTION
				"disable(1), enable(2)"
			DEFVAL { enable }
			::= { sleEponAlarmControl 17 }

		
		-- 1.3.6.1.4.1.6296.101.20.6.2.18
		sleEponAlarmControlStandardDyingGasp OBJECT-TYPE
			SYNTAX EnableFlag
			MAX-ACCESS read-write
			STATUS current
			DESCRIPTION
				"disable(1), enable(2)"
			DEFVAL { enable }
			::= { sleEponAlarmControl 18 }

		
		-- 1.3.6.1.4.1.6296.101.20.6.2.19
		sleEponAlarmControlExternalDyingGasp OBJECT-TYPE
			SYNTAX EnableFlag
			MAX-ACCESS read-write
			STATUS current
			DESCRIPTION
				"disable(1), enable(2)"
			DEFVAL { enable }
			::= { sleEponAlarmControl 19 }

		
		-- 1.3.6.1.4.1.6296.101.20.6.2.20
		sleEponAlarmControlStandardCriticalevent OBJECT-TYPE
			SYNTAX EnableFlag
			MAX-ACCESS read-write
			STATUS current
			DESCRIPTION
				"disable(1), enable(2)"
			DEFVAL { enable }
			::= { sleEponAlarmControl 20 }

		
		-- 1.3.6.1.4.1.6296.101.20.6.2.21
		sleEponAlarmControlExternalCriticalEvent OBJECT-TYPE
			SYNTAX EnableFlag
			MAX-ACCESS read-write
			STATUS current
			DESCRIPTION
				"disable(1), enable(2)"
			DEFVAL { enable }
			::= { sleEponAlarmControl 21 }

		
		-- 1.3.6.1.4.1.6296.101.20.6.2.22
		sleEponAlarmControlEponStandbyLos OBJECT-TYPE
			SYNTAX EnableFlag
			MAX-ACCESS read-write
			STATUS current
			DESCRIPTION
				"disable(1), enable(2)"
			DEFVAL { enable }
			::= { sleEponAlarmControl 22 }

		
		-- 1.3.6.1.4.1.6296.101.20.6.3
		sleEponAlarmNotification OBJECT IDENTIFIER ::= { sleEponAlarm 3 }

		
		-- 1.3.6.1.4.1.6296.101.20.6.3.1
		sleEponAlarmProfileChanged NOTIFICATION-TYPE
			OBJECTS { sleEponAlarmControlRequest, sleEponAlarmControlTimeStamp, sleEponAlarmControlReqResult, sleEponAlarmControlOltIndex }
			STATUS current
			DESCRIPTION 
				"alarm profile changed trap"
			::= { sleEponAlarmNotification 1 }

		
		-- 1.3.6.1.4.1.6296.101.20.6.3.2
		sleEponAlarmChanged NOTIFICATION-TYPE
			OBJECTS { sleEponAlarmControlRequest, sleEponAlarmControlTimeStamp, sleEponAlarmControlReqResult }
			STATUS current
			DESCRIPTION 
				"alarm changed trap"
			::= { sleEponAlarmNotification 2 }

		
		-- 1.3.6.1.4.1.6296.101.20.7
		sleEponStatistics OBJECT IDENTIFIER ::= { sleEpon 7 }

		
		-- 1.3.6.1.4.1.6296.101.20.7.1
		sleEponOltStatistics OBJECT IDENTIFIER ::= { sleEponStatistics 1 }

		
		-- 1.3.6.1.4.1.6296.101.20.7.1.1
		sleEponStatsOltTable OBJECT-TYPE
			SYNTAX SEQUENCE OF SleEponStatsOltEntry
			MAX-ACCESS not-accessible
			STATUS current
			DESCRIPTION
				"Description."
			::= { sleEponOltStatistics 1 }

		
		-- 1.3.6.1.4.1.6296.101.20.7.1.1.1
		sleEponStatsOltEntry OBJECT-TYPE
			SYNTAX SleEponStatsOltEntry
			MAX-ACCESS not-accessible
			STATUS current
			DESCRIPTION
				"Description."
			INDEX { sleEponOltIndex }
			::= { sleEponStatsOltTable 1 }

		
		SleEponStatsOltEntry ::=
			SEQUENCE { 
				sleEponStatsOltInOctets
					Counter64,
				sleEponStatsOltInPkts
					Counter32,
				sleEponStatsOltInPause
					Counter32,
				sleEponStatsOltInErroredFrame
					Counter32,
				sleEponStatsOltInUnicastPkts
					Counter32,
				sleEponstatsOltInBroadcastPkts
					Counter32,
				sleEponStatsOltInMulticastPkts
					Counter32,
				sleEponStatsOltOutOctets
					Counter64,
				sleEponStatsOltOutPkts
					Counter32,
				sleEponStatsOltOutPause
					Counter32,
				sleEponStatsOltOutDropped
					Counter32,
				sleEponStatsOltOutUnicastPkts
					Counter32,
				sleEponstatsOltOutBroadcastPkts
					Counter32,
				sleEponStatsOltOutMulticastPkts
					Counter32,
				sleEponStatsOltHostFrame
					Counter32,
				sleEponStatsOltInTooLongFrame
					Counter32,
				sleEponStatsOltHostFrameDropped
					Counter32
			 }

		-- 1.3.6.1.4.1.6296.101.20.7.1.1.1.1
		sleEponStatsOltInOctets OBJECT-TYPE
			SYNTAX Counter64
			MAX-ACCESS read-only
			STATUS current
			DESCRIPTION
				"The total number of octets received on the switch side"
			::= { sleEponStatsOltEntry 1 }

		
		-- 1.3.6.1.4.1.6296.101.20.7.1.1.1.2
		sleEponStatsOltInPkts OBJECT-TYPE
			SYNTAX Counter32
			MAX-ACCESS read-only
			STATUS current
			DESCRIPTION
				"The total number of packets received on the switch side"
			::= { sleEponStatsOltEntry 2 }

		
		-- 1.3.6.1.4.1.6296.101.20.7.1.1.1.3
		sleEponStatsOltInPause OBJECT-TYPE
			SYNTAX Counter32
			MAX-ACCESS read-only
			STATUS current
			DESCRIPTION
				"The total number of paused packet received on the switch side"
			::= { sleEponStatsOltEntry 3 }

		
		-- 1.3.6.1.4.1.6296.101.20.7.1.1.1.4
		sleEponStatsOltInErroredFrame OBJECT-TYPE
			SYNTAX Counter32
			MAX-ACCESS read-only
			STATUS current
			DESCRIPTION
				"The total number of errored frame received on the switch side"
			::= { sleEponStatsOltEntry 4 }

		
		-- 1.3.6.1.4.1.6296.101.20.7.1.1.1.5
		sleEponStatsOltInUnicastPkts OBJECT-TYPE
			SYNTAX Counter32
			MAX-ACCESS read-only
			STATUS current
			DESCRIPTION
				"The total number of unicast packets received on the switch side"
			::= { sleEponStatsOltEntry 5 }

		
		-- 1.3.6.1.4.1.6296.101.20.7.1.1.1.6
		sleEponstatsOltInBroadcastPkts OBJECT-TYPE
			SYNTAX Counter32
			MAX-ACCESS read-only
			STATUS current
			DESCRIPTION
				"The total number of broadcast packets received on the switch side"
			::= { sleEponStatsOltEntry 6 }

		
		-- 1.3.6.1.4.1.6296.101.20.7.1.1.1.7
		sleEponStatsOltInMulticastPkts OBJECT-TYPE
			SYNTAX Counter32
			MAX-ACCESS read-only
			STATUS current
			DESCRIPTION
				"The total number of multicast packets received on the switch side"
			::= { sleEponStatsOltEntry 7 }

		
		-- 1.3.6.1.4.1.6296.101.20.7.1.1.1.8
		sleEponStatsOltOutOctets OBJECT-TYPE
			SYNTAX Counter64
			MAX-ACCESS read-only
			STATUS current
			DESCRIPTION
				"The total number of octets transmitted out of the switch side"
			::= { sleEponStatsOltEntry 8 }

		
		-- 1.3.6.1.4.1.6296.101.20.7.1.1.1.9
		sleEponStatsOltOutPkts OBJECT-TYPE
			SYNTAX Counter32
			MAX-ACCESS read-only
			STATUS current
			DESCRIPTION
				"The total number of packets transmitted out of the switch side"
			::= { sleEponStatsOltEntry 9 }

		
		-- 1.3.6.1.4.1.6296.101.20.7.1.1.1.10
		sleEponStatsOltOutPause OBJECT-TYPE
			SYNTAX Counter32
			MAX-ACCESS read-only
			STATUS current
			DESCRIPTION
				"The total number of paused packets transmitted out of the switch side"
			::= { sleEponStatsOltEntry 10 }

		
		-- 1.3.6.1.4.1.6296.101.20.7.1.1.1.11
		sleEponStatsOltOutDropped OBJECT-TYPE
			SYNTAX Counter32
			MAX-ACCESS read-only
			STATUS current
			DESCRIPTION
				"The total number of droped packets transmitted out of the switch side"
			::= { sleEponStatsOltEntry 11 }

		
		-- 1.3.6.1.4.1.6296.101.20.7.1.1.1.12
		sleEponStatsOltOutUnicastPkts OBJECT-TYPE
			SYNTAX Counter32
			MAX-ACCESS read-only
			STATUS current
			DESCRIPTION
				"The total number of unicast packets transmitted out of the switch side"
			::= { sleEponStatsOltEntry 12 }

		
		-- 1.3.6.1.4.1.6296.101.20.7.1.1.1.13
		sleEponstatsOltOutBroadcastPkts OBJECT-TYPE
			SYNTAX Counter32
			MAX-ACCESS read-only
			STATUS current
			DESCRIPTION
				"The total number of broadcast packets transmitted out of the switch side"
			::= { sleEponStatsOltEntry 13 }

		
		-- 1.3.6.1.4.1.6296.101.20.7.1.1.1.14
		sleEponStatsOltOutMulticastPkts OBJECT-TYPE
			SYNTAX Counter32
			MAX-ACCESS read-only
			STATUS current
			DESCRIPTION
				"The total number of multicast packets transmitted out of the switch side"
			::= { sleEponStatsOltEntry 14 }

		
		-- 1.3.6.1.4.1.6296.101.20.7.1.1.1.15
		sleEponStatsOltHostFrame OBJECT-TYPE
			SYNTAX Counter32
			MAX-ACCESS read-only
			STATUS current
			DESCRIPTION
				"The total number of host frame received on the switch side."
			::= { sleEponStatsOltEntry 15 }

		
		-- 1.3.6.1.4.1.6296.101.20.7.1.1.1.16
		sleEponStatsOltInTooLongFrame OBJECT-TYPE
			SYNTAX Counter32
			MAX-ACCESS read-only
			STATUS current
			DESCRIPTION
				"The total number of too long frame received on the switch side."
			::= { sleEponStatsOltEntry 16 }

		
		-- 1.3.6.1.4.1.6296.101.20.7.1.1.1.17
		sleEponStatsOltHostFrameDropped OBJECT-TYPE
			SYNTAX Counter32
			MAX-ACCESS read-write
			STATUS current
			DESCRIPTION
				"The total number of droped frame transmitted out of the switch side."
			::= { sleEponStatsOltEntry 17 }

		
		-- 1.3.6.1.4.1.6296.101.20.7.1.2
		sleEponStatsOltPonTable OBJECT-TYPE
			SYNTAX SEQUENCE OF SleEponStatsOltPonEntry
			MAX-ACCESS not-accessible
			STATUS current
			DESCRIPTION
				"Description."
			::= { sleEponOltStatistics 2 }

		
		-- 1.3.6.1.4.1.6296.101.20.7.1.2.1
		sleEponStatsOltPonEntry OBJECT-TYPE
			SYNTAX SleEponStatsOltPonEntry
			MAX-ACCESS not-accessible
			STATUS current
			DESCRIPTION
				"Description."
			INDEX { sleEponOltIndex }
			::= { sleEponStatsOltPonTable 1 }

		
		SleEponStatsOltPonEntry ::=
			SEQUENCE { 
				sleEponStatsOltPonInOctets
					Counter64,
				sleEponStatsOltPonInPkts
					Counter32,
				sleEponStatsOltPonInPause
					Counter32,
				sleEponStatsOltPonInErroredFrame
					Counter32,
				sleEponStatsOltPonInUnicastPkts
					Counter32,
				sleEponstatsOltPonInBroadcastPkts
					Counter32,
				sleEponStatsOltPonInMulticastPkts
					Counter32,
				sleEponStatsOltPonOutOctets
					Counter64,
				sleEponStatsOltPonOutPkts
					Counter32,
				sleEponStatsOltPonOutPause
					Counter32,
				sleEponStatsOltPonOutDropped
					Counter32,
				sleEponStatsOltPonOutUnicastPkts
					Counter32,
				sleEponstatsOltPonOutBroadcastPkts
					Counter32,
				sleEponStatsOltPonOutMulticastPkts
					Counter32,
				sleEponStatsOltPonInHostFrame
					Counter32,
				sleEponStatsOltPonInTooLongFrame
					Counter32,
				sleEponStatsOltPonInHostFrameDropped
					Counter32,
				sleEponStatsOltPonInHECErrorFrame
					Counter32
			 }

		-- 1.3.6.1.4.1.6296.101.20.7.1.2.1.1
		sleEponStatsOltPonInOctets OBJECT-TYPE
			SYNTAX Counter64
			MAX-ACCESS read-only
			STATUS current
			DESCRIPTION
				"The total number of octets received on the OLT side"
			::= { sleEponStatsOltPonEntry 1 }

		
		-- 1.3.6.1.4.1.6296.101.20.7.1.2.1.2
		sleEponStatsOltPonInPkts OBJECT-TYPE
			SYNTAX Counter32
			MAX-ACCESS read-only
			STATUS current
			DESCRIPTION
				"The total number of packets received on the OLT side"
			::= { sleEponStatsOltPonEntry 2 }

		
		-- 1.3.6.1.4.1.6296.101.20.7.1.2.1.3
		sleEponStatsOltPonInPause OBJECT-TYPE
			SYNTAX Counter32
			MAX-ACCESS read-only
			STATUS current
			DESCRIPTION
				"The total number of paused packet received on the OLT side"
			::= { sleEponStatsOltPonEntry 3 }

		
		-- 1.3.6.1.4.1.6296.101.20.7.1.2.1.4
		sleEponStatsOltPonInErroredFrame OBJECT-TYPE
			SYNTAX Counter32
			MAX-ACCESS read-only
			STATUS current
			DESCRIPTION
				"The total number of errored frame received on the OLT side"
			::= { sleEponStatsOltPonEntry 4 }

		
		-- 1.3.6.1.4.1.6296.101.20.7.1.2.1.5
		sleEponStatsOltPonInUnicastPkts OBJECT-TYPE
			SYNTAX Counter32
			MAX-ACCESS read-only
			STATUS current
			DESCRIPTION
				"The total number of unicast packets received on the OLT side"
			::= { sleEponStatsOltPonEntry 5 }

		
		-- 1.3.6.1.4.1.6296.101.20.7.1.2.1.6
		sleEponstatsOltPonInBroadcastPkts OBJECT-TYPE
			SYNTAX Counter32
			MAX-ACCESS read-only
			STATUS current
			DESCRIPTION
				"The total number of broadcast packets received on the OLT side"
			::= { sleEponStatsOltPonEntry 6 }

		
		-- 1.3.6.1.4.1.6296.101.20.7.1.2.1.7
		sleEponStatsOltPonInMulticastPkts OBJECT-TYPE
			SYNTAX Counter32
			MAX-ACCESS read-only
			STATUS current
			DESCRIPTION
				"The total number of multicast packets received on the OLT side"
			::= { sleEponStatsOltPonEntry 7 }

		
		-- 1.3.6.1.4.1.6296.101.20.7.1.2.1.8
		sleEponStatsOltPonOutOctets OBJECT-TYPE
			SYNTAX Counter64
			MAX-ACCESS read-only
			STATUS current
			DESCRIPTION
				"The total number of octets transmitted out of the OLT side"
			::= { sleEponStatsOltPonEntry 8 }

		
		-- 1.3.6.1.4.1.6296.101.20.7.1.2.1.9
		sleEponStatsOltPonOutPkts OBJECT-TYPE
			SYNTAX Counter32
			MAX-ACCESS read-only
			STATUS current
			DESCRIPTION
				"The total number of packets transmitted out of the OLT side"
			::= { sleEponStatsOltPonEntry 9 }

		
		-- 1.3.6.1.4.1.6296.101.20.7.1.2.1.10
		sleEponStatsOltPonOutPause OBJECT-TYPE
			SYNTAX Counter32
			MAX-ACCESS read-only
			STATUS current
			DESCRIPTION
				"The total number of paused packets transmitted out of the OLT side"
			::= { sleEponStatsOltPonEntry 10 }

		
		-- 1.3.6.1.4.1.6296.101.20.7.1.2.1.11
		sleEponStatsOltPonOutDropped OBJECT-TYPE
			SYNTAX Counter32
			MAX-ACCESS read-only
			STATUS current
			DESCRIPTION
				"The total number of droped packets transmitted out of the OLT side"
			::= { sleEponStatsOltPonEntry 11 }

		
		-- 1.3.6.1.4.1.6296.101.20.7.1.2.1.12
		sleEponStatsOltPonOutUnicastPkts OBJECT-TYPE
			SYNTAX Counter32
			MAX-ACCESS read-only
			STATUS current
			DESCRIPTION
				"The total number of unicast packets transmitted out of the OLT side"
			::= { sleEponStatsOltPonEntry 12 }

		
		-- 1.3.6.1.4.1.6296.101.20.7.1.2.1.13
		sleEponstatsOltPonOutBroadcastPkts OBJECT-TYPE
			SYNTAX Counter32
			MAX-ACCESS read-only
			STATUS current
			DESCRIPTION
				"The total number of broadcast packets transmitted out of the OLT side"
			::= { sleEponStatsOltPonEntry 13 }

		
		-- 1.3.6.1.4.1.6296.101.20.7.1.2.1.14
		sleEponStatsOltPonOutMulticastPkts OBJECT-TYPE
			SYNTAX Counter32
			MAX-ACCESS read-only
			STATUS current
			DESCRIPTION
				"The total number of multicast packets transmitted out of the OLT side"
			::= { sleEponStatsOltPonEntry 14 }

		
		-- 1.3.6.1.4.1.6296.101.20.7.1.2.1.15
		sleEponStatsOltPonInHostFrame OBJECT-TYPE
			SYNTAX Counter32
			MAX-ACCESS read-only
			STATUS current
			DESCRIPTION
				"The total number of frame received on the OLT side."
			::= { sleEponStatsOltPonEntry 15 }

		
		-- 1.3.6.1.4.1.6296.101.20.7.1.2.1.16
		sleEponStatsOltPonInTooLongFrame OBJECT-TYPE
			SYNTAX Counter32
			MAX-ACCESS read-only
			STATUS current
			DESCRIPTION
				"The total number of long frame received on the OLT side."
			::= { sleEponStatsOltPonEntry 16 }

		
		-- 1.3.6.1.4.1.6296.101.20.7.1.2.1.17
		sleEponStatsOltPonInHostFrameDropped OBJECT-TYPE
			SYNTAX Counter32
			MAX-ACCESS read-only
			STATUS current
			DESCRIPTION
				"The total number of droped frame received on the OLT side."
			::= { sleEponStatsOltPonEntry 17 }

		
		-- 1.3.6.1.4.1.6296.101.20.7.1.2.1.18
		sleEponStatsOltPonInHECErrorFrame OBJECT-TYPE
			SYNTAX Counter32
			MAX-ACCESS read-only
			STATUS current
			DESCRIPTION
				"The total number of HEC error frame received on the OLT side."
			::= { sleEponStatsOltPonEntry 18 }

		
		-- 1.3.6.1.4.1.6296.101.20.7.1.3
		sleEponStatsOltChannelTable OBJECT-TYPE
			SYNTAX SEQUENCE OF SleEponStatsOltChannelEntry
			MAX-ACCESS not-accessible
			STATUS current
			DESCRIPTION
				"Description."
			::= { sleEponOltStatistics 3 }

		
		-- 1.3.6.1.4.1.6296.101.20.7.1.3.1
		sleEponStatsOltChannelEntry OBJECT-TYPE
			SYNTAX SleEponStatsOltChannelEntry
			MAX-ACCESS not-accessible
			STATUS current
			DESCRIPTION
				"Description."
			INDEX { sleEponOltIndex, sleEponOnuIndex }
			::= { sleEponStatsOltChannelTable 1 }

		
		SleEponStatsOltChannelEntry ::=
			SEQUENCE { 
				sleEponStatsOltChannelInOctets
					Counter64,
				sleEponStatsOltChannelInDataOctets
					Counter64,
				sleEponStatsOltChannelInPkts
					Counter32,
				sleEponStatsOltChannelInMulticastPkts
					Counter32,
				sleEponStatsOltChannelInBroadcastPkts
					Counter32,
				sleEponStatsOltChannelInErrorOctets
					Counter32,
				sleEponStatsOltChannelInErrorPkts
					Counter32,
				sleEponStatsOltChannelOutOctets
					Counter64,
				sleEponStatsOltChannelOutPkts
					Counter32,
				sleEponStatsOltChannelOutPolicerDroppedPkts
					Counter32,
				sleEponStatsOltChannelOutMismatchDroppedPkts
					Counter32,
				sleEponStatsOltChannelOutMulticastPkts
					Counter32,
				sleEponStatsOltChannelOutBroadcastPkts
					Counter32,
				sleEponStatsOltChannelFCS
					Counter32,
				sleEponStatsOltChannelInRangeLengthErrors
					Counter32,
				sleEponStatsOltChannelFrameTooLongErrors
					Counter32,
				sleEponStatsOltChannelInUnicastPkts
					Counter32,
				sleEponStatsOltChannelOutUnicastPkts
					Counter32
			 }

		-- 1.3.6.1.4.1.6296.101.20.7.1.3.1.1
		sleEponStatsOltChannelInOctets OBJECT-TYPE
			SYNTAX Counter64
			MAX-ACCESS read-only
			STATUS current
			DESCRIPTION
				"The total number of octets received on the ONU side"
			::= { sleEponStatsOltChannelEntry 1 }

		
		-- 1.3.6.1.4.1.6296.101.20.7.1.3.1.2
		sleEponStatsOltChannelInDataOctets OBJECT-TYPE
			SYNTAX Counter64
			MAX-ACCESS read-only
			STATUS current
			DESCRIPTION
				"The total number of  data octets received on the ONU side"
			::= { sleEponStatsOltChannelEntry 2 }

		
		-- 1.3.6.1.4.1.6296.101.20.7.1.3.1.3
		sleEponStatsOltChannelInPkts OBJECT-TYPE
			SYNTAX Counter32
			MAX-ACCESS read-only
			STATUS current
			DESCRIPTION
				"The total number of packets transmitted out of the ONU side"
			::= { sleEponStatsOltChannelEntry 3 }

		
		-- 1.3.6.1.4.1.6296.101.20.7.1.3.1.4
		sleEponStatsOltChannelInMulticastPkts OBJECT-TYPE
			SYNTAX Counter32
			MAX-ACCESS read-only
			STATUS current
			DESCRIPTION
				"The total number of multicast packets received on the ONU side"
			::= { sleEponStatsOltChannelEntry 4 }

		
		-- 1.3.6.1.4.1.6296.101.20.7.1.3.1.5
		sleEponStatsOltChannelInBroadcastPkts OBJECT-TYPE
			SYNTAX Counter32
			MAX-ACCESS read-only
			STATUS current
			DESCRIPTION
				"The total number of broadcast packets received on the ONU side"
			::= { sleEponStatsOltChannelEntry 5 }

		
		-- 1.3.6.1.4.1.6296.101.20.7.1.3.1.6
		sleEponStatsOltChannelInErrorOctets OBJECT-TYPE
			SYNTAX Counter32
			MAX-ACCESS read-only
			STATUS current
			DESCRIPTION
				"The total number of errored octets received on the ONU side"
			::= { sleEponStatsOltChannelEntry 6 }

		
		-- 1.3.6.1.4.1.6296.101.20.7.1.3.1.7
		sleEponStatsOltChannelInErrorPkts OBJECT-TYPE
			SYNTAX Counter32
			MAX-ACCESS read-only
			STATUS current
			DESCRIPTION
				"The total number of errored packets received on the ONU side"
			::= { sleEponStatsOltChannelEntry 7 }

		
		-- 1.3.6.1.4.1.6296.101.20.7.1.3.1.8
		sleEponStatsOltChannelOutOctets OBJECT-TYPE
			SYNTAX Counter64
			MAX-ACCESS read-only
			STATUS current
			DESCRIPTION
				"The total number of octets transmitted out of the ONU side"
			::= { sleEponStatsOltChannelEntry 8 }

		
		-- 1.3.6.1.4.1.6296.101.20.7.1.3.1.9
		sleEponStatsOltChannelOutPkts OBJECT-TYPE
			SYNTAX Counter32
			MAX-ACCESS read-only
			STATUS current
			DESCRIPTION
				"The total number of packets transmitted out of the ONU side"
			::= { sleEponStatsOltChannelEntry 9 }

		
		-- 1.3.6.1.4.1.6296.101.20.7.1.3.1.10
		sleEponStatsOltChannelOutPolicerDroppedPkts OBJECT-TYPE
			SYNTAX Counter32
			MAX-ACCESS read-only
			STATUS current
			DESCRIPTION
				"The total number of policer dropped transmitted out of the ONU side"
			::= { sleEponStatsOltChannelEntry 10 }

		
		-- 1.3.6.1.4.1.6296.101.20.7.1.3.1.11
		sleEponStatsOltChannelOutMismatchDroppedPkts OBJECT-TYPE
			SYNTAX Counter32
			MAX-ACCESS read-only
			STATUS current
			DESCRIPTION
				"The total number of mismatch dropped packets transmitted out of the ONU side"
			::= { sleEponStatsOltChannelEntry 11 }

		
		-- 1.3.6.1.4.1.6296.101.20.7.1.3.1.12
		sleEponStatsOltChannelOutMulticastPkts OBJECT-TYPE
			SYNTAX Counter32
			MAX-ACCESS read-only
			STATUS current
			DESCRIPTION
				"The total number of multicast packets transmitted out of the ONU side"
			::= { sleEponStatsOltChannelEntry 12 }

		
		-- 1.3.6.1.4.1.6296.101.20.7.1.3.1.13
		sleEponStatsOltChannelOutBroadcastPkts OBJECT-TYPE
			SYNTAX Counter32
			MAX-ACCESS read-only
			STATUS current
			DESCRIPTION
				"The total number of broadcast packets transmitted out of the ONU side"
			::= { sleEponStatsOltChannelEntry 13 }

		
		-- 1.3.6.1.4.1.6296.101.20.7.1.3.1.14
		sleEponStatsOltChannelFCS OBJECT-TYPE
			SYNTAX Counter32
			MAX-ACCESS read-only
			STATUS current
			DESCRIPTION
				"The total number of FCS transmitted out of the ONU side"
			::= { sleEponStatsOltChannelEntry 14 }

		
		-- 1.3.6.1.4.1.6296.101.20.7.1.3.1.15
		sleEponStatsOltChannelInRangeLengthErrors OBJECT-TYPE
			SYNTAX Counter32
			MAX-ACCESS read-only
			STATUS current
			DESCRIPTION
				"The total number of range length errors received on th ONU side"
			::= { sleEponStatsOltChannelEntry 15 }

		
		-- 1.3.6.1.4.1.6296.101.20.7.1.3.1.16
		sleEponStatsOltChannelFrameTooLongErrors OBJECT-TYPE
			SYNTAX Counter32
			MAX-ACCESS read-only
			STATUS current
			DESCRIPTION
				"The total number of frame to long errors on the ONU side"
			::= { sleEponStatsOltChannelEntry 16 }

		
		-- 1.3.6.1.4.1.6296.101.20.7.1.3.1.17
		sleEponStatsOltChannelInUnicastPkts OBJECT-TYPE
			SYNTAX Counter32
			MAX-ACCESS read-only
			STATUS current
			DESCRIPTION
				"The total number of unicast packets received on the ONU side"
			::= { sleEponStatsOltChannelEntry 17 }

		
		-- 1.3.6.1.4.1.6296.101.20.7.1.3.1.18
		sleEponStatsOltChannelOutUnicastPkts OBJECT-TYPE
			SYNTAX Counter32
			MAX-ACCESS read-only
			STATUS current
			DESCRIPTION
				"The total number of unicast packets transmitted out of the ONU side"
			::= { sleEponStatsOltChannelEntry 18 }

		
		-- 1.3.6.1.4.1.6296.101.20.7.1.4
		sleEponStatsOltControl OBJECT IDENTIFIER ::= { sleEponOltStatistics 4 }

		
		-- 1.3.6.1.4.1.6296.101.20.7.1.4.1
		sleEponStatsOltControlRequest OBJECT-TYPE
			SYNTAX INTEGER
				{
				clearEponStatsOlt(1),
				clearEponStatsOltChannel(2),
				clearEponStatsAll(3)
				}
			MAX-ACCESS read-write
			STATUS current
			DESCRIPTION
				"The request of a user command"
			::= { sleEponStatsOltControl 1 }

		
		-- 1.3.6.1.4.1.6296.101.20.7.1.4.2
		sleEponStatsOltControlStatus OBJECT-TYPE
			SYNTAX SleControlStatusType
			MAX-ACCESS read-only
			STATUS current
			DESCRIPTION
				"The status of user command"
			::= { sleEponStatsOltControl 2 }

		
		-- 1.3.6.1.4.1.6296.101.20.7.1.4.3
		sleEponStatsOltControlTimer OBJECT-TYPE
			SYNTAX Gauge32
			MAX-ACCESS read-write
			STATUS current
			DESCRIPTION
				"The maximum time for the manager for a long running user command"
			::= { sleEponStatsOltControl 3 }

		
		-- 1.3.6.1.4.1.6296.101.20.7.1.4.4
		sleEponStatsOltControlTimeStamp OBJECT-TYPE
			SYNTAX TimeTicks
			MAX-ACCESS read-only
			STATUS current
			DESCRIPTION
				"The time stamp of the last command(end of command)"
			::= { sleEponStatsOltControl 4 }

		
		-- 1.3.6.1.4.1.6296.101.20.7.1.4.5
		sleEponStatsOltControlReqResult OBJECT-TYPE
			SYNTAX SleControlRequestResultType
			MAX-ACCESS read-only
			STATUS current
			DESCRIPTION
				"The result of the last user command"
			::= { sleEponStatsOltControl 5 }

		
		-- 1.3.6.1.4.1.6296.101.20.7.1.4.6
		sleEponStatsOltControlOltIndex OBJECT-TYPE
			SYNTAX INTEGER (1..512)
			MAX-ACCESS read-write
			STATUS current
			DESCRIPTION
				"OLT index"
			::= { sleEponStatsOltControl 6 }

		
		-- 1.3.6.1.4.1.6296.101.20.7.1.4.7
		sleEponStatsOltControlChannelIndex OBJECT-TYPE
			SYNTAX INTEGER (1..32)
			MAX-ACCESS read-write
			STATUS current
			DESCRIPTION
				"ONU index"
			::= { sleEponStatsOltControl 7 }

		
		-- 1.3.6.1.4.1.6296.101.20.7.1.5
		sleEponStatsOltNotification OBJECT IDENTIFIER ::= { sleEponOltStatistics 5 }

		
		-- 1.3.6.1.4.1.6296.101.20.7.1.5.1
		sleEponstatsOltCleared NOTIFICATION-TYPE
			OBJECTS { sleEponStatsOltControlRequest, sleEponStatsOltControlTimeStamp, sleEponStatsOltControlReqResult, sleEponStatsOltControlOltIndex }
			STATUS current
			DESCRIPTION 
				"Description."
			::= { sleEponStatsOltNotification 1 }

		
		-- 1.3.6.1.4.1.6296.101.20.7.1.5.2
		sleEponStatsOltChannelCleared NOTIFICATION-TYPE
			OBJECTS { sleEponStatsOltControlRequest, sleEponStatsOltControlTimeStamp, sleEponStatsOltControlReqResult, sleEponStatsOltControlOltIndex, sleEponStatsOltControlChannelIndex
				 }
			STATUS current
			DESCRIPTION 
				"Description."
			::= { sleEponStatsOltNotification 2 }

		
		-- 1.3.6.1.4.1.6296.101.20.7.1.5.3
		sleEponStatsAllCleared NOTIFICATION-TYPE
			OBJECTS { sleEponStatsOltControlRequest, sleEponStatsOltControlTimeStamp, sleEponStatsOltControlReqResult, sleEponStatsOltControlOltIndex, sleEponStatsOltControlChannelIndex
				 }
			STATUS current
			DESCRIPTION 
				"Description."
			::= { sleEponStatsOltNotification 3 }

		
		-- 1.3.6.1.4.1.6296.101.20.7.1.6
		sleEponStatsOltFromOnuTable OBJECT-TYPE
			SYNTAX SEQUENCE OF SleEponStatsOltFromOnuEntry
			MAX-ACCESS not-accessible
			STATUS current
			DESCRIPTION
				"Description."
			::= { sleEponOltStatistics 6 }

		
		-- 1.3.6.1.4.1.6296.101.20.7.1.6.1
		sleEponStatsOltFromOnuEntry OBJECT-TYPE
			SYNTAX SleEponStatsOltFromOnuEntry
			MAX-ACCESS not-accessible
			STATUS current
			DESCRIPTION
				"Olt statistics: from onu."
			INDEX { sleEponOltIndex }
			::= { sleEponStatsOltFromOnuTable 1 }

		
		SleEponStatsOltFromOnuEntry ::=
			SEQUENCE { 
				sleEponStatsOltFromOnuInFrame
					Counter32,
				sleEponStatsOltFromOnuInErrorFrame
					Counter32,
				sleEponStatsOltFromOnuInMulticastFrame
					Counter32,
				sleEponStatsOltFromOnuInBroadcastFrame
					Counter32,
				sleEponStatsOltFromOnuInReportFrame
					Counter32,
				sleEponStatsOltFromOnuInCheckSeqErrorFrame
					Counter32,
				sleEponStatsOltFromOnuInRangeLenErrors
					Counter32,
				sleEponStatsOltFromOnuInTooLongFrame
					Counter32,
				sleEponStatsOltFromOnuOutFrame
					Counter32,
				sleEponStatsOltFromOnuOutFrameBytes
					Counter64,
				sleEponStatsOltFromOnuOutMulticastFrame
					Counter32,
				sleEponStatsOltFromOnuOutBroadcastFrame
					Counter32,
				sleEponStatsOltFromOnuOutDBAGrantFrame
					Counter32,
				sleEponStatsOltFromOnuOutControlGrantFrame
					Counter32
			 }

		-- 1.3.6.1.4.1.6296.101.20.7.1.6.1.1
		sleEponStatsOltFromOnuInFrame OBJECT-TYPE
			SYNTAX Counter32
			MAX-ACCESS read-only
			STATUS current
			DESCRIPTION
				"The total number of Rx frame."
			::= { sleEponStatsOltFromOnuEntry 1 }

		
		-- 1.3.6.1.4.1.6296.101.20.7.1.6.1.2
		sleEponStatsOltFromOnuInErrorFrame OBJECT-TYPE
			SYNTAX Counter32
			MAX-ACCESS read-only
			STATUS current
			DESCRIPTION
				"Rx error frame count."
			::= { sleEponStatsOltFromOnuEntry 2 }

		
		-- 1.3.6.1.4.1.6296.101.20.7.1.6.1.3
		sleEponStatsOltFromOnuInMulticastFrame OBJECT-TYPE
			SYNTAX Counter32
			MAX-ACCESS read-only
			STATUS current
			DESCRIPTION
				"Rx multicast frame count."
			::= { sleEponStatsOltFromOnuEntry 3 }

		
		-- 1.3.6.1.4.1.6296.101.20.7.1.6.1.4
		sleEponStatsOltFromOnuInBroadcastFrame OBJECT-TYPE
			SYNTAX Counter32
			MAX-ACCESS read-only
			STATUS current
			DESCRIPTION
				"Rx broadcast frame count."
			::= { sleEponStatsOltFromOnuEntry 4 }

		
		-- 1.3.6.1.4.1.6296.101.20.7.1.6.1.5
		sleEponStatsOltFromOnuInReportFrame OBJECT-TYPE
			SYNTAX Counter32
			MAX-ACCESS read-only
			STATUS current
			DESCRIPTION
				"Rx report frame count."
			::= { sleEponStatsOltFromOnuEntry 5 }

		
		-- 1.3.6.1.4.1.6296.101.20.7.1.6.1.6
		sleEponStatsOltFromOnuInCheckSeqErrorFrame OBJECT-TYPE
			SYNTAX Counter32
			MAX-ACCESS read-only
			STATUS current
			DESCRIPTION
				"Rx check sequenece error frame count."
			::= { sleEponStatsOltFromOnuEntry 6 }

		
		-- 1.3.6.1.4.1.6296.101.20.7.1.6.1.7
		sleEponStatsOltFromOnuInRangeLenErrors OBJECT-TYPE
			SYNTAX Counter32
			MAX-ACCESS read-only
			STATUS current
			DESCRIPTION
				"Rx range of length error frame count."
			::= { sleEponStatsOltFromOnuEntry 7 }

		
		-- 1.3.6.1.4.1.6296.101.20.7.1.6.1.8
		sleEponStatsOltFromOnuInTooLongFrame OBJECT-TYPE
			SYNTAX Counter32
			MAX-ACCESS read-only
			STATUS current
			DESCRIPTION
				"Rx too long frame counts."
			::= { sleEponStatsOltFromOnuEntry 8 }

		
		-- 1.3.6.1.4.1.6296.101.20.7.1.6.1.9
		sleEponStatsOltFromOnuOutFrame OBJECT-TYPE
			SYNTAX Counter32
			MAX-ACCESS read-only
			STATUS current
			DESCRIPTION
				"Tx frame count."
			::= { sleEponStatsOltFromOnuEntry 9 }

		
		-- 1.3.6.1.4.1.6296.101.20.7.1.6.1.10
		sleEponStatsOltFromOnuOutFrameBytes OBJECT-TYPE
			SYNTAX Counter64
			MAX-ACCESS read-only
			STATUS current
			DESCRIPTION
				"Tx frame bytes."
			::= { sleEponStatsOltFromOnuEntry 10 }

		
		-- 1.3.6.1.4.1.6296.101.20.7.1.6.1.11
		sleEponStatsOltFromOnuOutMulticastFrame OBJECT-TYPE
			SYNTAX Counter32
			MAX-ACCESS read-only
			STATUS current
			DESCRIPTION
				"Tx multicast frame count."
			::= { sleEponStatsOltFromOnuEntry 11 }

		
		-- 1.3.6.1.4.1.6296.101.20.7.1.6.1.12
		sleEponStatsOltFromOnuOutBroadcastFrame OBJECT-TYPE
			SYNTAX Counter32
			MAX-ACCESS read-only
			STATUS current
			DESCRIPTION
				"Tx broadcast frame count."
			::= { sleEponStatsOltFromOnuEntry 12 }

		
		-- 1.3.6.1.4.1.6296.101.20.7.1.6.1.13
		sleEponStatsOltFromOnuOutDBAGrantFrame OBJECT-TYPE
			SYNTAX Counter32
			MAX-ACCESS read-only
			STATUS current
			DESCRIPTION
				"Tx grant DBA frame count."
			::= { sleEponStatsOltFromOnuEntry 13 }

		
		-- 1.3.6.1.4.1.6296.101.20.7.1.6.1.14
		sleEponStatsOltFromOnuOutControlGrantFrame OBJECT-TYPE
			SYNTAX Counter32
			MAX-ACCESS read-only
			STATUS current
			DESCRIPTION
				"Tx grant frame count."
			::= { sleEponStatsOltFromOnuEntry 14 }

		
		-- 1.3.6.1.4.1.6296.101.20.7.2
		sleEponOnuStatistics OBJECT IDENTIFIER ::= { sleEponStatistics 2 }

		
		-- 1.3.6.1.4.1.6296.101.20.7.2.1
		sleEponStatsOnuPortTable OBJECT-TYPE
			SYNTAX SEQUENCE OF SleEponStatsOnuPortEntry
			MAX-ACCESS not-accessible
			STATUS current
			DESCRIPTION
				"Description."
			::= { sleEponOnuStatistics 1 }

		
		-- 1.3.6.1.4.1.6296.101.20.7.2.1.1
		sleEponStatsOnuPortEntry OBJECT-TYPE
			SYNTAX SleEponStatsOnuPortEntry
			MAX-ACCESS not-accessible
			STATUS current
			DESCRIPTION
				"Description."
			INDEX { sleEponOltIndex, sleEponOnuIndex, sleEponOnuPortIndex }
			::= { sleEponStatsOnuPortTable 1 }

		
		SleEponStatsOnuPortEntry ::=
			SEQUENCE { 
				sleEponStatsOnuPortInOctets
					Counter64,
				sleEponStatsOnuPortInPkts
					Counter32,
				sleEponStatsOnuPortInUcastPkts
					Counter32,
				sleEponStatsOnuPortInBcastPkts
					Counter32,
				sleEponStatsOnuPortInMcastPkts
					Counter32,
				sleEponStatsOnuPortOutOctets
					Counter64,
				sleEponStatsOnuPortOutPkts
					Counter32,
				sleEponStatsOnuPortOutUcastPkts
					Counter32,
				sleEponStatsOnuPortOutBcastPkts
					Counter32,
				sleEponStatsOnuPortOutMcastPkts
					Counter32,
				sleEponStatsOnuPortInUndersize
					Counter32,
				sleEponStatsOnuPortInOversize
					Counter32,
				sleEponStatsOnuPortInJabber
					Counter32,
				sleEponStatsOnuPortInRxError
					Counter32,
				sleEponStatsOnuPortInRxFcsError
					Counter32
			 }

		-- 1.3.6.1.4.1.6296.101.20.7.2.1.1.1
		sleEponStatsOnuPortInOctets OBJECT-TYPE
			SYNTAX Counter64
			MAX-ACCESS read-only
			STATUS current
			DESCRIPTION
				"Description."
			::= { sleEponStatsOnuPortEntry 1 }

		
		-- 1.3.6.1.4.1.6296.101.20.7.2.1.1.2
		sleEponStatsOnuPortInPkts OBJECT-TYPE
			SYNTAX Counter32
			MAX-ACCESS read-only
			STATUS current
			DESCRIPTION
				"Description."
			::= { sleEponStatsOnuPortEntry 2 }

		
		-- 1.3.6.1.4.1.6296.101.20.7.2.1.1.3
		sleEponStatsOnuPortInUcastPkts OBJECT-TYPE
			SYNTAX Counter32
			MAX-ACCESS read-only
			STATUS current
			DESCRIPTION
				"Description."
			::= { sleEponStatsOnuPortEntry 3 }

		
		-- 1.3.6.1.4.1.6296.101.20.7.2.1.1.4
		sleEponStatsOnuPortInBcastPkts OBJECT-TYPE
			SYNTAX Counter32
			MAX-ACCESS read-only
			STATUS current
			DESCRIPTION
				"Description."
			::= { sleEponStatsOnuPortEntry 4 }

		
		-- 1.3.6.1.4.1.6296.101.20.7.2.1.1.5
		sleEponStatsOnuPortInMcastPkts OBJECT-TYPE
			SYNTAX Counter32
			MAX-ACCESS read-only
			STATUS current
			DESCRIPTION
				"Description."
			::= { sleEponStatsOnuPortEntry 5 }

		
		-- 1.3.6.1.4.1.6296.101.20.7.2.1.1.6
		sleEponStatsOnuPortOutOctets OBJECT-TYPE
			SYNTAX Counter64
			MAX-ACCESS read-only
			STATUS current
			DESCRIPTION
				"Description."
			::= { sleEponStatsOnuPortEntry 6 }

		
		-- 1.3.6.1.4.1.6296.101.20.7.2.1.1.7
		sleEponStatsOnuPortOutPkts OBJECT-TYPE
			SYNTAX Counter32
			MAX-ACCESS read-only
			STATUS current
			DESCRIPTION
				"Description."
			::= { sleEponStatsOnuPortEntry 7 }

		
		-- 1.3.6.1.4.1.6296.101.20.7.2.1.1.8
		sleEponStatsOnuPortOutUcastPkts OBJECT-TYPE
			SYNTAX Counter32
			MAX-ACCESS read-only
			STATUS current
			DESCRIPTION
				"Description."
			::= { sleEponStatsOnuPortEntry 8 }

		
		-- 1.3.6.1.4.1.6296.101.20.7.2.1.1.9
		sleEponStatsOnuPortOutBcastPkts OBJECT-TYPE
			SYNTAX Counter32
			MAX-ACCESS read-only
			STATUS current
			DESCRIPTION
				"Description."
			::= { sleEponStatsOnuPortEntry 9 }

		
		-- 1.3.6.1.4.1.6296.101.20.7.2.1.1.10
		sleEponStatsOnuPortOutMcastPkts OBJECT-TYPE
			SYNTAX Counter32
			MAX-ACCESS read-only
			STATUS current
			DESCRIPTION
				"Description."
			::= { sleEponStatsOnuPortEntry 10 }

		
		-- 1.3.6.1.4.1.6296.101.20.7.2.1.1.11
		sleEponStatsOnuPortInUndersize OBJECT-TYPE
			SYNTAX Counter32
			MAX-ACCESS read-only
			STATUS current
			DESCRIPTION
				"Description."
			::= { sleEponStatsOnuPortEntry 11 }

		
		-- 1.3.6.1.4.1.6296.101.20.7.2.1.1.12
		sleEponStatsOnuPortInOversize OBJECT-TYPE
			SYNTAX Counter32
			MAX-ACCESS read-only
			STATUS current
			DESCRIPTION
				"Description."
			::= { sleEponStatsOnuPortEntry 12 }

		
		-- 1.3.6.1.4.1.6296.101.20.7.2.1.1.13
		sleEponStatsOnuPortInJabber OBJECT-TYPE
			SYNTAX Counter32
			MAX-ACCESS read-only
			STATUS current
			DESCRIPTION
				"Description."
			::= { sleEponStatsOnuPortEntry 13 }

		
		-- 1.3.6.1.4.1.6296.101.20.7.2.1.1.14
		sleEponStatsOnuPortInRxError OBJECT-TYPE
			SYNTAX Counter32
			MAX-ACCESS read-only
			STATUS current
			DESCRIPTION
				"Description."
			::= { sleEponStatsOnuPortEntry 14 }

		
		-- 1.3.6.1.4.1.6296.101.20.7.2.1.1.15
		sleEponStatsOnuPortInRxFcsError OBJECT-TYPE
			SYNTAX Counter32
			MAX-ACCESS read-only
			STATUS current
			DESCRIPTION
				"Description."
			::= { sleEponStatsOnuPortEntry 15 }

		
		-- 1.3.6.1.4.1.6296.101.20.7.2.2
		sleEponStatsOnuUniTable OBJECT-TYPE
			SYNTAX SEQUENCE OF SleEponStatsOnuUniEntry
			MAX-ACCESS not-accessible
			STATUS current
			DESCRIPTION
				"Description."
			::= { sleEponOnuStatistics 2 }

		
		-- 1.3.6.1.4.1.6296.101.20.7.2.2.1
		sleEponStatsOnuUniEntry OBJECT-TYPE
			SYNTAX SleEponStatsOnuUniEntry
			MAX-ACCESS not-accessible
			STATUS current
			DESCRIPTION
				"Description."
			INDEX { sleEponOltIndex, sleEponOnuIndex }
			::= { sleEponStatsOnuUniTable 1 }

		
		SleEponStatsOnuUniEntry ::=
			SEQUENCE { 
				sleEponStatsOnuUniInPkts
					Counter32,
				sleEponStatsOnuUniInBytes
					Counter64,
				sleEponStatsOnuUniInErrPkts
					Counter32,
				sleEponStatsOnuUniInErrBytes
					Counter32,
				sleEponStatsOnuUniInPause
					Counter32,
				sleEponStatsOnuUniFrameLongError
					Counter32,
				sleEponStatsOnuUniOutPkts
					Counter32,
				sleEponStatsOnuUniOutBytes
					Counter64,
				sleEponStatsOnuUniOutPause
					Counter32,
				sleEponStatsOnuUniOutDropPkts
					Counter32,
				sleEponStatsOnuUnInMcastPkts
					Counter32,
				sleEponStatsOnuUnInBcastPkts
					Counter32,
				sleEponStatsOnuUniInDropPkts
					Counter32,
				sleEponStatsOnuUniOutMcastPkts
					Counter32,
				sleEponStatsOnuUniOutBcastPkts
					Counter32
			 }

		-- 1.3.6.1.4.1.6296.101.20.7.2.2.1.1
		sleEponStatsOnuUniInPkts OBJECT-TYPE
			SYNTAX Counter32
			MAX-ACCESS read-only
			STATUS current
			DESCRIPTION
				"Description."
			::= { sleEponStatsOnuUniEntry 1 }

		
		-- 1.3.6.1.4.1.6296.101.20.7.2.2.1.2
		sleEponStatsOnuUniInBytes OBJECT-TYPE
			SYNTAX Counter64
			MAX-ACCESS read-only
			STATUS current
			DESCRIPTION
				"Description."
			::= { sleEponStatsOnuUniEntry 2 }

		
		-- 1.3.6.1.4.1.6296.101.20.7.2.2.1.3
		sleEponStatsOnuUniInErrPkts OBJECT-TYPE
			SYNTAX Counter32
			MAX-ACCESS read-only
			STATUS current
			DESCRIPTION
				"Description."
			::= { sleEponStatsOnuUniEntry 3 }

		
		-- 1.3.6.1.4.1.6296.101.20.7.2.2.1.4
		sleEponStatsOnuUniInErrBytes OBJECT-TYPE
			SYNTAX Counter32
			MAX-ACCESS read-only
			STATUS current
			DESCRIPTION
				"Description."
			::= { sleEponStatsOnuUniEntry 4 }

		
		-- 1.3.6.1.4.1.6296.101.20.7.2.2.1.5
		sleEponStatsOnuUniInPause OBJECT-TYPE
			SYNTAX Counter32
			MAX-ACCESS read-only
			STATUS current
			DESCRIPTION
				"Description."
			::= { sleEponStatsOnuUniEntry 5 }

		
		-- 1.3.6.1.4.1.6296.101.20.7.2.2.1.6
		sleEponStatsOnuUniFrameLongError OBJECT-TYPE
			SYNTAX Counter32
			MAX-ACCESS read-only
			STATUS current
			DESCRIPTION
				"Description."
			::= { sleEponStatsOnuUniEntry 6 }

		
		-- 1.3.6.1.4.1.6296.101.20.7.2.2.1.7
		sleEponStatsOnuUniOutPkts OBJECT-TYPE
			SYNTAX Counter32
			MAX-ACCESS read-only
			STATUS current
			DESCRIPTION
				"Description."
			::= { sleEponStatsOnuUniEntry 7 }

		
		-- 1.3.6.1.4.1.6296.101.20.7.2.2.1.8
		sleEponStatsOnuUniOutBytes OBJECT-TYPE
			SYNTAX Counter64
			MAX-ACCESS read-only
			STATUS current
			DESCRIPTION
				"Description."
			::= { sleEponStatsOnuUniEntry 8 }

		
		-- 1.3.6.1.4.1.6296.101.20.7.2.2.1.9
		sleEponStatsOnuUniOutPause OBJECT-TYPE
			SYNTAX Counter32
			MAX-ACCESS read-only
			STATUS current
			DESCRIPTION
				"Description."
			::= { sleEponStatsOnuUniEntry 9 }

		
		-- 1.3.6.1.4.1.6296.101.20.7.2.2.1.10
		sleEponStatsOnuUniOutDropPkts OBJECT-TYPE
			SYNTAX Counter32
			MAX-ACCESS read-only
			STATUS current
			DESCRIPTION
				"Description."
			::= { sleEponStatsOnuUniEntry 10 }

		
		-- 1.3.6.1.4.1.6296.101.20.7.2.2.1.11
		sleEponStatsOnuUnInMcastPkts OBJECT-TYPE
			SYNTAX Counter32
			MAX-ACCESS read-only
			STATUS current
			DESCRIPTION
				"The total number of Rx multicast packets on the ONU Uni side."
			::= { sleEponStatsOnuUniEntry 11 }

		
		-- 1.3.6.1.4.1.6296.101.20.7.2.2.1.12
		sleEponStatsOnuUnInBcastPkts OBJECT-TYPE
			SYNTAX Counter32
			MAX-ACCESS read-only
			STATUS current
			DESCRIPTION
				"The total number of Rx broadcast packets on the ONU Uni side."
			::= { sleEponStatsOnuUniEntry 12 }

		
		-- 1.3.6.1.4.1.6296.101.20.7.2.2.1.13
		sleEponStatsOnuUniInDropPkts OBJECT-TYPE
			SYNTAX Counter32
			MAX-ACCESS read-only
			STATUS current
			DESCRIPTION
				"The total number of Rx dropped packets on the ONU Uni side."
			::= { sleEponStatsOnuUniEntry 13 }

		
		-- 1.3.6.1.4.1.6296.101.20.7.2.2.1.14
		sleEponStatsOnuUniOutMcastPkts OBJECT-TYPE
			SYNTAX Counter32
			MAX-ACCESS read-only
			STATUS current
			DESCRIPTION
				"The total number of Tx multicast packets on the ONU Uni side."
			::= { sleEponStatsOnuUniEntry 14 }

		
		-- 1.3.6.1.4.1.6296.101.20.7.2.2.1.15
		sleEponStatsOnuUniOutBcastPkts OBJECT-TYPE
			SYNTAX Counter32
			MAX-ACCESS read-only
			STATUS current
			DESCRIPTION
				"The total number of Tx braocast packets on the ONU Uni side."
			::= { sleEponStatsOnuUniEntry 15 }

		
		-- 1.3.6.1.4.1.6296.101.20.7.2.3
		sleEponStatsOnuPonTable OBJECT-TYPE
			SYNTAX SEQUENCE OF SleEponStatsOnuPonEntry
			MAX-ACCESS not-accessible
			STATUS current
			DESCRIPTION
				"Description."
			::= { sleEponOnuStatistics 3 }

		
		-- 1.3.6.1.4.1.6296.101.20.7.2.3.1
		sleEponStatsOnuPonEntry OBJECT-TYPE
			SYNTAX SleEponStatsOnuPonEntry
			MAX-ACCESS not-accessible
			STATUS current
			DESCRIPTION
				"Description."
			INDEX { sleEponOltIndex, sleEponOnuIndex }
			::= { sleEponStatsOnuPonTable 1 }

		
		SleEponStatsOnuPonEntry ::=
			SEQUENCE { 
				sleEponStatsOnuPonInPkts
					Counter32,
				sleEponStatsOnuPonInBytes
					Counter32,
				sleEponStatsOnuPonInMcastPkts
					Counter32,
				sleEponStatsOnuPonIntBcastPkts
					Counter32,
				sleEponStatsOnuPonInErrPkts
					Counter32,
				sleEponStatsOnuPonInErrBytes
					Counter32,
				sleEponStatsOnuPonInPause
					Counter32,
				sleEponStatsOnuPonInHostPkts
					Counter32,
				sleEponStatsOnuPonInDropHostPkts
					Counter32,
				sleEponStatsOnuPonFrameLongError
					Counter32,
				sleEponStatsOnuPonOutPkts
					Counter32,
				sleEponStatsOnuPonOutBytes
					Counter32,
				sleEponStatsOnuPonOutMcastPkts
					Counter32,
				sleEponStatsOnuPonOutBcastPkts
					Counter32,
				sleEponStatsOnuPonOutPause
					Counter32,
				sleEponStatsOnuPonOutDropPkts
					Counter32,
				sleEponStatsOnuPonOutHostPkts
					Counter32,
				sleEponStatsOnuPonOutChipErrPkts
					Counter32,
				sleEponStatsOnuPonInDropPkts
					Counter32
			 }

		-- 1.3.6.1.4.1.6296.101.20.7.2.3.1.1
		sleEponStatsOnuPonInPkts OBJECT-TYPE
			SYNTAX Counter32
			MAX-ACCESS read-only
			STATUS current
			DESCRIPTION
				"Description."
			::= { sleEponStatsOnuPonEntry 1 }

		
		-- 1.3.6.1.4.1.6296.101.20.7.2.3.1.2
		sleEponStatsOnuPonInBytes OBJECT-TYPE
			SYNTAX Counter32
			MAX-ACCESS read-only
			STATUS current
			DESCRIPTION
				"Description."
			::= { sleEponStatsOnuPonEntry 2 }

		
		-- 1.3.6.1.4.1.6296.101.20.7.2.3.1.3
		sleEponStatsOnuPonInMcastPkts OBJECT-TYPE
			SYNTAX Counter32
			MAX-ACCESS read-only
			STATUS current
			DESCRIPTION
				"Description."
			::= { sleEponStatsOnuPonEntry 3 }

		
		-- 1.3.6.1.4.1.6296.101.20.7.2.3.1.4
		sleEponStatsOnuPonIntBcastPkts OBJECT-TYPE
			SYNTAX Counter32
			MAX-ACCESS read-only
			STATUS current
			DESCRIPTION
				"Description."
			::= { sleEponStatsOnuPonEntry 4 }

		
		-- 1.3.6.1.4.1.6296.101.20.7.2.3.1.5
		sleEponStatsOnuPonInErrPkts OBJECT-TYPE
			SYNTAX Counter32
			MAX-ACCESS read-only
			STATUS current
			DESCRIPTION
				"Description."
			::= { sleEponStatsOnuPonEntry 5 }

		
		-- 1.3.6.1.4.1.6296.101.20.7.2.3.1.6
		sleEponStatsOnuPonInErrBytes OBJECT-TYPE
			SYNTAX Counter32
			MAX-ACCESS read-only
			STATUS current
			DESCRIPTION
				"Description."
			::= { sleEponStatsOnuPonEntry 6 }

		
		-- 1.3.6.1.4.1.6296.101.20.7.2.3.1.7
		sleEponStatsOnuPonInPause OBJECT-TYPE
			SYNTAX Counter32
			MAX-ACCESS read-only
			STATUS current
			DESCRIPTION
				"Description."
			::= { sleEponStatsOnuPonEntry 7 }

		
		-- 1.3.6.1.4.1.6296.101.20.7.2.3.1.8
		sleEponStatsOnuPonInHostPkts OBJECT-TYPE
			SYNTAX Counter32
			MAX-ACCESS read-only
			STATUS current
			DESCRIPTION
				"Description."
			::= { sleEponStatsOnuPonEntry 8 }

		
		-- 1.3.6.1.4.1.6296.101.20.7.2.3.1.9
		sleEponStatsOnuPonInDropHostPkts OBJECT-TYPE
			SYNTAX Counter32
			MAX-ACCESS read-only
			STATUS current
			DESCRIPTION
				"Description."
			::= { sleEponStatsOnuPonEntry 9 }

		
		-- 1.3.6.1.4.1.6296.101.20.7.2.3.1.10
		sleEponStatsOnuPonFrameLongError OBJECT-TYPE
			SYNTAX Counter32
			MAX-ACCESS read-only
			STATUS current
			DESCRIPTION
				"Description."
			::= { sleEponStatsOnuPonEntry 10 }

		
		-- 1.3.6.1.4.1.6296.101.20.7.2.3.1.11
		sleEponStatsOnuPonOutPkts OBJECT-TYPE
			SYNTAX Counter32
			MAX-ACCESS read-only
			STATUS current
			DESCRIPTION
				"Description."
			::= { sleEponStatsOnuPonEntry 11 }

		
		-- 1.3.6.1.4.1.6296.101.20.7.2.3.1.12
		sleEponStatsOnuPonOutBytes OBJECT-TYPE
			SYNTAX Counter32
			MAX-ACCESS read-only
			STATUS current
			DESCRIPTION
				"Description."
			::= { sleEponStatsOnuPonEntry 12 }

		
		-- 1.3.6.1.4.1.6296.101.20.7.2.3.1.13
		sleEponStatsOnuPonOutMcastPkts OBJECT-TYPE
			SYNTAX Counter32
			MAX-ACCESS read-only
			STATUS current
			DESCRIPTION
				"Description."
			::= { sleEponStatsOnuPonEntry 13 }

		
		-- 1.3.6.1.4.1.6296.101.20.7.2.3.1.14
		sleEponStatsOnuPonOutBcastPkts OBJECT-TYPE
			SYNTAX Counter32
			MAX-ACCESS read-only
			STATUS current
			DESCRIPTION
				"Description."
			::= { sleEponStatsOnuPonEntry 14 }

		
		-- 1.3.6.1.4.1.6296.101.20.7.2.3.1.15
		sleEponStatsOnuPonOutPause OBJECT-TYPE
			SYNTAX Counter32
			MAX-ACCESS read-only
			STATUS current
			DESCRIPTION
				"Description."
			::= { sleEponStatsOnuPonEntry 15 }

		
		-- 1.3.6.1.4.1.6296.101.20.7.2.3.1.16
		sleEponStatsOnuPonOutDropPkts OBJECT-TYPE
			SYNTAX Counter32
			MAX-ACCESS read-only
			STATUS current
			DESCRIPTION
				"Description."
			::= { sleEponStatsOnuPonEntry 16 }

		
		-- 1.3.6.1.4.1.6296.101.20.7.2.3.1.17
		sleEponStatsOnuPonOutHostPkts OBJECT-TYPE
			SYNTAX Counter32
			MAX-ACCESS read-only
			STATUS current
			DESCRIPTION
				"Description."
			::= { sleEponStatsOnuPonEntry 17 }

		
		-- 1.3.6.1.4.1.6296.101.20.7.2.3.1.18
		sleEponStatsOnuPonOutChipErrPkts OBJECT-TYPE
			SYNTAX Counter32
			MAX-ACCESS read-only
			STATUS current
			DESCRIPTION
				"Description."
			::= { sleEponStatsOnuPonEntry 18 }

		
		-- 1.3.6.1.4.1.6296.101.20.7.2.3.1.19
		sleEponStatsOnuPonInDropPkts OBJECT-TYPE
			SYNTAX Counter32
			MAX-ACCESS read-only
			STATUS current
			DESCRIPTION
				"The total number of Rx droped packest received on the ONU Pon side."
			::= { sleEponStatsOnuPonEntry 19 }

		
		-- 1.3.6.1.4.1.6296.101.20.7.3
		sleEponPerTimeStatistics OBJECT IDENTIFIER ::= { sleEponStatistics 3 }

		
		-- 1.3.6.1.4.1.6296.101.20.7.3.1
		sleEponPTimeStatsPortTable OBJECT-TYPE
			SYNTAX SEQUENCE OF SleEponPTimeStatsPortEntry
			MAX-ACCESS not-accessible
			STATUS current
			DESCRIPTION
				"Description."
			::= { sleEponPerTimeStatistics 1 }

		
		-- 1.3.6.1.4.1.6296.101.20.7.3.1.1
		sleEponPTimeStatsPortEntry OBJECT-TYPE
			SYNTAX SleEponPTimeStatsPortEntry
			MAX-ACCESS not-accessible
			STATUS current
			DESCRIPTION
				"Description."
			INDEX { ifIndex }
			::= { sleEponPTimeStatsPortTable 1 }

		
		SleEponPTimeStatsPortEntry ::=
			SEQUENCE { 
				sleEponPTimeStatsPortSaveTime
					Gauge32,
				sleEponPTimeStatsPortHourInOctets
					Counter64,
				sleEponPTimeStatsPortHourOutOctets
					Counter64,
				sleEponPTimeStatsPortDayInOctets
					Counter64,
				sleEponPTimeStatsPortDayOutOctets
					Counter64
			 }

		-- 1.3.6.1.4.1.6296.101.20.7.3.1.1.1
		sleEponPTimeStatsPortSaveTime OBJECT-TYPE
			SYNTAX Gauge32
			MAX-ACCESS read-only
			STATUS current
			DESCRIPTION
				"Description."
			::= { sleEponPTimeStatsPortEntry 1 }

		
		-- 1.3.6.1.4.1.6296.101.20.7.3.1.1.2
		sleEponPTimeStatsPortHourInOctets OBJECT-TYPE
			SYNTAX Counter64
			MAX-ACCESS read-only
			STATUS current
			DESCRIPTION
				"Description."
			::= { sleEponPTimeStatsPortEntry 2 }

		
		-- 1.3.6.1.4.1.6296.101.20.7.3.1.1.3
		sleEponPTimeStatsPortHourOutOctets OBJECT-TYPE
			SYNTAX Counter64
			MAX-ACCESS read-only
			STATUS current
			DESCRIPTION
				"Description."
			::= { sleEponPTimeStatsPortEntry 3 }

		
		-- 1.3.6.1.4.1.6296.101.20.7.3.1.1.4
		sleEponPTimeStatsPortDayInOctets OBJECT-TYPE
			SYNTAX Counter64
			MAX-ACCESS read-only
			STATUS current
			DESCRIPTION
				"Description."
			::= { sleEponPTimeStatsPortEntry 4 }

		
		-- 1.3.6.1.4.1.6296.101.20.7.3.1.1.5
		sleEponPTimeStatsPortDayOutOctets OBJECT-TYPE
			SYNTAX Counter64
			MAX-ACCESS read-only
			STATUS current
			DESCRIPTION
				"Description."
			::= { sleEponPTimeStatsPortEntry 5 }

		
		-- 1.3.6.1.4.1.6296.101.20.7.3.2
		sleEponPTimeStatsOltTable OBJECT-TYPE
			SYNTAX SEQUENCE OF SleEponPTimeStatsOltEntry
			MAX-ACCESS not-accessible
			STATUS current
			DESCRIPTION
				"Description."
			::= { sleEponPerTimeStatistics 2 }

		
		-- 1.3.6.1.4.1.6296.101.20.7.3.2.1
		sleEponPTimeStatsOltEntry OBJECT-TYPE
			SYNTAX SleEponPTimeStatsOltEntry
			MAX-ACCESS not-accessible
			STATUS current
			DESCRIPTION
				"Description."
			INDEX { sleEponOltIndex }
			::= { sleEponPTimeStatsOltTable 1 }

		
		SleEponPTimeStatsOltEntry ::=
			SEQUENCE { 
				sleEponPTimeStatsOltSaveTime
					Gauge32,
				sleEponPTimeStatsOltHourInOctets
					Counter64,
				sleEponPTimeStatsOltHourOutOctets
					Counter64,
				sleEponPTimeStatsOltDayInOctets
					Counter64,
				sleEponPTimeStatsOltDayOutOctets
					Counter64
			 }

		-- 1.3.6.1.4.1.6296.101.20.7.3.2.1.1
		sleEponPTimeStatsOltSaveTime OBJECT-TYPE
			SYNTAX Gauge32
			MAX-ACCESS read-only
			STATUS current
			DESCRIPTION
				"Description."
			::= { sleEponPTimeStatsOltEntry 1 }

		
		-- 1.3.6.1.4.1.6296.101.20.7.3.2.1.2
		sleEponPTimeStatsOltHourInOctets OBJECT-TYPE
			SYNTAX Counter64
			MAX-ACCESS read-only
			STATUS current
			DESCRIPTION
				"Description."
			::= { sleEponPTimeStatsOltEntry 2 }

		
		-- 1.3.6.1.4.1.6296.101.20.7.3.2.1.3
		sleEponPTimeStatsOltHourOutOctets OBJECT-TYPE
			SYNTAX Counter64
			MAX-ACCESS read-only
			STATUS current
			DESCRIPTION
				"Description."
			::= { sleEponPTimeStatsOltEntry 3 }

		
		-- 1.3.6.1.4.1.6296.101.20.7.3.2.1.4
		sleEponPTimeStatsOltDayInOctets OBJECT-TYPE
			SYNTAX Counter64
			MAX-ACCESS read-only
			STATUS current
			DESCRIPTION
				"Description."
			::= { sleEponPTimeStatsOltEntry 4 }

		
		-- 1.3.6.1.4.1.6296.101.20.7.3.2.1.5
		sleEponPTimeStatsOltDayOutOctets OBJECT-TYPE
			SYNTAX Counter64
			MAX-ACCESS read-only
			STATUS current
			DESCRIPTION
				"Description."
			::= { sleEponPTimeStatsOltEntry 5 }

		
		-- 1.3.6.1.4.1.6296.101.20.7.3.3
		sleEponPTimeStatsOnuTable OBJECT-TYPE
			SYNTAX SEQUENCE OF SleEponPTimeStatsOnuEntry
			MAX-ACCESS not-accessible
			STATUS current
			DESCRIPTION
				"Description."
			::= { sleEponPerTimeStatistics 3 }

		
		-- 1.3.6.1.4.1.6296.101.20.7.3.3.1
		sleEponPTimeStatsOnuEntry OBJECT-TYPE
			SYNTAX SleEponPTimeStatsOnuEntry
			MAX-ACCESS not-accessible
			STATUS current
			DESCRIPTION
				"Description."
			INDEX { sleEponOltIndex, sleEponOnuIndex }
			::= { sleEponPTimeStatsOnuTable 1 }

		
		SleEponPTimeStatsOnuEntry ::=
			SEQUENCE { 
				sleEponPTimeStatsOnuSaveTime
					Gauge32,
				sleEponPTimeStatsOnuHourInOctets
					Counter64,
				sleEponPTimeStatsOnuHourOutOctets
					Counter64,
				sleEponPTimeStatsOnuDayInOctets
					Counter64,
				sleEponPTimeStatsOnuDayOutOctets
					Counter64
			 }

		-- 1.3.6.1.4.1.6296.101.20.7.3.3.1.1
		sleEponPTimeStatsOnuSaveTime OBJECT-TYPE
			SYNTAX Gauge32
			MAX-ACCESS read-only
			STATUS current
			DESCRIPTION
				"Description."
			::= { sleEponPTimeStatsOnuEntry 1 }

		
		-- 1.3.6.1.4.1.6296.101.20.7.3.3.1.2
		sleEponPTimeStatsOnuHourInOctets OBJECT-TYPE
			SYNTAX Counter64
			MAX-ACCESS read-only
			STATUS current
			DESCRIPTION
				"Description."
			::= { sleEponPTimeStatsOnuEntry 2 }

		
		-- 1.3.6.1.4.1.6296.101.20.7.3.3.1.3
		sleEponPTimeStatsOnuHourOutOctets OBJECT-TYPE
			SYNTAX Counter64
			MAX-ACCESS read-only
			STATUS current
			DESCRIPTION
				"Description."
			::= { sleEponPTimeStatsOnuEntry 3 }

		
		-- 1.3.6.1.4.1.6296.101.20.7.3.3.1.4
		sleEponPTimeStatsOnuDayInOctets OBJECT-TYPE
			SYNTAX Counter64
			MAX-ACCESS read-only
			STATUS current
			DESCRIPTION
				"Description."
			::= { sleEponPTimeStatsOnuEntry 4 }

		
		-- 1.3.6.1.4.1.6296.101.20.7.3.3.1.5
		sleEponPTimeStatsOnuDayOutOctets OBJECT-TYPE
			SYNTAX Counter64
			MAX-ACCESS read-only
			STATUS current
			DESCRIPTION
				"Description."
			::= { sleEponPTimeStatsOnuEntry 5 }

		
		-- 1.3.6.1.4.1.6296.101.20.7.3.4
		sleEponPTimeStatsInfo OBJECT IDENTIFIER ::= { sleEponPerTimeStatistics 4 }

		
		-- 1.3.6.1.4.1.6296.101.20.7.3.4.1
		sleEponPTimeStatsBase OBJECT IDENTIFIER ::= { sleEponPTimeStatsInfo 1 }

		
		-- 1.3.6.1.4.1.6296.101.20.7.3.4.1.1
		sleEponPTimeStatsServiceActivity OBJECT-TYPE
			SYNTAX EnableFlag
			MAX-ACCESS read-only
			STATUS current
			DESCRIPTION
				"Description."
			::= { sleEponPTimeStatsBase 1 }

		
		-- 1.3.6.1.4.1.6296.101.20.7.3.4.2
		sleEponPTimeStatsControl OBJECT IDENTIFIER ::= { sleEponPTimeStatsInfo 2 }

		
		-- 1.3.6.1.4.1.6296.101.20.7.3.4.2.1
		sleEponPTimeStatsControlRequest OBJECT-TYPE
			SYNTAX INTEGER
				{
				setEponPerTimeStatisticsServiceActivity(1),
				clearEponPerTimeStatistics(2)
				}
			MAX-ACCESS read-write
			STATUS current
			DESCRIPTION
				"Description."
			::= { sleEponPTimeStatsControl 1 }

		
		-- 1.3.6.1.4.1.6296.101.20.7.3.4.2.2
		sleEponPTimeStatsControlStatus OBJECT-TYPE
			SYNTAX SleControlStatusType
			MAX-ACCESS read-only
			STATUS current
			DESCRIPTION
				"Description."
			::= { sleEponPTimeStatsControl 2 }

		
		-- 1.3.6.1.4.1.6296.101.20.7.3.4.2.3
		sleEponPTimeStatsControlTimer OBJECT-TYPE
			SYNTAX Gauge32
			MAX-ACCESS read-write
			STATUS current
			DESCRIPTION
				"Description."
			::= { sleEponPTimeStatsControl 3 }

		
		-- 1.3.6.1.4.1.6296.101.20.7.3.4.2.4
		sleEponPTimeStatsControlTimeStamp OBJECT-TYPE
			SYNTAX TimeTicks
			MAX-ACCESS read-only
			STATUS current
			DESCRIPTION
				"Description."
			::= { sleEponPTimeStatsControl 4 }

		
		-- 1.3.6.1.4.1.6296.101.20.7.3.4.2.5
		sleEponPTimeStatsControlReqResult OBJECT-TYPE
			SYNTAX SleControlRequestResultType
			MAX-ACCESS read-only
			STATUS current
			DESCRIPTION
				"Description."
			::= { sleEponPTimeStatsControl 5 }

		
		-- 1.3.6.1.4.1.6296.101.20.7.3.4.2.6
		sleEponPTimeStatsControlServiceActivity OBJECT-TYPE
			SYNTAX EnableFlag
			MAX-ACCESS read-write
			STATUS current
			DESCRIPTION
				"Description."
			::= { sleEponPTimeStatsControl 6 }

		
		-- 1.3.6.1.4.1.6296.101.20.7.3.4.3
		sleEponPTimeStatsNotification OBJECT IDENTIFIER ::= { sleEponPTimeStatsInfo 3 }

		
		-- 1.3.6.1.4.1.6296.101.20.7.3.4.3.1
		sleEponPTimeStatsServiceActivityChanged NOTIFICATION-TYPE
			OBJECTS { sleEponPTimeStatsControlRequest, sleEponPTimeStatsControlTimeStamp, sleEponPTimeStatsControlReqResult, sleEponPTimeStatsControlServiceActivity }
			STATUS current
			DESCRIPTION 
				"Description."
			::= { sleEponPTimeStatsNotification 1 }

		
		-- 1.3.6.1.4.1.6296.101.20.7.3.4.3.2
		sleEponPTimeStatsCleared NOTIFICATION-TYPE
			OBJECTS { sleEponPTimeStatsControlRequest, sleEponPTimeStatsControlTimeStamp, sleEponPTimeStatsControlReqResult }
			STATUS current
			DESCRIPTION 
				"Description."
			::= { sleEponPTimeStatsNotification 2 }

		
		-- 1.3.6.1.4.1.6296.101.20.8
		sleEponOnuClassification OBJECT IDENTIFIER ::= { sleEpon 8 }

		
		-- 1.3.6.1.4.1.6296.101.20.8.1
		sleEponOnuClassificationTable OBJECT-TYPE
			SYNTAX SEQUENCE OF SleEponOnuClassificationEntry
			MAX-ACCESS not-accessible
			STATUS current
			DESCRIPTION
				"Description."
			::= { sleEponOnuClassification 1 }

		
		-- 1.3.6.1.4.1.6296.101.20.8.1.1
		sleEponOnuClassificationEntry OBJECT-TYPE
			SYNTAX SleEponOnuClassificationEntry
			MAX-ACCESS not-accessible
			STATUS current
			DESCRIPTION
				"Description."
			INDEX { sleEponOnuClassificationIndex }
			::= { sleEponOnuClassificationTable 1 }

		
		SleEponOnuClassificationEntry ::=
			SEQUENCE { 
				sleEponOnuClassificationIndex
					INTEGER,
				sleEponOnuClassificationName
					OCTET STRING,
				sleEponOnuClassificationTrafficDirection
					INTEGER,
				sleEponOnuClassificationLayer
					INTEGER,
				sleEponOnuClassificationEtherType
					Integer32,
				sleEponOnuClassificationProtoTypeNum
					INTEGER,
				sleEponOnuClassificationL3Addr
					IpAddress,
				sleEponOnuClassificationL4Num
					Integer32
			 }

		-- 1.3.6.1.4.1.6296.101.20.8.1.1.1
		sleEponOnuClassificationIndex OBJECT-TYPE
			SYNTAX INTEGER (1..256)
			MAX-ACCESS read-only
			STATUS current
			DESCRIPTION
				"Description."
			::= { sleEponOnuClassificationEntry 1 }

		
		-- 1.3.6.1.4.1.6296.101.20.8.1.1.2
		sleEponOnuClassificationName OBJECT-TYPE
			SYNTAX OCTET STRING (SIZE (1..32))
			MAX-ACCESS read-only
			STATUS current
			DESCRIPTION
				"Description."
			::= { sleEponOnuClassificationEntry 2 }

		
		-- 1.3.6.1.4.1.6296.101.20.8.1.1.3
		sleEponOnuClassificationTrafficDirection OBJECT-TYPE
			SYNTAX INTEGER
				{
				downstream(1),
				upstream(2)
				}
			MAX-ACCESS read-only
			STATUS current
			DESCRIPTION
				"Description."
			::= { sleEponOnuClassificationEntry 3 }

		
		-- 1.3.6.1.4.1.6296.101.20.8.1.1.4
		sleEponOnuClassificationLayer OBJECT-TYPE
			SYNTAX INTEGER
				{
				etherType(1),
				protoType(2),
				layer3Destination(3),
				layer3Source(4),
				layer4Tcp(5),
				layer4Udp(6),
				layer2Cos(7),
				layer2vid(8)
				}
			MAX-ACCESS read-only
			STATUS current
			DESCRIPTION
				"Description."
			::= { sleEponOnuClassificationEntry 4 }

		
		-- 1.3.6.1.4.1.6296.101.20.8.1.1.5
		sleEponOnuClassificationEtherType OBJECT-TYPE
			SYNTAX Integer32
			MAX-ACCESS read-only
			STATUS current
			DESCRIPTION
				"Description."
			::= { sleEponOnuClassificationEntry 5 }

		
		-- 1.3.6.1.4.1.6296.101.20.8.1.1.6
		sleEponOnuClassificationProtoTypeNum OBJECT-TYPE
			SYNTAX INTEGER (0 | 1..255)
			MAX-ACCESS read-only
			STATUS current
			DESCRIPTION
				"Description."
			::= { sleEponOnuClassificationEntry 6 }

		
		-- 1.3.6.1.4.1.6296.101.20.8.1.1.7
		sleEponOnuClassificationL3Addr OBJECT-TYPE
			SYNTAX IpAddress
			MAX-ACCESS read-only
			STATUS current
			DESCRIPTION
				"Description."
			::= { sleEponOnuClassificationEntry 7 }

		
		-- 1.3.6.1.4.1.6296.101.20.8.1.1.8
		sleEponOnuClassificationL4Num OBJECT-TYPE
			SYNTAX Integer32
			MAX-ACCESS read-only
			STATUS current
			DESCRIPTION
				"Description."
			::= { sleEponOnuClassificationEntry 8 }

		
		-- 1.3.6.1.4.1.6296.101.20.8.2
		sleEponOnuClassificationControl OBJECT IDENTIFIER ::= { sleEponOnuClassification 2 }

		
		-- 1.3.6.1.4.1.6296.101.20.8.2.1
		sleEponOnuClassificationControlRequest OBJECT-TYPE
			SYNTAX INTEGER
				{
				createOnuClassification(1),
				destroyOnuClassification(2)
				}
			MAX-ACCESS read-write
			STATUS current
			DESCRIPTION
				"The request of a user command"
			::= { sleEponOnuClassificationControl 1 }

		
		-- 1.3.6.1.4.1.6296.101.20.8.2.2
		sleEponOnuClassificationControlStatus OBJECT-TYPE
			SYNTAX SleControlStatusType
			MAX-ACCESS read-only
			STATUS current
			DESCRIPTION
				"The status of user command"
			::= { sleEponOnuClassificationControl 2 }

		
		-- 1.3.6.1.4.1.6296.101.20.8.2.3
		sleEponOnuClassificationControlTimer OBJECT-TYPE
			SYNTAX Gauge32
			MAX-ACCESS read-write
			STATUS current
			DESCRIPTION
				"The maximum time for the manager for a long running user command"
			::= { sleEponOnuClassificationControl 3 }

		
		-- 1.3.6.1.4.1.6296.101.20.8.2.4
		sleEponOnuClassificationControlTimeStamp OBJECT-TYPE
			SYNTAX TimeTicks
			MAX-ACCESS read-only
			STATUS current
			DESCRIPTION
				"The time stamp of the last command(end of command)"
			::= { sleEponOnuClassificationControl 4 }

		
		-- 1.3.6.1.4.1.6296.101.20.8.2.5
		sleEponOnuClassificationControlReqResult OBJECT-TYPE
			SYNTAX SleControlRequestResultType
			MAX-ACCESS read-only
			STATUS current
			DESCRIPTION
				"The result of the last user command"
			::= { sleEponOnuClassificationControl 5 }

		
		-- 1.3.6.1.4.1.6296.101.20.8.2.6
		sleEponOnuClassificationControlName OBJECT-TYPE
			SYNTAX OCTET STRING (SIZE (1..32))
			MAX-ACCESS read-write
			STATUS current
			DESCRIPTION
				"Description."
			::= { sleEponOnuClassificationControl 6 }

		
		-- 1.3.6.1.4.1.6296.101.20.8.2.7
		sleEponOnuClassificationControlTrafficDirection OBJECT-TYPE
			SYNTAX INTEGER
				{
				downstream(1),
				upstream(2)
				}
			MAX-ACCESS read-write
			STATUS current
			DESCRIPTION
				"Description."
			::= { sleEponOnuClassificationControl 7 }

		
		-- 1.3.6.1.4.1.6296.101.20.8.2.8
		sleEponOnuClassificationControlLayer OBJECT-TYPE
			SYNTAX INTEGER
				{
				etherType(1),
				protoType(2),
				layer3Destination(3),
				layer3Source(4),
				layer4Tcp(5),
				layer4Udp(6),
				layer2Cos(7),
				layer2Vid(8)
				}
			MAX-ACCESS read-write
			STATUS current
			DESCRIPTION
				"Description."
			::= { sleEponOnuClassificationControl 8 }

		
		-- 1.3.6.1.4.1.6296.101.20.8.2.9
		sleEponOnuClassificationControlEtherType OBJECT-TYPE
			SYNTAX Integer32
			MAX-ACCESS read-write
			STATUS current
			DESCRIPTION
				"Description."
			::= { sleEponOnuClassificationControl 9 }

		
		-- 1.3.6.1.4.1.6296.101.20.8.2.10
		sleEponOnuClassificationControlProtoTypeNum OBJECT-TYPE
			SYNTAX INTEGER (0 | 1..255)
			MAX-ACCESS read-write
			STATUS current
			DESCRIPTION
				"Description."
			::= { sleEponOnuClassificationControl 10 }

		
		-- 1.3.6.1.4.1.6296.101.20.8.2.11
		sleEponOnuClassificationControlL3Addr OBJECT-TYPE
			SYNTAX IpAddress
			MAX-ACCESS read-write
			STATUS current
			DESCRIPTION
				"Description."
			::= { sleEponOnuClassificationControl 11 }

		
		-- 1.3.6.1.4.1.6296.101.20.8.2.12
		sleEponOnuClassificationControlL4Num OBJECT-TYPE
			SYNTAX Integer32
			MAX-ACCESS read-write
			STATUS current
			DESCRIPTION
				"Description."
			::= { sleEponOnuClassificationControl 12 }

		
		-- 1.3.6.1.4.1.6296.101.20.8.3
		sleEponOnuClassificationNotification OBJECT IDENTIFIER ::= { sleEponOnuClassification 3 }

		
		-- 1.3.6.1.4.1.6296.101.20.8.3.1
		sleEponOnuClassificationCreated NOTIFICATION-TYPE
			OBJECTS { sleEponOnuClassificationControlName }
			STATUS current
			DESCRIPTION 
				"Description."
			::= { sleEponOnuClassificationNotification 1 }

		
		-- 1.3.6.1.4.1.6296.101.20.8.3.2
		sleEponOnuClassificationDestroyed NOTIFICATION-TYPE
			OBJECTS { sleEponOnuClassificationControlName }
			STATUS current
			DESCRIPTION 
				"Description."
			::= { sleEponOnuClassificationNotification 2 }

		
		-- 1.3.6.1.4.1.6296.101.20.9
		sleEponVlan OBJECT IDENTIFIER ::= { sleEpon 9 }

		
		-- 1.3.6.1.4.1.6296.101.20.9.1
		sleEponVlanOltVlan OBJECT IDENTIFIER ::= { sleEponVlan 1 }

		
		-- 1.3.6.1.4.1.6296.101.20.9.1.1
		sleEponVlanOltVlanTable OBJECT-TYPE
			SYNTAX SEQUENCE OF SleEponVlanOltVlanEntry
			MAX-ACCESS not-accessible
			STATUS current
			DESCRIPTION
				"Description."
			::= { sleEponVlanOltVlan 1 }

		
		-- 1.3.6.1.4.1.6296.101.20.9.1.1.1
		sleEponVlanOltVlanEntry OBJECT-TYPE
			SYNTAX SleEponVlanOltVlanEntry
			MAX-ACCESS not-accessible
			STATUS current
			DESCRIPTION
				"Description."
			INDEX { sleEponOltIndex, sleEponOnuIndex }
			::= { sleEponVlanOltVlanTable 1 }

		
		SleEponVlanOltVlanEntry ::=
			SEQUENCE { 
				sleEponVlanOltVlanMode
					INTEGER,
				sleEponVlanOltVlanNestedStack
					EnableFlag,
				sleEponVlanOltVlanPrefix
					INTEGER,
				sleEponVlanOltVlanSuffix
					INTEGER,
				sleEponVlanOltVlanTag
					INTEGER,
				sleEponVlanOltVlanEtherType
					INTEGER
			 }

		-- 1.3.6.1.4.1.6296.101.20.9.1.1.1.1
		sleEponVlanOltVlanMode OBJECT-TYPE
			SYNTAX INTEGER
				{
				none(0),
				exchange(1),
				stack(2)
				}
			MAX-ACCESS read-only
			STATUS current
			DESCRIPTION
				"Description."
			::= { sleEponVlanOltVlanEntry 1 }

		
		-- 1.3.6.1.4.1.6296.101.20.9.1.1.1.2
		sleEponVlanOltVlanNestedStack OBJECT-TYPE
			SYNTAX EnableFlag
			MAX-ACCESS read-only
			STATUS current
			DESCRIPTION
				"Description."
			::= { sleEponVlanOltVlanEntry 2 }

		
		-- 1.3.6.1.4.1.6296.101.20.9.1.1.1.3
		sleEponVlanOltVlanPrefix OBJECT-TYPE
			SYNTAX INTEGER (-1 | 0..255)
			MAX-ACCESS read-only
			STATUS current
			DESCRIPTION
				"Description."
			::= { sleEponVlanOltVlanEntry 3 }

		
		-- 1.3.6.1.4.1.6296.101.20.9.1.1.1.4
		sleEponVlanOltVlanSuffix OBJECT-TYPE
			SYNTAX INTEGER (-1 | 0..15)
			MAX-ACCESS read-only
			STATUS current
			DESCRIPTION
				"Description."
			::= { sleEponVlanOltVlanEntry 4 }

		
		-- 1.3.6.1.4.1.6296.101.20.9.1.1.1.5
		sleEponVlanOltVlanTag OBJECT-TYPE
			SYNTAX INTEGER (-1 | 1..4096)
			MAX-ACCESS read-only
			STATUS current
			DESCRIPTION
				"Description."
			::= { sleEponVlanOltVlanEntry 5 }

		
		-- 1.3.6.1.4.1.6296.101.20.9.1.1.1.6
		sleEponVlanOltVlanEtherType OBJECT-TYPE
			SYNTAX INTEGER
				{
				none(0),
				etherType0x8100(1),
				etherType0x9100(2)
				}
			MAX-ACCESS read-only
			STATUS current
			DESCRIPTION
				"Description."
			::= { sleEponVlanOltVlanEntry 6 }

		
		-- 1.3.6.1.4.1.6296.101.20.9.1.2
		sleEponVlanOltVlanControl OBJECT IDENTIFIER ::= { sleEponVlanOltVlan 2 }

		
		-- 1.3.6.1.4.1.6296.101.20.9.1.2.1
		sleEponVlanOltVlanControlRequest OBJECT-TYPE
			SYNTAX INTEGER
				{
				setEponVlanOltVlanPrefix(1),
				setEponVlanOltVlanProfile(2)
				}
			MAX-ACCESS read-write
			STATUS current
			DESCRIPTION
				"Description."
			::= { sleEponVlanOltVlanControl 1 }

		
		-- 1.3.6.1.4.1.6296.101.20.9.1.2.2
		sleEponVlanOltVlanControlStatus OBJECT-TYPE
			SYNTAX SleControlStatusType
			MAX-ACCESS read-only
			STATUS current
			DESCRIPTION
				"Description."
			::= { sleEponVlanOltVlanControl 2 }

		
		-- 1.3.6.1.4.1.6296.101.20.9.1.2.3
		sleEponVlanOltVlanControlTimer OBJECT-TYPE
			SYNTAX Gauge32
			MAX-ACCESS read-write
			STATUS current
			DESCRIPTION
				"Description."
			::= { sleEponVlanOltVlanControl 3 }

		
		-- 1.3.6.1.4.1.6296.101.20.9.1.2.4
		sleEponVlanOltVlanControlTimeStamp OBJECT-TYPE
			SYNTAX TimeTicks
			MAX-ACCESS read-only
			STATUS current
			DESCRIPTION
				"Description."
			::= { sleEponVlanOltVlanControl 4 }

		
		-- 1.3.6.1.4.1.6296.101.20.9.1.2.5
		sleEponVlanOltVlanControlReqResult OBJECT-TYPE
			SYNTAX SleControlRequestResultType
			MAX-ACCESS read-only
			STATUS current
			DESCRIPTION
				"Description."
			::= { sleEponVlanOltVlanControl 5 }

		
		-- 1.3.6.1.4.1.6296.101.20.9.1.2.6
		sleEponVlanOltVlanControlOltIndex OBJECT-TYPE
			SYNTAX INTEGER (1..512)
			MAX-ACCESS read-write
			STATUS current
			DESCRIPTION
				"Description."
			::= { sleEponVlanOltVlanControl 6 }

		
		-- 1.3.6.1.4.1.6296.101.20.9.1.2.7
		sleEponVlanOltVlanControlOnuIndex OBJECT-TYPE
			SYNTAX INTEGER (1..64)
			MAX-ACCESS read-write
			STATUS current
			DESCRIPTION
				"Description."
			::= { sleEponVlanOltVlanControl 7 }

		
		-- 1.3.6.1.4.1.6296.101.20.9.1.2.8
		sleEponVlanOltVlanControlMode OBJECT-TYPE
			SYNTAX INTEGER
				{
				none(0),
				exchange(1),
				stack(2)
				}
			MAX-ACCESS read-write
			STATUS current
			DESCRIPTION
				"Description."
			::= { sleEponVlanOltVlanControl 8 }

		
		-- 1.3.6.1.4.1.6296.101.20.9.1.2.9
		sleEponVlanOltVlanControlNestedStack OBJECT-TYPE
			SYNTAX EnableFlag
			MAX-ACCESS read-write
			STATUS current
			DESCRIPTION
				"Description."
			::= { sleEponVlanOltVlanControl 9 }

		
		-- 1.3.6.1.4.1.6296.101.20.9.1.2.10
		sleEponVlanOltVlanControlPrefix OBJECT-TYPE
			SYNTAX INTEGER (-1 | 0..255)
			MAX-ACCESS read-write
			STATUS current
			DESCRIPTION
				"Description."
			::= { sleEponVlanOltVlanControl 10 }

		
		-- 1.3.6.1.4.1.6296.101.20.9.1.2.11
		sleEponVlanOltVlanControlSuffix OBJECT-TYPE
			SYNTAX INTEGER (-1 | 0..15)
			MAX-ACCESS read-write
			STATUS current
			DESCRIPTION
				"Description."
			::= { sleEponVlanOltVlanControl 11 }

		
		-- 1.3.6.1.4.1.6296.101.20.9.1.2.12
		sleEponVlanOltVlanControlVlanTag OBJECT-TYPE
			SYNTAX INTEGER (-1 | 1..4094)
			MAX-ACCESS read-write
			STATUS current
			DESCRIPTION
				"Description."
			::= { sleEponVlanOltVlanControl 12 }

		
		-- 1.3.6.1.4.1.6296.101.20.9.1.2.13
		sleEponVlanOltVlanControlEtherType OBJECT-TYPE
			SYNTAX INTEGER
				{
				none(0),
				etherType0x8100(1),
				etherType0x9100(2)
				}
			MAX-ACCESS read-write
			STATUS current
			DESCRIPTION
				"Description."
			::= { sleEponVlanOltVlanControl 13 }

		
		-- 1.3.6.1.4.1.6296.101.20.9.1.3
		sleEponVlanOltVlanNotification OBJECT IDENTIFIER ::= { sleEponVlanOltVlan 3 }

		
		-- 1.3.6.1.4.1.6296.101.20.9.1.3.1
		sleEponVlanOltVlanPrefixChanged NOTIFICATION-TYPE
			OBJECTS { sleEponVlanOltVlanControlRequest, sleEponVlanOltVlanControlTimeStamp, sleEponVlanOltVlanControlReqResult, sleEponVlanOltVlanControlOltIndex, sleEponVlanOltVlanControlPrefix
				 }
			STATUS current
			DESCRIPTION 
				"Description."
			::= { sleEponVlanOltVlanNotification 1 }

		
		-- 1.3.6.1.4.1.6296.101.20.9.1.3.2
		sleEponVlanOltVlanProfileChanged NOTIFICATION-TYPE
			OBJECTS { sleEponVlanOltVlanControlRequest, sleEponVlanOltVlanControlTimeStamp, sleEponVlanOltVlanControlReqResult, sleEponVlanOltVlanControlOltIndex, sleEponVlanOltVlanControlOnuIndex, 
				sleEponVlanOltVlanControlMode, sleEponVlanOltVlanControlNestedStack, sleEponVlanOltVlanControlSuffix, sleEponVlanOltVlanControlVlanTag, sleEponVlanOltVlanControlEtherType
				 }
			STATUS current
			DESCRIPTION 
				"Description."
			::= { sleEponVlanOltVlanNotification 2 }

		
		-- 1.3.6.1.4.1.6296.101.20.9.2
		sleEponVlanOnuVlan OBJECT IDENTIFIER ::= { sleEponVlan 2 }

		
		-- 1.3.6.1.4.1.6296.101.20.9.2.1
		sleEponVlanOnuVlanTable OBJECT-TYPE
			SYNTAX SEQUENCE OF SleEponVlanOnuVlanEntry
			MAX-ACCESS not-accessible
			STATUS current
			DESCRIPTION
				"Description."
			::= { sleEponVlanOnuVlan 1 }

		
		-- 1.3.6.1.4.1.6296.101.20.9.2.1.1
		sleEponVlanOnuVlanEntry OBJECT-TYPE
			SYNTAX SleEponVlanOnuVlanEntry
			MAX-ACCESS not-accessible
			STATUS current
			DESCRIPTION
				"Description."
			INDEX { sleEponOltIndex, sleEponOnuIndex }
			::= { sleEponVlanOnuVlanTable 1 }

		
		SleEponVlanOnuVlanEntry ::=
			SEQUENCE { 
				sleEponVlanOnuVlanUpMode
					INTEGER,
				sleEponVlanOnuVlanUpVlanTag
					INTEGER,
				sleEponVlanOnuVlanUpEtherType
					INTEGER,
				sleEponVlanOnuVlanUpPriority
					Integer32,
				sleEponVlanOnuVlanDownMode
					INTEGER,
				sleEponVlanOnuVlanDownVlanTag
					INTEGER,
				sleEponVlanOnuVlanDownPriority
					Integer32
			 }

		-- 1.3.6.1.4.1.6296.101.20.9.2.1.1.1
		sleEponVlanOnuVlanUpMode OBJECT-TYPE
			SYNTAX INTEGER
				{
				none(0),
				exchange(1),
				stack(2)
				}
			MAX-ACCESS read-only
			STATUS current
			DESCRIPTION
				"Description."
			::= { sleEponVlanOnuVlanEntry 1 }

		
		-- 1.3.6.1.4.1.6296.101.20.9.2.1.1.2
		sleEponVlanOnuVlanUpVlanTag OBJECT-TYPE
			SYNTAX INTEGER (-1 | 1..4094)
			MAX-ACCESS read-only
			STATUS current
			DESCRIPTION
				"Description."
			::= { sleEponVlanOnuVlanEntry 2 }

		
		-- 1.3.6.1.4.1.6296.101.20.9.2.1.1.3
		sleEponVlanOnuVlanUpEtherType OBJECT-TYPE
			SYNTAX INTEGER
				{
				none(0),
				etherType0x8100(1),
				etherType0x9100(2)
				}
			MAX-ACCESS read-only
			STATUS current
			DESCRIPTION
				"Description."
			::= { sleEponVlanOnuVlanEntry 3 }

		
		-- 1.3.6.1.4.1.6296.101.20.9.2.1.1.4
		sleEponVlanOnuVlanUpPriority OBJECT-TYPE
			SYNTAX Integer32
			MAX-ACCESS read-only
			STATUS current
			DESCRIPTION
				"Description."
			::= { sleEponVlanOnuVlanEntry 4 }

		
		-- 1.3.6.1.4.1.6296.101.20.9.2.1.1.5
		sleEponVlanOnuVlanDownMode OBJECT-TYPE
			SYNTAX INTEGER
				{
				none(0),
				exchange(1),
				stack(2)
				}
			MAX-ACCESS read-only
			STATUS current
			DESCRIPTION
				"Description."
			::= { sleEponVlanOnuVlanEntry 5 }

		
		-- 1.3.6.1.4.1.6296.101.20.9.2.1.1.6
		sleEponVlanOnuVlanDownVlanTag OBJECT-TYPE
			SYNTAX INTEGER (-1 | 1..4094)
			MAX-ACCESS read-only
			STATUS current
			DESCRIPTION
				"Description."
			::= { sleEponVlanOnuVlanEntry 6 }

		
		-- 1.3.6.1.4.1.6296.101.20.9.2.1.1.7
		sleEponVlanOnuVlanDownPriority OBJECT-TYPE
			SYNTAX Integer32
			MAX-ACCESS read-write
			STATUS current
			DESCRIPTION
				"Description."
			::= { sleEponVlanOnuVlanEntry 7 }

		
		-- 1.3.6.1.4.1.6296.101.20.9.2.2
		sleEponVlanOnuVlanControl OBJECT IDENTIFIER ::= { sleEponVlanOnuVlan 2 }

		
		-- 1.3.6.1.4.1.6296.101.20.9.2.2.1
		sleEponVlanOnuVlanControlRequest OBJECT-TYPE
			SYNTAX INTEGER { setEponVlanOnuVlanProfile(1) }
			MAX-ACCESS read-write
			STATUS current
			DESCRIPTION
				"Description."
			::= { sleEponVlanOnuVlanControl 1 }

		
		-- 1.3.6.1.4.1.6296.101.20.9.2.2.2
		sleEponVlanOnuVlanControlStatus OBJECT-TYPE
			SYNTAX SleControlStatusType
			MAX-ACCESS read-only
			STATUS current
			DESCRIPTION
				"Description."
			::= { sleEponVlanOnuVlanControl 2 }

		
		-- 1.3.6.1.4.1.6296.101.20.9.2.2.3
		sleEponVlanOnuVlanControlTimer OBJECT-TYPE
			SYNTAX Gauge32
			MAX-ACCESS read-write
			STATUS current
			DESCRIPTION
				"Description."
			::= { sleEponVlanOnuVlanControl 3 }

		
		-- 1.3.6.1.4.1.6296.101.20.9.2.2.4
		sleEponVlanOnuVlanControlTimeStamp OBJECT-TYPE
			SYNTAX TimeTicks
			MAX-ACCESS read-only
			STATUS current
			DESCRIPTION
				"Description."
			::= { sleEponVlanOnuVlanControl 4 }

		
		-- 1.3.6.1.4.1.6296.101.20.9.2.2.5
		sleEponVlanOnuVlanControlReqResult OBJECT-TYPE
			SYNTAX SleControlRequestResultType
			MAX-ACCESS read-only
			STATUS current
			DESCRIPTION
				"Description."
			::= { sleEponVlanOnuVlanControl 5 }

		
		-- 1.3.6.1.4.1.6296.101.20.9.2.2.6
		sleEponVlanOnuVlanControlOltIndex OBJECT-TYPE
			SYNTAX INTEGER (1..512)
			MAX-ACCESS read-write
			STATUS current
			DESCRIPTION
				"Description."
			::= { sleEponVlanOnuVlanControl 6 }

		
		-- 1.3.6.1.4.1.6296.101.20.9.2.2.7
		sleEponVlanOnuVlanControlOnuIndex OBJECT-TYPE
			SYNTAX INTEGER (1..64)
			MAX-ACCESS read-write
			STATUS current
			DESCRIPTION
				"Description."
			::= { sleEponVlanOnuVlanControl 7 }

		
		-- 1.3.6.1.4.1.6296.101.20.9.2.2.8
		sleEponVlanOnuVlanControlUpMode OBJECT-TYPE
			SYNTAX INTEGER
				{
				none(0),
				exchange(1),
				stack(2)
				}
			MAX-ACCESS read-write
			STATUS current
			DESCRIPTION
				"Description."
			::= { sleEponVlanOnuVlanControl 8 }

		
		-- 1.3.6.1.4.1.6296.101.20.9.2.2.9
		sleEponVlanOnuVlanControlUpVlanTag OBJECT-TYPE
			SYNTAX INTEGER (-1 | 1..4094)
			MAX-ACCESS read-write
			STATUS current
			DESCRIPTION
				"Description."
			::= { sleEponVlanOnuVlanControl 9 }

		
		-- 1.3.6.1.4.1.6296.101.20.9.2.2.10
		sleEponVlanOnuVlanControlUpEtherType OBJECT-TYPE
			SYNTAX INTEGER
				{
				none(0),
				etherType0x8100(1),
				etherType0x9100(2)
				}
			MAX-ACCESS read-write
			STATUS current
			DESCRIPTION
				"Description."
			::= { sleEponVlanOnuVlanControl 10 }

		
		-- 1.3.6.1.4.1.6296.101.20.9.2.2.11
		sleEponVlanOnuVlanControlUpPriority OBJECT-TYPE
			SYNTAX Integer32
			MAX-ACCESS read-write
			STATUS current
			DESCRIPTION
				"Description."
			::= { sleEponVlanOnuVlanControl 11 }

		
		-- 1.3.6.1.4.1.6296.101.20.9.2.2.12
		sleEponVlanOnuVlanControlDownMode OBJECT-TYPE
			SYNTAX INTEGER
				{
				none(0),
				exchange(1),
				stack(2)
				}
			MAX-ACCESS read-write
			STATUS current
			DESCRIPTION
				"Description."
			::= { sleEponVlanOnuVlanControl 12 }

		
		-- 1.3.6.1.4.1.6296.101.20.9.2.2.13
		sleEponVlanOnuVlanControlDownVlanTag OBJECT-TYPE
			SYNTAX INTEGER (-1 | 1..4094)
			MAX-ACCESS read-write
			STATUS current
			DESCRIPTION
				"Description."
			::= { sleEponVlanOnuVlanControl 13 }

		
		-- 1.3.6.1.4.1.6296.101.20.9.2.2.14
		sleEponVlanOnuVlanControlDownPriority OBJECT-TYPE
			SYNTAX Integer32
			MAX-ACCESS read-write
			STATUS current
			DESCRIPTION
				"Description."
			::= { sleEponVlanOnuVlanControl 14 }

		
		-- 1.3.6.1.4.1.6296.101.20.9.2.3
		sleEponVlanOnuVlanNotification OBJECT IDENTIFIER ::= { sleEponVlanOnuVlan 3 }

		
		-- 1.3.6.1.4.1.6296.101.20.9.2.3.1
		sleEponVlanOnuVlanProfileChanged NOTIFICATION-TYPE
			OBJECTS { sleEponVlanOnuVlanControlRequest, sleEponVlanOnuVlanControlTimeStamp, sleEponVlanOnuVlanControlReqResult, sleEponVlanOnuVlanControlOltIndex, sleEponVlanOnuVlanControlOnuIndex, 
				sleEponVlanOnuVlanControlUpMode, sleEponVlanOnuVlanControlUpVlanTag, sleEponVlanOnuVlanControlUpEtherType, sleEponVlanOnuVlanControlDownMode, sleEponVlanOnuVlanControlDownVlanTag
				 }
			STATUS current
			DESCRIPTION 
				"Description."
			::= { sleEponVlanOnuVlanNotification 1 }

		
		-- 1.3.6.1.4.1.6296.101.20.10
		sleEponFirmwareMgmt OBJECT IDENTIFIER ::= { sleEpon 10 }

		
		-- 1.3.6.1.4.1.6296.101.20.10.1
		sleEponFirmwareTable OBJECT-TYPE
			SYNTAX SEQUENCE OF SleEponFirmwareEntry
			MAX-ACCESS not-accessible
			STATUS current
			DESCRIPTION
				"Description."
			::= { sleEponFirmwareMgmt 1 }

		
		-- 1.3.6.1.4.1.6296.101.20.10.1.1
		sleEponFirmwareEntry OBJECT-TYPE
			SYNTAX SleEponFirmwareEntry
			MAX-ACCESS not-accessible
			STATUS current
			DESCRIPTION
				"Description."
			INDEX { sleEponFirmwareType, sleEponFirmwareName }
			::= { sleEponFirmwareTable 1 }

		
		SleEponFirmwareEntry ::=
			SEQUENCE { 
				sleEponFirmwareType
					INTEGER,
				sleEponFirmwareName
					OCTET STRING
			 }

		-- 1.3.6.1.4.1.6296.101.20.10.1.1.1
		sleEponFirmwareType OBJECT-TYPE
			SYNTAX INTEGER
				{
				olt(1),
				onu(2)
				}
			MAX-ACCESS read-only
			STATUS current
			DESCRIPTION
				"Description."
			::= { sleEponFirmwareEntry 1 }

		
		-- 1.3.6.1.4.1.6296.101.20.10.1.1.2
		sleEponFirmwareName OBJECT-TYPE
			SYNTAX OCTET STRING (SIZE (1..128))
			MAX-ACCESS read-only
			STATUS current
			DESCRIPTION
				"Description."
			::= { sleEponFirmwareEntry 2 }

		
		-- 1.3.6.1.4.1.6296.101.20.10.2
		sleEponFirmwareControl OBJECT IDENTIFIER ::= { sleEponFirmwareMgmt 2 }

		
		-- 1.3.6.1.4.1.6296.101.20.10.2.1
		sleEponFirmwareControlRequest OBJECT-TYPE
			SYNTAX INTEGER
				{
				setEponFirmwareUpgradeProfile(1),
				deleteEponFirmware(2)
				}
			MAX-ACCESS read-write
			STATUS current
			DESCRIPTION
				"Description."
			::= { sleEponFirmwareControl 1 }

		
		-- 1.3.6.1.4.1.6296.101.20.10.2.2
		sleEponFirmwareControlStatus OBJECT-TYPE
			SYNTAX SleControlStatusType
			MAX-ACCESS read-only
			STATUS current
			DESCRIPTION
				"Description."
			::= { sleEponFirmwareControl 2 }

		
		-- 1.3.6.1.4.1.6296.101.20.10.2.3
		sleEponFirmwareControlTimer OBJECT-TYPE
			SYNTAX Gauge32
			MAX-ACCESS read-write
			STATUS current
			DESCRIPTION
				"Description."
			::= { sleEponFirmwareControl 3 }

		
		-- 1.3.6.1.4.1.6296.101.20.10.2.4
		sleEponFirmwareControlTimeStamp OBJECT-TYPE
			SYNTAX TimeTicks
			MAX-ACCESS read-only
			STATUS current
			DESCRIPTION
				"Description."
			::= { sleEponFirmwareControl 4 }

		
		-- 1.3.6.1.4.1.6296.101.20.10.2.5
		sleEponFirmwareControlReqResult OBJECT-TYPE
			SYNTAX SleControlRequestResultType
			MAX-ACCESS read-only
			STATUS current
			DESCRIPTION
				"Description."
			::= { sleEponFirmwareControl 5 }

		
		-- 1.3.6.1.4.1.6296.101.20.10.2.6
		sleEponFirmwareControlName OBJECT-TYPE
			SYNTAX OCTET STRING (SIZE (1..128))
			MAX-ACCESS read-write
			STATUS current
			DESCRIPTION
				"Description."
			::= { sleEponFirmwareControl 6 }

		
		-- 1.3.6.1.4.1.6296.101.20.10.2.7
		sleEponFirmwareControlUpgradeMethod OBJECT-TYPE
			SYNTAX INTEGER
				{
				ftp(1),
				tftp(2)
				}
			MAX-ACCESS read-write
			STATUS current
			DESCRIPTION
				"Description."
			::= { sleEponFirmwareControl 7 }

		
		-- 1.3.6.1.4.1.6296.101.20.10.2.8
		sleEponFirmwareControlUpgradeMode OBJECT-TYPE
			SYNTAX INTEGER
				{
				upload(1),
				download(2)
				}
			MAX-ACCESS read-write
			STATUS current
			DESCRIPTION
				"Description."
			::= { sleEponFirmwareControl 8 }

		
		-- 1.3.6.1.4.1.6296.101.20.10.2.9
		sleEponFirmwareControlServerAddress OBJECT-TYPE
			SYNTAX IpAddress
			MAX-ACCESS read-write
			STATUS current
			DESCRIPTION
				"Description."
			::= { sleEponFirmwareControl 9 }

		
		-- 1.3.6.1.4.1.6296.101.20.10.2.10
		sleEponFirmwareControlUser OBJECT-TYPE
			SYNTAX OCTET STRING
			MAX-ACCESS read-write
			STATUS current
			DESCRIPTION
				"Description."
			::= { sleEponFirmwareControl 10 }

		
		-- 1.3.6.1.4.1.6296.101.20.10.2.11
		sleEponFirmwareControlPasswd OBJECT-TYPE
			SYNTAX OCTET STRING
			MAX-ACCESS read-write
			STATUS current
			DESCRIPTION
				"Description."
			::= { sleEponFirmwareControl 11 }

		
		-- 1.3.6.1.4.1.6296.101.20.10.3
		sleEponFirmwareNotification OBJECT IDENTIFIER ::= { sleEponFirmwareMgmt 3 }

		
		-- 1.3.6.1.4.1.6296.101.20.10.3.1
		sleEponFirmwareUpgradeProfileChanged NOTIFICATION-TYPE
			OBJECTS { sleEponFirmwareControlRequest, sleEponFirmwareControlTimeStamp, sleEponFirmwareControlReqResult, sleEponFirmwareControlName, sleEponFirmwareControlUpgradeMethod, 
				sleEponFirmwareControlUpgradeMode, sleEponFirmwareControlServerAddress, sleEponFirmwareControlUser, sleEponFirmwareControlPasswd }
			STATUS current
			DESCRIPTION 
				"Description."
			::= { sleEponFirmwareNotification 1 }

		
		-- 1.3.6.1.4.1.6296.101.20.10.3.2
		sleEponFirmwareDeleted NOTIFICATION-TYPE
			OBJECTS { sleEponFirmwareControlRequest, sleEponFirmwareControlTimeStamp, sleEponFirmwareControlReqResult, sleEponFirmwareControlName }
			STATUS current
			DESCRIPTION 
				"Description."
			::= { sleEponFirmwareNotification 2 }

		
		-- 1.3.6.1.4.1.6296.101.20.11
		sleEponOnuSipUserConfig OBJECT IDENTIFIER ::= { sleEpon 11 }

		
		-- 1.3.6.1.4.1.6296.101.20.11.1
		sleEponOnuSipUserConfigTable OBJECT-TYPE
			SYNTAX SEQUENCE OF SleEponOnuSipUserConfigEntry
			MAX-ACCESS not-accessible
			STATUS current
			DESCRIPTION
				"Description."
			::= { sleEponOnuSipUserConfig 1 }

		
		-- 1.3.6.1.4.1.6296.101.20.11.1.1
		sleEponOnuSipUserConfigEntry OBJECT-TYPE
			SYNTAX SleEponOnuSipUserConfigEntry
			MAX-ACCESS not-accessible
			STATUS current
			DESCRIPTION
				"Description."
			INDEX { sleEponOltIndex, sleEponOnuIndex, sleEponOnuSipUserConfigPots }
			::= { sleEponOnuSipUserConfigTable 1 }

		
		SleEponOnuSipUserConfigEntry ::=
			SEQUENCE { 
				sleEponOnuSipUserConfigPots
					INTEGER,
				sleEponOnuSipUserConfigAccount
					OCTET STRING,
				sleEponOnuSipUserConfigName
					OCTET STRING,
				sleEponOnuSipUserConfigPasswd
					OCTET STRING
			 }

		-- 1.3.6.1.4.1.6296.101.20.11.1.1.1
		sleEponOnuSipUserConfigPots OBJECT-TYPE
			SYNTAX INTEGER (0..65535)
			MAX-ACCESS read-only
			STATUS current
			DESCRIPTION
				"Description."
			::= { sleEponOnuSipUserConfigEntry 1 }

		
		-- 1.3.6.1.4.1.6296.101.20.11.1.1.2
		sleEponOnuSipUserConfigAccount OBJECT-TYPE
			SYNTAX OCTET STRING
			MAX-ACCESS read-only
			STATUS current
			DESCRIPTION
				"Description."
			::= { sleEponOnuSipUserConfigEntry 2 }

		
		-- 1.3.6.1.4.1.6296.101.20.11.1.1.3
		sleEponOnuSipUserConfigName OBJECT-TYPE
			SYNTAX OCTET STRING
			MAX-ACCESS read-only
			STATUS current
			DESCRIPTION
				"Description."
			::= { sleEponOnuSipUserConfigEntry 3 }

		
		-- 1.3.6.1.4.1.6296.101.20.11.1.1.4
		sleEponOnuSipUserConfigPasswd OBJECT-TYPE
			SYNTAX OCTET STRING
			MAX-ACCESS read-only
			STATUS current
			DESCRIPTION
				"Description."
			::= { sleEponOnuSipUserConfigEntry 4 }

		
		-- 1.3.6.1.4.1.6296.101.20.11.2
		sleEponOnuSipUserConfigControl OBJECT IDENTIFIER ::= { sleEponOnuSipUserConfig 2 }

		
		-- 1.3.6.1.4.1.6296.101.20.11.2.1
		sleEponOnuSipUserConfigControlRequest OBJECT-TYPE
			SYNTAX INTEGER
				{
				setEponOnuSipUserConfig(1),
				destroyEponOnuSipUserConfig(2)
				}
			MAX-ACCESS read-write
			STATUS current
			DESCRIPTION
				"Description."
			::= { sleEponOnuSipUserConfigControl 1 }

		
		-- 1.3.6.1.4.1.6296.101.20.11.2.2
		sleEponOnuSipUserConfigControlStatus OBJECT-TYPE
			SYNTAX SleControlStatusType
			MAX-ACCESS read-only
			STATUS current
			DESCRIPTION
				"Description."
			::= { sleEponOnuSipUserConfigControl 2 }

		
		-- 1.3.6.1.4.1.6296.101.20.11.2.3
		sleEponOnuSipUserConfigControlTimer OBJECT-TYPE
			SYNTAX Gauge32
			MAX-ACCESS read-write
			STATUS current
			DESCRIPTION
				"Description."
			::= { sleEponOnuSipUserConfigControl 3 }

		
		-- 1.3.6.1.4.1.6296.101.20.11.2.4
		sleEponOnuSipUserConfigControlTimeStamp OBJECT-TYPE
			SYNTAX TimeTicks
			MAX-ACCESS read-only
			STATUS current
			DESCRIPTION
				"Description."
			::= { sleEponOnuSipUserConfigControl 4 }

		
		-- 1.3.6.1.4.1.6296.101.20.11.2.5
		sleEponOnuSipUserConfigControlReqResult OBJECT-TYPE
			SYNTAX SleControlRequestResultType
			MAX-ACCESS read-only
			STATUS current
			DESCRIPTION
				"Description."
			::= { sleEponOnuSipUserConfigControl 5 }

		
		-- 1.3.6.1.4.1.6296.101.20.11.2.6
		sleEponOnuSipUserConfigControlOltIndex OBJECT-TYPE
			SYNTAX INTEGER
			MAX-ACCESS read-write
			STATUS current
			DESCRIPTION
				"Description."
			::= { sleEponOnuSipUserConfigControl 6 }

		
		-- 1.3.6.1.4.1.6296.101.20.11.2.7
		sleEponOnuSipUserConfigControlOnuIndex OBJECT-TYPE
			SYNTAX INTEGER
			MAX-ACCESS read-write
			STATUS current
			DESCRIPTION
				"Description."
			::= { sleEponOnuSipUserConfigControl 7 }

		
		-- 1.3.6.1.4.1.6296.101.20.11.2.8
		sleEponOnuSipUserConfigControlPots OBJECT-TYPE
			SYNTAX INTEGER
			MAX-ACCESS read-write
			STATUS current
			DESCRIPTION
				"Description."
			::= { sleEponOnuSipUserConfigControl 8 }

		
		-- 1.3.6.1.4.1.6296.101.20.11.2.9
		sleEponOnuSipUserConfigControlAccount OBJECT-TYPE
			SYNTAX OCTET STRING
			MAX-ACCESS read-write
			STATUS current
			DESCRIPTION
				"Description."
			::= { sleEponOnuSipUserConfigControl 9 }

		
		-- 1.3.6.1.4.1.6296.101.20.11.2.10
		sleEponOnuSipUserConfigControlName OBJECT-TYPE
			SYNTAX OCTET STRING
			MAX-ACCESS read-write
			STATUS current
			DESCRIPTION
				"Description."
			::= { sleEponOnuSipUserConfigControl 10 }

		
		-- 1.3.6.1.4.1.6296.101.20.11.2.11
		sleEponOnuSipUserConfigControlPasswd OBJECT-TYPE
			SYNTAX OCTET STRING
			MAX-ACCESS read-write
			STATUS current
			DESCRIPTION
				"Description."
			::= { sleEponOnuSipUserConfigControl 11 }

		
		-- 1.3.6.1.4.1.6296.101.20.11.3
		sleEponOnuSipNotification OBJECT IDENTIFIER ::= { sleEponOnuSipUserConfig 3 }

		
		-- 1.3.6.1.4.1.6296.101.20.11.3.1
		sleEponOnuSipUserConfigChanged NOTIFICATION-TYPE
			OBJECTS { sleEponOnuSipUserConfigControlRequest, sleEponOnuSipUserConfigControlTimeStamp, sleEponOnuSipUserConfigControlReqResult, sleEponOnuSipUserConfigControlOltIndex, sleEponOnuSipUserConfigControlOnuIndex, 
				sleEponOnuSipUserConfigControlPots, sleEponOnuSipUserConfigControlAccount, sleEponOnuSipUserConfigControlName, sleEponOnuSipUserConfigControlPasswd }
			STATUS current
			DESCRIPTION 
				"Description."
			::= { sleEponOnuSipNotification 1 }

		
		-- 1.3.6.1.4.1.6296.101.20.11.3.2
		sleEponOnuSipUserConfigDestroyed NOTIFICATION-TYPE
			OBJECTS { sleEponOnuSipUserConfigControlRequest, sleEponOnuSipUserConfigControlTimeStamp, sleEponOnuSipUserConfigControlReqResult, sleEponOnuSipUserConfigControlOltIndex, sleEponOnuSipUserConfigControlOnuIndex, 
				sleEponOnuSipUserConfigControlPots }
			STATUS current
			DESCRIPTION 
				"Description."
			::= { sleEponOnuSipNotification 2 }

		
		-- 1.3.6.1.4.1.6296.101.20.12
		sleEponOnuSipPortStatus OBJECT IDENTIFIER ::= { sleEpon 12 }

		
		-- 1.3.6.1.4.1.6296.101.20.12.1
		sleEponOnuSipPortStatusTable OBJECT-TYPE
			SYNTAX SEQUENCE OF SleEponOnuSipPortStatusEntry
			MAX-ACCESS not-accessible
			STATUS current
			DESCRIPTION
				"Description."
			::= { sleEponOnuSipPortStatus 1 }

		
		-- 1.3.6.1.4.1.6296.101.20.12.1.1
		sleEponOnuSipPortStatusEntry OBJECT-TYPE
			SYNTAX SleEponOnuSipPortStatusEntry
			MAX-ACCESS not-accessible
			STATUS current
			DESCRIPTION
				"Description."
			INDEX { sleEponOltIndex, sleEponOnuIndex, sleEponOnuSipUserConfigPots }
			::= { sleEponOnuSipPortStatusTable 1 }

		
		SleEponOnuSipPortStatusEntry ::=
			SEQUENCE { 
				sleEponOnuVoipPortStatus
					OCTET STRING,
				sleEponOnuSipPortServiceState
					OCTET STRING,
				sleEponOnuSipPortCodecMode
					OCTET STRING
			 }

		-- 1.3.6.1.4.1.6296.101.20.12.1.1.1
		sleEponOnuVoipPortStatus OBJECT-TYPE
			SYNTAX OCTET STRING
			MAX-ACCESS read-only
			STATUS current
			DESCRIPTION
				"Description."
			::= { sleEponOnuSipPortStatusEntry 1 }

		
		-- 1.3.6.1.4.1.6296.101.20.12.1.1.2
		sleEponOnuSipPortServiceState OBJECT-TYPE
			SYNTAX OCTET STRING
			MAX-ACCESS read-only
			STATUS current
			DESCRIPTION
				"Description."
			::= { sleEponOnuSipPortStatusEntry 2 }

		
		-- 1.3.6.1.4.1.6296.101.20.12.1.1.3
		sleEponOnuSipPortCodecMode OBJECT-TYPE
			SYNTAX OCTET STRING
			MAX-ACCESS read-only
			STATUS current
			DESCRIPTION
				"Description."
			::= { sleEponOnuSipPortStatusEntry 3 }

		
		-- 1.3.6.1.4.1.6296.101.20.13
		sleEponRule OBJECT IDENTIFIER ::= { sleEpon 13 }

		
		-- 1.3.6.1.4.1.6296.101.20.13.1
		sleEponRuleClause OBJECT IDENTIFIER ::= { sleEponRule 1 }

		
		-- 1.3.6.1.4.1.6296.101.20.13.1.1
		sleEponRuleClauseTable OBJECT-TYPE
			SYNTAX SEQUENCE OF SleEponRuleClauseEntry
			MAX-ACCESS not-accessible
			STATUS current
			DESCRIPTION
				"Description."
			::= { sleEponRuleClause 1 }

		
		-- 1.3.6.1.4.1.6296.101.20.13.1.1.1
		sleEponRuleClauseEntry OBJECT-TYPE
			SYNTAX SleEponRuleClauseEntry
			MAX-ACCESS not-accessible
			STATUS current
			DESCRIPTION
				"Description."
			INDEX { sleEponOltIndex }
			::= { sleEponRuleClauseTable 1 }

		
		SleEponRuleClauseEntry ::=
			SEQUENCE { 
				sleEponRuleClauseQueue
					INTEGER,
				sleEponRuleClauseQueueValue
					Integer32,
				sleEponRuleClauseLayerOperation
					INTEGER,
				sleEponRuleClauseLayerValue
					INTEGER,
				sleEponRuleClauseL2Mac
					MacAddress,
				sleEponRuleClauseL2EthertypeValue
					INTEGER,
				sleEponRuleClauseNetmask
					INTEGER,
				sleEponRuleClauseL3Addr
					IpAddress,
				sleEponRuleClauseTcpUdpPort
					INTEGER,
				sleEponRuleClauseTcpUdpPortNum
					Integer32,
				sleEponRuleClauseProtoType
					INTEGER,
				sleEponRuleClauseProtoTypeNum
					Integer32,
				sleEponRuleClauseVlanType
					INTEGER,
				sleEponRuleClauseVlanValue
					Integer32,
				sleEponRuleClauseLinkIndexValue
					Integer32,
				sleEponRuleClauseMatchMode
					INTEGER
			 }

		-- 1.3.6.1.4.1.6296.101.20.13.1.1.1.1
		sleEponRuleClauseQueue OBJECT-TYPE
			SYNTAX INTEGER
				{
				queuea(1),
				queueb(2)
				}
			MAX-ACCESS read-only
			STATUS current
			DESCRIPTION
				"State Variable Queue
				1.queue-a
				2.queue-b"
			::= { sleEponRuleClauseEntry 1 }

		
		-- 1.3.6.1.4.1.6296.101.20.13.1.1.1.2
		sleEponRuleClauseQueueValue OBJECT-TYPE
			SYNTAX Integer32
			MAX-ACCESS read-only
			STATUS current
			DESCRIPTION
				"rule clause rule queue."
			::= { sleEponRuleClauseEntry 2 }

		
		-- 1.3.6.1.4.1.6296.101.20.13.1.1.1.3
		sleEponRuleClauseLayerOperation OBJECT-TYPE
			SYNTAX INTEGER
				{
				layer2SrcAddr(1),
				layer2DesAddr(2),
				layer2Tos(3),
				layer2Ttl(4),
				layer2EtherType(5),
				layer3SrcAddr(6),
				layer3DesAddr(7)
				}
			MAX-ACCESS read-only
			STATUS current
			DESCRIPTION
				"The rule clause be used to which layer and which type."
			::= { sleEponRuleClauseEntry 3 }

		
		-- 1.3.6.1.4.1.6296.101.20.13.1.1.1.4
		sleEponRuleClauseLayerValue OBJECT-TYPE
			SYNTAX INTEGER (0..7)
			MAX-ACCESS read-only
			STATUS current
			DESCRIPTION
				"layer value."
			::= { sleEponRuleClauseEntry 4 }

		
		-- 1.3.6.1.4.1.6296.101.20.13.1.1.1.5
		sleEponRuleClauseL2Mac OBJECT-TYPE
			SYNTAX MacAddress
			MAX-ACCESS read-only
			STATUS current
			DESCRIPTION
				"Layer 2 MAC address."
			::= { sleEponRuleClauseEntry 5 }

		
		-- 1.3.6.1.4.1.6296.101.20.13.1.1.1.6
		sleEponRuleClauseL2EthertypeValue OBJECT-TYPE
			SYNTAX INTEGER
				{
				null(0),
				ip0x0800(1),
				arp0x0806(2)
				}
			MAX-ACCESS read-write
			STATUS current
			DESCRIPTION
				"Rule Clause L2 Ethertype Value."
			::= { sleEponRuleClauseEntry 6 }

		
		-- 1.3.6.1.4.1.6296.101.20.13.1.1.1.7
		sleEponRuleClauseNetmask OBJECT-TYPE
			SYNTAX INTEGER (1..48)
			MAX-ACCESS read-only
			STATUS current
			DESCRIPTION
				"The netmask.
				1.layer2 range from 1-48
				2.layer3 range from 1-32"
			::= { sleEponRuleClauseEntry 7 }

		
		-- 1.3.6.1.4.1.6296.101.20.13.1.1.1.8
		sleEponRuleClauseL3Addr OBJECT-TYPE
			SYNTAX IpAddress
			MAX-ACCESS read-only
			STATUS current
			DESCRIPTION
				"Chooseing the sourse or destination IP address be used to the rule clause."
			::= { sleEponRuleClauseEntry 8 }

		
		-- 1.3.6.1.4.1.6296.101.20.13.1.1.1.9
		sleEponRuleClauseTcpUdpPort OBJECT-TYPE
			SYNTAX INTEGER
				{
				srcport(1),
				desport(2)
				}
			MAX-ACCESS read-only
			STATUS current
			DESCRIPTION
				"rule clause tcp/udp port."
			::= { sleEponRuleClauseEntry 9 }

		
		-- 1.3.6.1.4.1.6296.101.20.13.1.1.1.10
		sleEponRuleClauseTcpUdpPortNum OBJECT-TYPE
			SYNTAX Integer32 (0..65535)
			MAX-ACCESS read-only
			STATUS current
			DESCRIPTION
				"rule clause tcp/udp port, number range from 0 to 65535."
			::= { sleEponRuleClauseEntry 10 }

		
		-- 1.3.6.1.4.1.6296.101.20.13.1.1.1.11
		sleEponRuleClauseProtoType OBJECT-TYPE
			SYNTAX INTEGER
				{
				protoType(1),
				slowProto(2)
				}
			MAX-ACCESS read-only
			STATUS current
			DESCRIPTION
				"Protocol type
				1.proto-type 
				2.slow-proto 
				ex:For protocol type 1=ICMP 2=IGMP 6=TCP 17=UDP"
			::= { sleEponRuleClauseEntry 11 }

		
		-- 1.3.6.1.4.1.6296.101.20.13.1.1.1.12
		sleEponRuleClauseProtoTypeNum OBJECT-TYPE
			SYNTAX Integer32 (1..255)
			MAX-ACCESS read-only
			STATUS current
			DESCRIPTION
				"The range from 1 to 255"
			::= { sleEponRuleClauseEntry 12 }

		
		-- 1.3.6.1.4.1.6296.101.20.13.1.1.1.13
		sleEponRuleClauseVlanType OBJECT-TYPE
			SYNTAX INTEGER
				{
				svlan0(1),
				svlan1(2),
				cvlan0(3),
				cvlan1(4)
				}
			MAX-ACCESS read-only
			STATUS current
			DESCRIPTION
				"The rule VLAN type:
				1.s-vlan0
				2.s-vlan1
				3.c-vlan0
				4.c-vlan1"
			::= { sleEponRuleClauseEntry 13 }

		
		-- 1.3.6.1.4.1.6296.101.20.13.1.1.1.14
		sleEponRuleClauseVlanValue OBJECT-TYPE
			SYNTAX Integer32
			MAX-ACCESS read-write
			STATUS current
			DESCRIPTION
				"vlan value."
			::= { sleEponRuleClauseEntry 14 }

		
		-- 1.3.6.1.4.1.6296.101.20.13.1.1.1.15
		sleEponRuleClauseLinkIndexValue OBJECT-TYPE
			SYNTAX Integer32
			MAX-ACCESS read-write
			STATUS current
			DESCRIPTION
				"Link index."
			::= { sleEponRuleClauseEntry 15 }

		
		-- 1.3.6.1.4.1.6296.101.20.13.1.1.1.16
		sleEponRuleClauseMatchMode OBJECT-TYPE
			SYNTAX INTEGER
				{
				eq(1),
				neq(2),
				lte(3),
				gte(4),
				fe(5),
				nfe(6),
				al(7)
				}
			MAX-ACCESS read-write
			STATUS current
			DESCRIPTION
				"Description."
			::= { sleEponRuleClauseEntry 16 }

		
		-- 1.3.6.1.4.1.6296.101.20.13.1.2
		sleEponRuleClauseControl OBJECT IDENTIFIER ::= { sleEponRuleClause 2 }

		
		-- 1.3.6.1.4.1.6296.101.20.13.1.2.1
		sleEponRuleClauseControlRequest OBJECT-TYPE
			SYNTAX INTEGER
				{
				setRuleClauseQueue(1),
				setRuleClauseLayer2(2),
				setRuleClauseVlan(3),
				setRuleClauseLayer3(4),
				setRuleClauseTcpUdp(5),
				setRuleClauseProtocol(6),
				setRuleClauseLinkIndex(7),
				noRuleClause(8)
				}
			MAX-ACCESS read-write
			STATUS current
			DESCRIPTION
				"The request of a user command."
			::= { sleEponRuleClauseControl 1 }

		
		-- 1.3.6.1.4.1.6296.101.20.13.1.2.2
		sleEponRuleClauseControlStatus OBJECT-TYPE
			SYNTAX SleControlStatusType
			MAX-ACCESS read-only
			STATUS current
			DESCRIPTION
				"The status of user command"
			::= { sleEponRuleClauseControl 2 }

		
		-- 1.3.6.1.4.1.6296.101.20.13.1.2.3
		sleEponRuleClauseControlTimer OBJECT-TYPE
			SYNTAX Gauge32
			MAX-ACCESS read-write
			STATUS current
			DESCRIPTION
				"The maximum time for the manager for a long running user command"
			::= { sleEponRuleClauseControl 3 }

		
		-- 1.3.6.1.4.1.6296.101.20.13.1.2.4
		sleEponRuleClauseControlTimeStamp OBJECT-TYPE
			SYNTAX TimeTicks
			MAX-ACCESS read-only
			STATUS current
			DESCRIPTION
				"The time stamp of the last command(end of command)"
			::= { sleEponRuleClauseControl 4 }

		
		-- 1.3.6.1.4.1.6296.101.20.13.1.2.5
		sleEponRuleClauseControlReqResult OBJECT-TYPE
			SYNTAX SleControlRequestResultType
			MAX-ACCESS read-only
			STATUS current
			DESCRIPTION
				"The result of the last user command"
			::= { sleEponRuleClauseControl 5 }

		
		-- 1.3.6.1.4.1.6296.101.20.13.1.2.6
		sleEponRuleClauseControlClauseIndex OBJECT-TYPE
			SYNTAX Integer32
			MAX-ACCESS read-write
			STATUS current
			DESCRIPTION
				"Rule clause index"
			::= { sleEponRuleClauseControl 6 }

		
		-- 1.3.6.1.4.1.6296.101.20.13.1.2.7
		sleEponRuleClauseControlClauseMatch OBJECT-TYPE
			SYNTAX INTEGER
				{
				eq(1),
				neq(2),
				lte(3),
				gte(4),
				fe(5),
				nfe(6),
				al(7)
				}
			MAX-ACCESS read-write
			STATUS current
			DESCRIPTION
				"match mode."
			::= { sleEponRuleClauseControl 7 }

		
		-- 1.3.6.1.4.1.6296.101.20.13.1.2.8
		sleEponRuleClauseControlQueue OBJECT-TYPE
			SYNTAX INTEGER
				{
				queueA(1),
				queueB(2)
				}
			MAX-ACCESS read-write
			STATUS current
			DESCRIPTION
				"State Variable Queue."
			::= { sleEponRuleClauseControl 8 }

		
		-- 1.3.6.1.4.1.6296.101.20.13.1.2.9
		sleEponRuleClauseControlQueueValue OBJECT-TYPE
			SYNTAX INTEGER (0..7)
			MAX-ACCESS read-write
			STATUS current
			DESCRIPTION
				"State Variable Queue Value."
			::= { sleEponRuleClauseControl 9 }

		
		-- 1.3.6.1.4.1.6296.101.20.13.1.2.10
		sleEponRuleClauseControlLayerOperation OBJECT-TYPE
			SYNTAX INTEGER
				{
				layer2SrcAddress(1),
				layer2DesAddress(2),
				layer2Tos(3),
				layer2Ttl(4),
				layer2EtherType(5),
				layer3SrcIPAddress(6),
				layer3DesIPAddress(7)
				}
			MAX-ACCESS read-write
			STATUS current
			DESCRIPTION
				"The rule clause be used to which layer and which type.The layer as following:
				"
			::= { sleEponRuleClauseControl 10 }

		
		-- 1.3.6.1.4.1.6296.101.20.13.1.2.11
		sleEponRuleClauseControlLayerValue OBJECT-TYPE
			SYNTAX Integer32
			MAX-ACCESS read-write
			STATUS current
			DESCRIPTION
				"layer value."
			::= { sleEponRuleClauseControl 11 }

		
		-- 1.3.6.1.4.1.6296.101.20.13.1.2.12
		sleEponRuleClauseControlL2Mac OBJECT-TYPE
			SYNTAX MacAddress
			MAX-ACCESS read-write
			STATUS current
			DESCRIPTION
				"Layer2 Mac address."
			::= { sleEponRuleClauseControl 12 }

		
		-- 1.3.6.1.4.1.6296.101.20.13.1.2.13
		sleEponRuleClauseControlL2EtherType OBJECT-TYPE
			SYNTAX INTEGER
				{
				null(0),
				ip0x0800(1),
				arp0x0806(2)
				}
			MAX-ACCESS read-write
			STATUS current
			DESCRIPTION
				"Rule Clause L2 Ethertype Value."
			::= { sleEponRuleClauseControl 13 }

		
		-- 1.3.6.1.4.1.6296.101.20.13.1.2.14
		sleEponRuleClauseControlNetmask OBJECT-TYPE
			SYNTAX Integer32 (1..48)
			MAX-ACCESS read-write
			STATUS current
			DESCRIPTION
				"The netmask.
				1.layer2 range from 1-48
				2.layer3 range from 1-32"
			::= { sleEponRuleClauseControl 14 }

		
		-- 1.3.6.1.4.1.6296.101.20.13.1.2.15
		sleEponRuleClauseControlL3Addr OBJECT-TYPE
			SYNTAX IpAddress
			MAX-ACCESS read-write
			STATUS current
			DESCRIPTION
				"L3 IP address."
			::= { sleEponRuleClauseControl 15 }

		
		-- 1.3.6.1.4.1.6296.101.20.13.1.2.16
		sleEponRuleClauseControlTcpUdpPort OBJECT-TYPE
			SYNTAX INTEGER
				{
				srcPort(1),
				desPort(2)
				}
			MAX-ACCESS read-write
			STATUS current
			DESCRIPTION
				"Tcp port or Udp port."
			::= { sleEponRuleClauseControl 16 }

		
		-- 1.3.6.1.4.1.6296.101.20.13.1.2.17
		sleEponRuleClauseControlTcpUdpPortNum OBJECT-TYPE
			SYNTAX Integer32 (0..65535)
			MAX-ACCESS read-write
			STATUS current
			DESCRIPTION
				"Port number range from 0 to 65535."
			::= { sleEponRuleClauseControl 17 }

		
		-- 1.3.6.1.4.1.6296.101.20.13.1.2.18
		sleEponRuleClauseControlProtoType OBJECT-TYPE
			SYNTAX INTEGER
				{
				protoType(1),
				slowProtocol(2)
				}
			MAX-ACCESS read-write
			STATUS current
			DESCRIPTION
				"Protocol type
				1.proto-type 
				2.slow-proto 
				ex:For protocol type 1=ICMP 2=IGMP 6=TCP 17=UDP"
			::= { sleEponRuleClauseControl 18 }

		
		-- 1.3.6.1.4.1.6296.101.20.13.1.2.19
		sleEponRuleClauseControlProtoTypeNum OBJECT-TYPE
			SYNTAX INTEGER (1..255)
			MAX-ACCESS read-write
			STATUS current
			DESCRIPTION
				"For protocol type .ex :1=ICMP 2=IGMP 6=TCP 17=UDP
				The range from 1 to 255."
			::= { sleEponRuleClauseControl 19 }

		
		-- 1.3.6.1.4.1.6296.101.20.13.1.2.20
		sleEponRuleClauseControlVlanType OBJECT-TYPE
			SYNTAX INTEGER
				{
				svlan0(1),
				svlan1(2),
				cvlan0(3),
				cvlan1(4)
				}
			MAX-ACCESS read-write
			STATUS current
			DESCRIPTION
				"The rule VLAN type."
			::= { sleEponRuleClauseControl 20 }

		
		-- 1.3.6.1.4.1.6296.101.20.13.1.2.21
		sleEponRuleClauseControlVlanValue OBJECT-TYPE
			SYNTAX Integer32
			MAX-ACCESS read-write
			STATUS current
			DESCRIPTION
				"vlan value."
			::= { sleEponRuleClauseControl 21 }

		
		-- 1.3.6.1.4.1.6296.101.20.13.1.2.22
		sleEponRuleClauseControlLinkIndexValue OBJECT-TYPE
			SYNTAX INTEGER (1..32)
			MAX-ACCESS read-write
			STATUS current
			DESCRIPTION
				"Link index."
			::= { sleEponRuleClauseControl 22 }

		
		-- 1.3.6.1.4.1.6296.101.20.13.1.3
		sleEponRuleClauseNotification OBJECT IDENTIFIER ::= { sleEponRuleClause 3 }

		
		-- 1.3.6.1.4.1.6296.101.20.13.1.3.1
		sleEponRuleClauseQueueChanged NOTIFICATION-TYPE
			OBJECTS { sleEponRuleClauseControlRequest, sleEponRuleClauseControlTimeStamp, sleEponRuleClauseControlReqResult, sleEponRuleClauseControlClauseIndex, sleEponRuleClauseControlQueue, 
				sleEponRuleClauseControlQueueValue }
			STATUS current
			DESCRIPTION 
				"Description."
			::= { sleEponRuleClauseNotification 1 }

		
		-- 1.3.6.1.4.1.6296.101.20.13.1.3.2
		sleEponRuleClauseLayer2Changed NOTIFICATION-TYPE
			OBJECTS { sleEponRuleClauseControlRequest, sleEponRuleClauseControlTimeStamp, sleEponRuleClauseControlReqResult, sleEponRuleClauseControlClauseIndex, sleEponRuleClauseControlLayerOperation, 
				sleEponRuleClauseControlL2Mac, sleEponRuleClauseControlL2EtherType, sleEponRuleClauseControlNetmask }
			STATUS current
			DESCRIPTION 
				"Description."
			::= { sleEponRuleClauseNotification 2 }

		
		-- 1.3.6.1.4.1.6296.101.20.13.1.3.3
		sleEponRuleClauseVlanChanged NOTIFICATION-TYPE
			OBJECTS { sleEponRuleClauseControlRequest, sleEponRuleClauseControlTimeStamp, sleEponRuleClauseControlReqResult, sleEponRuleClauseControlClauseIndex, sleEponRuleClauseControlVlanType, 
				sleEponRuleClauseControlVlanValue }
			STATUS current
			DESCRIPTION 
				"Description."
			::= { sleEponRuleClauseNotification 3 }

		
		-- 1.3.6.1.4.1.6296.101.20.13.1.3.4
		sleEponRuleClauseLayer3Changed NOTIFICATION-TYPE
			OBJECTS { sleEponRuleClauseControlRequest, sleEponRuleClauseControlTimeStamp, sleEponRuleClauseControlReqResult, sleEponRuleClauseControlClauseIndex, sleEponRuleClauseControlTcpUdpPort, 
				sleEponRuleClauseControlTcpUdpPortNum }
			STATUS current
			DESCRIPTION 
				"Description."
			::= { sleEponRuleClauseNotification 4 }

		
		-- 1.3.6.1.4.1.6296.101.20.13.1.3.5
		sleEponRuleClauseTcpUdpChanged NOTIFICATION-TYPE
			OBJECTS { sleEponRuleClauseControlRequest, sleEponRuleClauseControlTimeStamp, sleEponRuleClauseControlReqResult, sleEponRuleClauseControlClauseIndex, sleEponRuleClauseControlTcpUdpPort, 
				sleEponRuleClauseControlTcpUdpPortNum }
			STATUS current
			DESCRIPTION 
				"Description."
			::= { sleEponRuleClauseNotification 5 }

		
		-- 1.3.6.1.4.1.6296.101.20.13.1.3.6
		sleEponRuleClauseProtocolChanged NOTIFICATION-TYPE
			OBJECTS { sleEponRuleClauseControlRequest, sleEponRuleClauseControlTimeStamp, sleEponRuleClauseControlReqResult, sleEponRuleClauseControlClauseIndex, sleEponRuleClauseControlProtoType, 
				sleEponRuleClauseControlProtoTypeNum }
			STATUS current
			DESCRIPTION 
				"Description."
			::= { sleEponRuleClauseNotification 6 }

		
		-- 1.3.6.1.4.1.6296.101.20.13.1.3.7
		sleEponRuleClauseLinkIndexChanged NOTIFICATION-TYPE
			OBJECTS { sleEponRuleClauseControlRequest, sleEponRuleClauseControlTimeStamp, sleEponRuleClauseControlReqResult, sleEponRuleClauseControlClauseIndex, sleEponRuleClauseControlLinkIndexValue
				 }
			STATUS current
			DESCRIPTION 
				"Description."
			::= { sleEponRuleClauseNotification 7 }

		
		-- 1.3.6.1.4.1.6296.101.20.13.1.3.8
		sleEponRuleClauseDel NOTIFICATION-TYPE
			OBJECTS { sleEponRuleClauseControlRequest, sleEponRuleClauseControlTimeStamp, sleEponRuleClauseControlReqResult, sleEponRuleClauseControlClauseIndex }
			STATUS current
			DESCRIPTION 
				"Description."
			::= { sleEponRuleClauseNotification 8 }

		
		-- 1.3.6.1.4.1.6296.101.20.13.2
		sleEponRuleAction OBJECT IDENTIFIER ::= { sleEponRule 2 }

		
		-- 1.3.6.1.4.1.6296.101.20.13.2.1
		sleEponRuleActionTable OBJECT-TYPE
			SYNTAX SEQUENCE OF SleEponRuleActionEntry
			MAX-ACCESS not-accessible
			STATUS current
			DESCRIPTION
				"Description."
			::= { sleEponRuleAction 1 }

		
		-- 1.3.6.1.4.1.6296.101.20.13.2.1.1
		sleEponRuleActionEntry OBJECT-TYPE
			SYNTAX SleEponRuleActionEntry
			MAX-ACCESS not-accessible
			STATUS current
			DESCRIPTION
				"Description."
			INDEX { sleEponOltIndex }
			::= { sleEponRuleActionTable 1 }

		
		SleEponRuleActionEntry ::=
			SEQUENCE { 
				sleEponRuleActionVlanOperate
					INTEGER,
				sleEponRuleActionVlanMap
					INTEGER,
				sleEponRuleActionEtherType
					OCTET STRING,
				sleEponRuleActionVlanID
					Integer32,
				sleEponRuleActionDiscardOperate
					INTEGER,
				sleEponRuleActionDiscardOperateValue
					INTEGER,
				sleEponRuleActionCaptureHostOperate
					INTEGER,
				sleEponRuleActionCaptureHostFlexibleOperate
					INTEGER,
				sleEponRuleActionQueueId
					Integer32,
				sleEponRuleActionUnicastLinkDestID
					Integer32,
				sleEponRuleActionUnicastLinkDestOffset
					Integer32,
				sleEponRuleActionMulticastLinkDomID
					Integer32,
				sleEponRuleActionMulticastLinkDomOffset
					Integer32,
				sleEponRuleActionCosOperate
					INTEGER,
				sleEponRuleActionCosValue
					Integer32,
				sleEponRuleActionTosOperate
					INTEGER,
				sleEponRuleActionTosValue
					Integer32,
				sleEponRuleActionOutputOperate
					INTEGER,
				sleEponRuleActionOutputValue
					Integer32,
				sleEponRuleActionOutputVlanContent
					INTEGER,
				sleEponRuleActionOutputSourceFiledCopy
					INTEGER,
				sleEponRuleActionQueuePendingOperate
					INTEGER
			 }

		-- 1.3.6.1.4.1.6296.101.20.13.2.1.1.1
		sleEponRuleActionVlanOperate OBJECT-TYPE
			SYNTAX INTEGER
				{
				addEthertype(1),
				clearAdd(2),
				clearDelete(3),
				delete(4),
				addNoEthertype(5)
				}
			MAX-ACCESS read-only
			STATUS current
			DESCRIPTION
				"Vlan Operate."
			::= { sleEponRuleActionEntry 1 }

		
		-- 1.3.6.1.4.1.6296.101.20.13.2.1.1.2
		sleEponRuleActionVlanMap OBJECT-TYPE
			SYNTAX INTEGER (0..15)
			MAX-ACCESS read-only
			STATUS current
			DESCRIPTION
				"VLAN map:0-null,1-Vlan0,2-Vlan1,4-Vlan2
				VLAN map:0x01-vlan0  0x02-vlan1  0x04-vlan2  0x08-vlan3
				"
			::= { sleEponRuleActionEntry 2 }

		
		-- 1.3.6.1.4.1.6296.101.20.13.2.1.1.3
		sleEponRuleActionEtherType OBJECT-TYPE
			SYNTAX OCTET STRING
			MAX-ACCESS read-only
			STATUS current
			DESCRIPTION
				"Ether Type.
				"
			::= { sleEponRuleActionEntry 3 }

		
		-- 1.3.6.1.4.1.6296.101.20.13.2.1.1.4
		sleEponRuleActionVlanID OBJECT-TYPE
			SYNTAX Integer32
			MAX-ACCESS read-only
			STATUS current
			DESCRIPTION
				"vlan ID.Range from 1 to 4096"
			::= { sleEponRuleActionEntry 4 }

		
		-- 1.3.6.1.4.1.6296.101.20.13.2.1.1.5
		sleEponRuleActionDiscardOperate OBJECT-TYPE
			SYNTAX INTEGER
				{
				discard(1),
				cleardiscard(2)
				}
			MAX-ACCESS read-only
			STATUS current
			DESCRIPTION
				"port map operate
				discard(1),
				clear-discard(2)"
			::= { sleEponRuleActionEntry 5 }

		
		-- 1.3.6.1.4.1.6296.101.20.13.2.1.1.6
		sleEponRuleActionDiscardOperateValue OBJECT-TYPE
			SYNTAX INTEGER
				{
				eponPort(1),
				eponPort1(2),
				nniPort0(4),
				nniPort1(8)
				}
			MAX-ACCESS read-only
			STATUS current
			DESCRIPTION
				"Port map:Epon-port0 x01, Epon-port1 0x02 ,NNI-port0 0x04 ,NNI-port1 0x08."
			::= { sleEponRuleActionEntry 6 }

		
		-- 1.3.6.1.4.1.6296.101.20.13.2.1.1.7
		sleEponRuleActionCaptureHostOperate OBJECT-TYPE
			SYNTAX INTEGER
				{
				premod(1),
				postmod(2),
				premodd(3),
				postmodd(4)
				}
			MAX-ACCESS read-only
			STATUS current
			DESCRIPTION
				"Capture to host operate
				pre-mod(1),Pre-modifications
				post-mod(2),Post-modifications
				pre-mod-d(3),Pre-modifications with domain/destination
				post-mod-d(4),Post-modifications with domain/destination"
			::= { sleEponRuleActionEntry 7 }

		
		-- 1.3.6.1.4.1.6296.101.20.13.2.1.1.8
		sleEponRuleActionCaptureHostFlexibleOperate OBJECT-TYPE
			SYNTAX INTEGER
				{
				preMod(1),
				domDest(2),
				queuePend(3),
				clearD(4)
				}
			MAX-ACCESS read-only
			STATUS current
			DESCRIPTION
				"Capture Host Flexible Operate."
			::= { sleEponRuleActionEntry 8 }

		
		-- 1.3.6.1.4.1.6296.101.20.13.2.1.1.9
		sleEponRuleActionQueueId OBJECT-TYPE
			SYNTAX Integer32
			MAX-ACCESS read-only
			STATUS current
			DESCRIPTION
				"Queue Id."
			::= { sleEponRuleActionEntry 9 }

		
		-- 1.3.6.1.4.1.6296.101.20.13.2.1.1.10
		sleEponRuleActionUnicastLinkDestID OBJECT-TYPE
			SYNTAX Integer32
			MAX-ACCESS read-only
			STATUS current
			DESCRIPTION
				"Destination ID on which to set the link"
			::= { sleEponRuleActionEntry 10 }

		
		-- 1.3.6.1.4.1.6296.101.20.13.2.1.1.11
		sleEponRuleActionUnicastLinkDestOffset OBJECT-TYPE
			SYNTAX Integer32
			MAX-ACCESS read-only
			STATUS current
			DESCRIPTION
				"Offset to the link within the destination"
			::= { sleEponRuleActionEntry 11 }

		
		-- 1.3.6.1.4.1.6296.101.20.13.2.1.1.12
		sleEponRuleActionMulticastLinkDomID OBJECT-TYPE
			SYNTAX Integer32
			MAX-ACCESS read-only
			STATUS current
			DESCRIPTION
				"Domain ID on which to set the multicast link
				"
			::= { sleEponRuleActionEntry 12 }

		
		-- 1.3.6.1.4.1.6296.101.20.13.2.1.1.13
		sleEponRuleActionMulticastLinkDomOffset OBJECT-TYPE
			SYNTAX Integer32
			MAX-ACCESS read-only
			STATUS current
			DESCRIPTION
				"Offset to the multicast link within the domain."
			::= { sleEponRuleActionEntry 13 }

		
		-- 1.3.6.1.4.1.6296.101.20.13.2.1.1.14
		sleEponRuleActionCosOperate OBJECT-TYPE
			SYNTAX INTEGER
				{
				cos(1),
				cosRegTag(2),
				cosCopy(3),
				cosClear(4)
				}
			MAX-ACCESS read-write
			STATUS current
			DESCRIPTION
				"Cos Operate."
			::= { sleEponRuleActionEntry 14 }

		
		-- 1.3.6.1.4.1.6296.101.20.13.2.1.1.15
		sleEponRuleActionCosValue OBJECT-TYPE
			SYNTAX Integer32
			MAX-ACCESS read-write
			STATUS current
			DESCRIPTION
				"Cos Value."
			::= { sleEponRuleActionEntry 15 }

		
		-- 1.3.6.1.4.1.6296.101.20.13.2.1.1.16
		sleEponRuleActionTosOperate OBJECT-TYPE
			SYNTAX INTEGER
				{
				tos(1),
				tosClear(2)
				}
			MAX-ACCESS read-write
			STATUS current
			DESCRIPTION
				"Tos Operate."
			::= { sleEponRuleActionEntry 16 }

		
		-- 1.3.6.1.4.1.6296.101.20.13.2.1.1.17
		sleEponRuleActionTosValue OBJECT-TYPE
			SYNTAX Integer32
			MAX-ACCESS read-write
			STATUS current
			DESCRIPTION
				"tos value."
			::= { sleEponRuleActionEntry 17 }

		
		-- 1.3.6.1.4.1.6296.101.20.13.2.1.1.18
		sleEponRuleActionOutputOperate OBJECT-TYPE
			SYNTAX INTEGER
				{
				and(1),
				or(2),
				set(3),
				add(4),
				copy(5)
				}
			MAX-ACCESS read-only
			STATUS current
			DESCRIPTION
				"Rule action output on the selected field
				1.and,Perform a binary AND on the selected field
				2.or,Perform a binary OR on the selected field
				3.set,Set the selected field
				4.add,Add the selected field
				5.copy,Copy the selected field from another field."
			::= { sleEponRuleActionEntry 18 }

		
		-- 1.3.6.1.4.1.6296.101.20.13.2.1.1.19
		sleEponRuleActionOutputValue OBJECT-TYPE
			SYNTAX Integer32
			MAX-ACCESS read-write
			STATUS current
			DESCRIPTION
				"output value."
			::= { sleEponRuleActionEntry 19 }

		
		-- 1.3.6.1.4.1.6296.101.20.13.2.1.1.20
		sleEponRuleActionOutputVlanContent OBJECT-TYPE
			SYNTAX INTEGER (0..8)
			MAX-ACCESS read-only
			STATUS current
			DESCRIPTION
				"0-3 vlan0 4-7 vlan1(0-TPID 1-CoS 2-VID 3-CoS and VID 4-TPID 5-CoS 6-VID 7-CoS and VID 8-IPv4 ToS
				"
			::= { sleEponRuleActionEntry 20 }

		
		-- 1.3.6.1.4.1.6296.101.20.13.2.1.1.21
		sleEponRuleActionOutputSourceFiledCopy OBJECT-TYPE
			SYNTAX INTEGER (0..25)
			MAX-ACCESS read-only
			STATUS current
			DESCRIPTION
				"Source field for the copy."
			::= { sleEponRuleActionEntry 21 }

		
		-- 1.3.6.1.4.1.6296.101.20.13.2.1.1.22
		sleEponRuleActionQueuePendingOperate OBJECT-TYPE
			SYNTAX INTEGER
				{
				set(1),
				clear(2)
				}
			MAX-ACCESS read-only
			STATUS current
			DESCRIPTION
				"queue-pending operate."
			::= { sleEponRuleActionEntry 22 }

		
		-- 1.3.6.1.4.1.6296.101.20.13.2.2
		sleEponRuleActionControl OBJECT IDENTIFIER ::= { sleEponRuleAction 2 }

		
		-- 1.3.6.1.4.1.6296.101.20.13.2.2.1
		sleEponRuleActionControlRequest OBJECT-TYPE
			SYNTAX INTEGER
				{
				ruleActionVlanSet(1),
				ruleActionDiscardSet(2),
				ruleActionCaptureHostSet(3),
				ruleActionCaptureHostFlexibleSet(4),
				ruleActionQueueSet(5),
				ruleActionUnicastLinkSet(6),
				ruleActionMulticastLinkSet(7),
				ruleActionNoOperation(8),
				ruleActionCosSet(9),
				ruleActionTosSet(10),
				ruleActionOutputSet(11),
				ruleActionQueuePendingSet(12),
				ruleActionSleSet(13),
				noRuleAction(14)
				}
			MAX-ACCESS read-write
			STATUS current
			DESCRIPTION
				"The request of a user command."
			::= { sleEponRuleActionControl 1 }

		
		-- 1.3.6.1.4.1.6296.101.20.13.2.2.2
		sleEponRuleActionControlStatus OBJECT-TYPE
			SYNTAX SleControlStatusType
			MAX-ACCESS read-only
			STATUS current
			DESCRIPTION
				"The status of user command"
			::= { sleEponRuleActionControl 2 }

		
		-- 1.3.6.1.4.1.6296.101.20.13.2.2.3
		sleEponRuleActionControlTimer OBJECT-TYPE
			SYNTAX Gauge32
			MAX-ACCESS read-write
			STATUS current
			DESCRIPTION
				"The maximum time for the manager for a long running user command."
			::= { sleEponRuleActionControl 3 }

		
		-- 1.3.6.1.4.1.6296.101.20.13.2.2.4
		sleEponRuleActionControlTimeStamp OBJECT-TYPE
			SYNTAX TimeTicks
			MAX-ACCESS read-only
			STATUS current
			DESCRIPTION
				"The time stamp of the last command(end of command)"
			::= { sleEponRuleActionControl 4 }

		
		-- 1.3.6.1.4.1.6296.101.20.13.2.2.5
		sleEponRuleActionControlReqResult OBJECT-TYPE
			SYNTAX SleControlRequestResultType
			MAX-ACCESS read-only
			STATUS current
			DESCRIPTION
				"The result of the last user command"
			::= { sleEponRuleActionControl 5 }

		
		-- 1.3.6.1.4.1.6296.101.20.13.2.2.6
		sleEponRuleActionControlIndex OBJECT-TYPE
			SYNTAX Integer32
			MAX-ACCESS read-write
			STATUS current
			DESCRIPTION
				"Rule action index."
			::= { sleEponRuleActionControl 6 }

		
		-- 1.3.6.1.4.1.6296.101.20.13.2.2.7
		sleEponRuleActionControlVlanOperate OBJECT-TYPE
			SYNTAX INTEGER
				{
				addEthertype(1),
				clearAdd(2),
				clearD(3),
				delete(4),
				addNoEthertype(5)
				}
			MAX-ACCESS read-write
			STATUS current
			DESCRIPTION
				"Vlan Operate.
				"
			::= { sleEponRuleActionControl 7 }

		
		-- 1.3.6.1.4.1.6296.101.20.13.2.2.8
		sleEponRuleActionControlVlanMap OBJECT-TYPE
			SYNTAX INTEGER (0..15)
			MAX-ACCESS read-write
			STATUS current
			DESCRIPTION
				"Rule action VLAN map:0-null,1-Vlan0,2-Vlan1,4-Vlan2.
				Rule action cos copy VLAN map:0x01-vlan0  0x02-vlan1  0x04-vlan2  0x08-vlan3."
			::= { sleEponRuleActionControl 8 }

		
		-- 1.3.6.1.4.1.6296.101.20.13.2.2.9
		sleEponRuleActionControlEtherType OBJECT-TYPE
			SYNTAX OCTET STRING
			MAX-ACCESS read-write
			STATUS current
			DESCRIPTION
				"Ethernet Type."
			::= { sleEponRuleActionControl 9 }

		
		-- 1.3.6.1.4.1.6296.101.20.13.2.2.10
		sleEponRuleActionControlVlanID OBJECT-TYPE
			SYNTAX Integer32 (1..4096)
			MAX-ACCESS read-write
			STATUS current
			DESCRIPTION
				"vlan ID.Range from 1 to 4096."
			::= { sleEponRuleActionControl 10 }

		
		-- 1.3.6.1.4.1.6296.101.20.13.2.2.11
		sleEponRuleActionControlDiscardOperate OBJECT-TYPE
			SYNTAX INTEGER
				{
				discard(1),
				clearDdiscard(2)
				}
			MAX-ACCESS read-write
			STATUS current
			DESCRIPTION
				"discard operate.
				"
			::= { sleEponRuleActionControl 11 }

		
		-- 1.3.6.1.4.1.6296.101.20.13.2.2.12
		sleEponRuleActionControlDiscardOperateValue OBJECT-TYPE
			SYNTAX INTEGER
				{
				eponPort(1),
				eponPort1(2),
				nniPort0(4),
				nniPort1(8)
				}
			MAX-ACCESS read-write
			STATUS current
			DESCRIPTION
				"Port map:Epon-port0 x01, Epon-port1 0x02 ,NNI-port0 0x04 ,NNI-port1 0x08."
			::= { sleEponRuleActionControl 12 }

		
		-- 1.3.6.1.4.1.6296.101.20.13.2.2.13
		sleEponRuleActionControlCaptureHostOperate OBJECT-TYPE
			SYNTAX INTEGER
				{
				preMod(1),
				postMod(2),
				preModD(3),
				postModD(4)
				}
			MAX-ACCESS read-write
			STATUS current
			DESCRIPTION
				"Capture to host operate."
			::= { sleEponRuleActionControl 13 }

		
		-- 1.3.6.1.4.1.6296.101.20.13.2.2.14
		sleEponRuleActionControlCaptureHostFlexibleOperate OBJECT-TYPE
			SYNTAX INTEGER
				{
				perMod(1),
				domDest(2),
				queuePend(3),
				clearD(4)
				}
			MAX-ACCESS read-write
			STATUS current
			DESCRIPTION
				"Capture Host Flexible Operate."
			::= { sleEponRuleActionControl 14 }

		
		-- 1.3.6.1.4.1.6296.101.20.13.2.2.15
		sleEponRuleActionControlQueueId OBJECT-TYPE
			SYNTAX Integer32
			MAX-ACCESS read-write
			STATUS current
			DESCRIPTION
				"QueueId."
			::= { sleEponRuleActionControl 15 }

		
		-- 1.3.6.1.4.1.6296.101.20.13.2.2.16
		sleEponRuleActionControlQueuependingOperate OBJECT-TYPE
			SYNTAX INTEGER
				{
				set(1),
				clear(2)
				}
			MAX-ACCESS read-write
			STATUS current
			DESCRIPTION
				"queue-pending operate."
			::= { sleEponRuleActionControl 16 }

		
		-- 1.3.6.1.4.1.6296.101.20.13.2.2.17
		sleEponRuleActionControlUnicastLinkDestID OBJECT-TYPE
			SYNTAX Integer32
			MAX-ACCESS read-write
			STATUS current
			DESCRIPTION
				"Destination ID on which to set the link."
			::= { sleEponRuleActionControl 17 }

		
		-- 1.3.6.1.4.1.6296.101.20.13.2.2.18
		sleEponRuleActionControlUnicastLinkDestOffset OBJECT-TYPE
			SYNTAX Integer32
			MAX-ACCESS read-write
			STATUS current
			DESCRIPTION
				"Offset to the link within the destination."
			::= { sleEponRuleActionControl 18 }

		
		-- 1.3.6.1.4.1.6296.101.20.13.2.2.19
		sleEponRuleActionControlMulticastLinkDomID OBJECT-TYPE
			SYNTAX Integer32
			MAX-ACCESS read-write
			STATUS current
			DESCRIPTION
				"Domain ID on which to set the multicast link."
			::= { sleEponRuleActionControl 19 }

		
		-- 1.3.6.1.4.1.6296.101.20.13.2.2.20
		sleEponRuleActionControlMulticastLinkDomOffset OBJECT-TYPE
			SYNTAX Integer32
			MAX-ACCESS read-write
			STATUS current
			DESCRIPTION
				"Offset to the multicast link within the domain."
			::= { sleEponRuleActionControl 20 }

		
		-- 1.3.6.1.4.1.6296.101.20.13.2.2.21
		sleEponRuleActionControlCosOperate OBJECT-TYPE
			SYNTAX INTEGER
				{
				cos(1),
				cosRepTag(2),
				cosCopy(3),
				cosClear(4)
				}
			MAX-ACCESS read-write
			STATUS current
			DESCRIPTION
				"cos operate.
				"
			::= { sleEponRuleActionControl 21 }

		
		-- 1.3.6.1.4.1.6296.101.20.13.2.2.22
		sleEponRuleActionControlCosValue OBJECT-TYPE
			SYNTAX Integer32
			MAX-ACCESS read-write
			STATUS current
			DESCRIPTION
				"cos value."
			::= { sleEponRuleActionControl 22 }

		
		-- 1.3.6.1.4.1.6296.101.20.13.2.2.23
		sleEponRuleActionControlTosOperate OBJECT-TYPE
			SYNTAX INTEGER
				{
				tos(1),
				tosClear(2)
				}
			MAX-ACCESS read-write
			STATUS current
			DESCRIPTION
				"tos operate."
			::= { sleEponRuleActionControl 23 }

		
		-- 1.3.6.1.4.1.6296.101.20.13.2.2.24
		sleEponRuleActionControlTosValue OBJECT-TYPE
			SYNTAX Integer32
			MAX-ACCESS read-write
			STATUS current
			DESCRIPTION
				"tos value."
			::= { sleEponRuleActionControl 24 }

		
		-- 1.3.6.1.4.1.6296.101.20.13.2.2.25
		sleEponRuleActionControlOutputOperate OBJECT-TYPE
			SYNTAX INTEGER
				{
				and(1),
				or(2),
				set(3),
				add(4),
				copy(5)
				}
			MAX-ACCESS read-write
			STATUS current
			DESCRIPTION
				"Rule action output on the selected field
				1.and,Perform a binary AND on the selected field
				2.or,Perform a binary OR on the selected field
				3.set,Set the selected field
				4.add,Add the selected field
				5.copy,Copy the selected field from another field.
				"
			::= { sleEponRuleActionControl 25 }

		
		-- 1.3.6.1.4.1.6296.101.20.13.2.2.26
		sleEponRuleActionControlOutputValue OBJECT-TYPE
			SYNTAX Integer32
			MAX-ACCESS read-write
			STATUS current
			DESCRIPTION
				"output value."
			::= { sleEponRuleActionControl 26 }

		
		-- 1.3.6.1.4.1.6296.101.20.13.2.2.27
		sleEponRuleActionControlOutputVlanContent OBJECT-TYPE
			SYNTAX INTEGER (0..8)
			MAX-ACCESS read-write
			STATUS current
			DESCRIPTION
				"0-3 vlan0 4-7 vlan1(0-TPID 1-CoS 2-VID 3-CoS and VID 4-TPID 5-CoS 6-VID 7-CoS and VID 8-IPv4 ToS."
			::= { sleEponRuleActionControl 27 }

		
		-- 1.3.6.1.4.1.6296.101.20.13.2.2.28
		sleEponRuleActionControlOutputSourceFiledCopy OBJECT-TYPE
			SYNTAX Integer32 (1..25)
			MAX-ACCESS read-write
			STATUS current
			DESCRIPTION
				"Source field for the copy."
			::= { sleEponRuleActionControl 28 }

		
		-- 1.3.6.1.4.1.6296.101.20.13.2.3
		sleEponRuleActionNotification OBJECT IDENTIFIER ::= { sleEponRuleAction 3 }

		
		-- 1.3.6.1.4.1.6296.101.20.13.2.3.1
		sleEponRuleActionVlanChanged NOTIFICATION-TYPE
			OBJECTS { sleEponRuleActionControlRequest, sleEponRuleActionControlTimeStamp, sleEponRuleActionControlReqResult, sleEponRuleActionControlIndex, sleEponRuleActionControlVlanOperate, 
				sleEponRuleActionControlVlanMap, sleEponRuleActionControlEtherType, sleEponRuleActionControlVlanID }
			STATUS current
			DESCRIPTION 
				"Description."
			::= { sleEponRuleActionNotification 1 }

		
		-- 1.3.6.1.4.1.6296.101.20.13.2.3.2
		sleEponRuleActionDiscardChanged NOTIFICATION-TYPE
			OBJECTS { sleEponRuleActionControlRequest, sleEponRuleActionControlTimeStamp, sleEponRuleActionControlReqResult, sleEponRuleActionControlIndex, sleEponRuleActionControlDiscardOperate, 
				sleEponRuleActionControlDiscardOperateValue }
			STATUS current
			DESCRIPTION 
				"Description."
			::= { sleEponRuleActionNotification 2 }

		
		-- 1.3.6.1.4.1.6296.101.20.13.2.3.3
		sleEponRuleActionCaptureHostChanged NOTIFICATION-TYPE
			OBJECTS { sleEponRuleActionControlRequest, sleEponRuleActionControlTimeStamp, sleEponRuleActionControlReqResult, sleEponRuleActionControlIndex, sleEponRuleActionControlCaptureHostOperate
				 }
			STATUS current
			DESCRIPTION 
				"Description."
			::= { sleEponRuleActionNotification 3 }

		
		-- 1.3.6.1.4.1.6296.101.20.13.2.3.4
		sleEponRuleActionCaptureHostFlexibleChanged NOTIFICATION-TYPE
			OBJECTS { sleEponRuleActionControlRequest, sleEponRuleActionControlTimeStamp, sleEponRuleActionControlReqResult, sleEponRuleActionControlIndex, sleEponRuleActionControlCaptureHostFlexibleOperate
				 }
			STATUS current
			DESCRIPTION 
				"Description."
			::= { sleEponRuleActionNotification 4 }

		
		-- 1.3.6.1.4.1.6296.101.20.13.2.3.5
		sleEponRuleActionQueueChanged NOTIFICATION-TYPE
			OBJECTS { sleEponRuleActionControlRequest, sleEponRuleActionControlTimeStamp, sleEponRuleActionControlReqResult, sleEponRuleActionControlIndex, sleEponRuleActionControlQueueId
				 }
			STATUS current
			DESCRIPTION 
				"Description."
			::= { sleEponRuleActionNotification 5 }

		
		-- 1.3.6.1.4.1.6296.101.20.13.2.3.6
		sleEponRuleActionUnicastLinkChanged NOTIFICATION-TYPE
			OBJECTS { sleEponRuleActionControlRequest, sleEponRuleActionControlTimeStamp, sleEponRuleActionControlReqResult, sleEponRuleActionControlIndex, sleEponRuleActionControlUnicastLinkDestID, 
				sleEponRuleActionControlUnicastLinkDestOffset }
			STATUS current
			DESCRIPTION 
				"Description."
			::= { sleEponRuleActionNotification 6 }

		
		-- 1.3.6.1.4.1.6296.101.20.13.2.3.7
		sleEponRuleActionMulticastLinkChanged NOTIFICATION-TYPE
			OBJECTS { sleEponRuleActionControlRequest, sleEponRuleActionControlTimeStamp, sleEponRuleActionControlReqResult, sleEponRuleActionControlMulticastLinkDomID, sleEponRuleActionControlMulticastLinkDomOffset
				 }
			STATUS current
			DESCRIPTION 
				"Description."
			::= { sleEponRuleActionNotification 7 }

		
		-- 1.3.6.1.4.1.6296.101.20.13.2.3.8
		sleEponRuleActionNoOperation NOTIFICATION-TYPE
			OBJECTS { sleEponRuleActionControlRequest, sleEponRuleActionControlTimeStamp, sleEponRuleActionControlReqResult, sleEponRuleActionControlIndex }
			STATUS current
			DESCRIPTION 
				"Description."
			::= { sleEponRuleActionNotification 8 }

		
		-- 1.3.6.1.4.1.6296.101.20.13.2.3.9
		sleEponRuleActionCosChanged NOTIFICATION-TYPE
			OBJECTS { sleEponRuleActionControlRequest, sleEponRuleActionControlTimeStamp, sleEponRuleActionControlReqResult, sleEponRuleActionControlIndex, sleEponRuleActionControlCosOperate, 
				sleEponRuleActionControlCosValue }
			STATUS current
			DESCRIPTION 
				"Description."
			::= { sleEponRuleActionNotification 9 }

		
		-- 1.3.6.1.4.1.6296.101.20.13.2.3.10
		sleEponRuleActionTosChanged NOTIFICATION-TYPE
			OBJECTS { sleEponRuleActionControlRequest, sleEponRuleActionControlTimeStamp, sleEponRuleActionControlReqResult, sleEponRuleActionControlIndex, sleEponRuleActionControlTosOperate, 
				sleEponRuleActionControlTosValue }
			STATUS current
			DESCRIPTION 
				"Description."
			::= { sleEponRuleActionNotification 10 }

		
		-- 1.3.6.1.4.1.6296.101.20.13.2.3.11
		sleEponRuleActionOutputChanged NOTIFICATION-TYPE
			OBJECTS { sleEponRuleActionControlRequest, sleEponRuleActionControlTimeStamp, sleEponRuleActionControlReqResult, sleEponRuleActionControlIndex, sleEponRuleActionControlOutputOperate, 
				sleEponRuleActionControlOutputValue, sleEponRuleActionControlOutputSourceFiledCopy }
			STATUS current
			DESCRIPTION 
				"Description."
			::= { sleEponRuleActionNotification 11 }

		
		-- 1.3.6.1.4.1.6296.101.20.13.2.3.12
		sleEponRuleActionQueuePendingChanged NOTIFICATION-TYPE
			OBJECTS { sleEponRuleActionControlRequest, sleEponRuleActionControlTimeStamp, sleEponRuleActionControlReqResult, sleEponRuleActionControlQueueId }
			STATUS current
			DESCRIPTION 
				"Description."
			::= { sleEponRuleActionNotification 12 }

		
		-- 1.3.6.1.4.1.6296.101.20.13.2.3.13
		sleEponRuleActionSleChanged NOTIFICATION-TYPE
			OBJECTS { sleEponRuleActionControlRequest, sleEponRuleActionControlTimeStamp, sleEponRuleActionControlReqResult, sleEponRuleActionControlIndex }
			STATUS current
			DESCRIPTION 
				"Description."
			::= { sleEponRuleActionNotification 13 }

		
		-- 1.3.6.1.4.1.6296.101.20.13.2.3.14
		sleEponRuleActionNoRuleAction NOTIFICATION-TYPE
			OBJECTS { sleEponProfilePortControlRequest, sleEponRuleActionControlRequest, sleEponRuleActionControlTimeStamp, sleEponRuleActionControlReqResult, sleEponRuleActionControlIndex
				 }
			STATUS current
			DESCRIPTION 
				"Description."
			::= { sleEponRuleActionNotification 14 }

		
		-- 1.3.6.1.4.1.6296.101.20.13.3
		sleEponRuleModify OBJECT IDENTIFIER ::= { sleEponRule 3 }

		
		-- 1.3.6.1.4.1.6296.101.20.13.3.1
		sleEponRuleModifyTable OBJECT-TYPE
			SYNTAX SEQUENCE OF SleEponRuleModifyEntry
			MAX-ACCESS not-accessible
			STATUS current
			DESCRIPTION
				"Description."
			::= { sleEponRuleModify 1 }

		
		-- 1.3.6.1.4.1.6296.101.20.13.3.1.1
		sleEponRuleModifyEntry OBJECT-TYPE
			SYNTAX SleEponRuleModifyEntry
			MAX-ACCESS not-accessible
			STATUS current
			DESCRIPTION
				"Description."
			INDEX { sleEponOltIndex }
			::= { sleEponRuleModifyTable 1 }

		
		SleEponRuleModifyEntry ::=
			SEQUENCE { 
				sleEponRuleModifyRuleName
					OCTET STRING,
				sleEponRuleModifyTrafficDirection
					INTEGER,
				sleEponRuleModifyPriorityValue
					INTEGER,
				sleEponRuleModifyCIndex
					OCTET STRING,
				sleEponRuleModifyAIndex
					OCTET STRING
			 }

		-- 1.3.6.1.4.1.6296.101.20.13.3.1.1.1
		sleEponRuleModifyRuleName OBJECT-TYPE
			SYNTAX OCTET STRING
			MAX-ACCESS read-only
			STATUS current
			DESCRIPTION
				"Pon rule name."
			::= { sleEponRuleModifyEntry 1 }

		
		-- 1.3.6.1.4.1.6296.101.20.13.3.1.1.2
		sleEponRuleModifyTrafficDirection OBJECT-TYPE
			SYNTAX INTEGER
				{
				downstream(1),
				upstream(2)
				}
			MAX-ACCESS read-only
			STATUS current
			DESCRIPTION
				"The traffic direction of Rule .
				"
			::= { sleEponRuleModifyEntry 2 }

		
		-- 1.3.6.1.4.1.6296.101.20.13.3.1.1.3
		sleEponRuleModifyPriorityValue OBJECT-TYPE
			SYNTAX INTEGER (0..15)
			MAX-ACCESS read-only
			STATUS current
			DESCRIPTION
				"Priority Value."
			::= { sleEponRuleModifyEntry 3 }

		
		-- 1.3.6.1.4.1.6296.101.20.13.3.1.1.4
		sleEponRuleModifyCIndex OBJECT-TYPE
			SYNTAX OCTET STRING
			MAX-ACCESS read-only
			STATUS current
			DESCRIPTION
				"Rule clause index."
			::= { sleEponRuleModifyEntry 4 }

		
		-- 1.3.6.1.4.1.6296.101.20.13.3.1.1.5
		sleEponRuleModifyAIndex OBJECT-TYPE
			SYNTAX OCTET STRING
			MAX-ACCESS read-only
			STATUS current
			DESCRIPTION
				"Rule action index."
			::= { sleEponRuleModifyEntry 5 }

		
		-- 1.3.6.1.4.1.6296.101.20.13.3.2
		sleEponRuleModifyControl OBJECT IDENTIFIER ::= { sleEponRuleModify 2 }

		
		-- 1.3.6.1.4.1.6296.101.20.13.3.2.1
		sleEponRuleModifyControlRequest OBJECT-TYPE
			SYNTAX INTEGER
				{
				ponRuleCreate(1),
				ponRuleModifyPriority(2),
				ponRuleModifyTrafficDir(3),
				ponRuleModifyClauseAdd(4),
				ponRuleModifyActionAdd(5),
				ponRuleModifyClauseDel(6),
				ponRuleModifyActionDel(7),
				noPonRule(8),
				oltRuleAddApply(9),
				oltRuleDelApply(10)
				}
			MAX-ACCESS read-write
			STATUS current
			DESCRIPTION
				"The request of a user command."
			::= { sleEponRuleModifyControl 1 }

		
		-- 1.3.6.1.4.1.6296.101.20.13.3.2.2
		sleEponRuleModifyControlStatus OBJECT-TYPE
			SYNTAX SleControlStatusType
			MAX-ACCESS read-only
			STATUS current
			DESCRIPTION
				"The status of user command"
			::= { sleEponRuleModifyControl 2 }

		
		-- 1.3.6.1.4.1.6296.101.20.13.3.2.3
		sleEponRuleModifyControlTimer OBJECT-TYPE
			SYNTAX Gauge32
			MAX-ACCESS read-write
			STATUS current
			DESCRIPTION
				"The maximum time for the manager for a long running user command"
			::= { sleEponRuleModifyControl 3 }

		
		-- 1.3.6.1.4.1.6296.101.20.13.3.2.4
		sleEponRuleModifyControlTimeStamp OBJECT-TYPE
			SYNTAX TimeTicks
			MAX-ACCESS read-only
			STATUS current
			DESCRIPTION
				"The time stamp of the last command(end of command)"
			::= { sleEponRuleModifyControl 4 }

		
		-- 1.3.6.1.4.1.6296.101.20.13.3.2.5
		sleEponRuleModifyControlReqResult OBJECT-TYPE
			SYNTAX SleControlRequestResultType
			MAX-ACCESS read-only
			STATUS current
			DESCRIPTION
				"The result of the last user command"
			::= { sleEponRuleModifyControl 5 }

		
		-- 1.3.6.1.4.1.6296.101.20.13.3.2.6
		sleEponRuleModifyControlOltId OBJECT-TYPE
			SYNTAX INTEGER (1..24)
			MAX-ACCESS read-write
			STATUS current
			DESCRIPTION
				"Olt index."
			::= { sleEponRuleModifyControl 6 }

		
		-- 1.3.6.1.4.1.6296.101.20.13.3.2.7
		sleEponRuleModifyControlRuleName OBJECT-TYPE
			SYNTAX OCTET STRING
			MAX-ACCESS read-write
			STATUS current
			DESCRIPTION
				"Pon rule name."
			::= { sleEponRuleModifyControl 7 }

		
		-- 1.3.6.1.4.1.6296.101.20.13.3.2.8
		sleEponRuleModifyControlTrafficDirection OBJECT-TYPE
			SYNTAX INTEGER
				{
				downstream(1),
				upstream(2)
				}
			MAX-ACCESS read-write
			STATUS current
			DESCRIPTION
				"The traffic direction of Rule .
				"
			::= { sleEponRuleModifyControl 8 }

		
		-- 1.3.6.1.4.1.6296.101.20.13.3.2.9
		sleEponRuleModifyControlPriorityValue OBJECT-TYPE
			SYNTAX INTEGER (0..15)
			MAX-ACCESS read-write
			STATUS current
			DESCRIPTION
				"Priority Value."
			::= { sleEponRuleModifyControl 9 }

		
		-- 1.3.6.1.4.1.6296.101.20.13.3.2.10
		sleEponRuleModifyControlCIndex OBJECT-TYPE
			SYNTAX INTEGER (1..8)
			MAX-ACCESS read-write
			STATUS current
			DESCRIPTION
				"Rule clause index."
			::= { sleEponRuleModifyControl 10 }

		
		-- 1.3.6.1.4.1.6296.101.20.13.3.2.11
		sleEponRuleModifyControlAIndex OBJECT-TYPE
			SYNTAX INTEGER (1..8)
			MAX-ACCESS read-write
			STATUS current
			DESCRIPTION
				"Rule action index."
			::= { sleEponRuleModifyControl 11 }

		
		-- 1.3.6.1.4.1.6296.101.20.13.3.3
		sleEponRuleModifyNotification OBJECT IDENTIFIER ::= { sleEponRuleModify 3 }

		
		-- 1.3.6.1.4.1.6296.101.20.13.3.3.1
		sleEponRuleOltRuleCreate NOTIFICATION-TYPE
			OBJECTS { sleEponRuleModifyControlRequest, sleEponRuleModifyControlTimeStamp, sleEponRuleModifyControlReqResult, sleEponRuleModifyControlRuleName, sleEponRuleModifyControlPriorityValue, 
				sleEponRuleModifyControlCIndex, sleEponRuleModifyControlAIndex }
			STATUS current
			DESCRIPTION 
				"Description."
			::= { sleEponRuleModifyNotification 1 }

		
		-- 1.3.6.1.4.1.6296.101.20.13.3.3.2
		sleEponRuleModifyPriorityChange NOTIFICATION-TYPE
			OBJECTS { sleEponRuleModifyControlRequest, sleEponRuleModifyControlTimeStamp, sleEponRuleModifyControlReqResult, sleEponRuleModifyControlRuleName, sleEponRuleModifyControlPriorityValue, 
				sleEponRuleModifyControlTrafficDirection }
			STATUS current
			DESCRIPTION 
				"Description."
			::= { sleEponRuleModifyNotification 2 }

		
		-- 1.3.6.1.4.1.6296.101.20.13.3.3.3
		sleEponRuleModifyTrafficDirChange NOTIFICATION-TYPE
			OBJECTS { sleEponRuleModifyControlRequest, sleEponRuleModifyControlTimeStamp, sleEponRuleModifyControlReqResult, sleEponRuleModifyControlRuleName, sleEponRuleModifyControlPriorityValue, 
				sleEponRuleModifyControlTrafficDirection }
			STATUS current
			DESCRIPTION 
				"Description."
			::= { sleEponRuleModifyNotification 3 }

		
		-- 1.3.6.1.4.1.6296.101.20.13.3.3.4
		sleEponRuleModifyClauseAdd NOTIFICATION-TYPE
			OBJECTS { sleEponRuleModifyControlRequest, sleEponRuleModifyControlTimeStamp, sleEponRuleModifyControlReqResult, sleEponRuleModifyControlRuleName, sleEponRuleModifyControlCIndex, 
				sleEponRuleModifyControlAIndex }
			STATUS current
			DESCRIPTION 
				"Description."
			::= { sleEponRuleModifyNotification 4 }

		
		-- 1.3.6.1.4.1.6296.101.20.13.3.3.5
		sleEponRuleModifyActionAdd NOTIFICATION-TYPE
			OBJECTS { sleEponRuleModifyControlRequest, sleEponRuleModifyControlTimeStamp, sleEponRuleModifyControlReqResult, sleEponRuleModifyControlRuleName, sleEponRuleModifyControlCIndex, 
				sleEponRuleModifyControlAIndex }
			STATUS current
			DESCRIPTION 
				"Description."
			::= { sleEponRuleModifyNotification 5 }

		
		-- 1.3.6.1.4.1.6296.101.20.13.3.3.6
		sleEponRuleModifyClauseDel NOTIFICATION-TYPE
			OBJECTS { sleEponRuleModifyControlRequest, sleEponRuleModifyControlTimeStamp, sleEponRuleModifyControlReqResult, sleEponRuleModifyControlRuleName, sleEponRuleModifyControlCIndex, 
				sleEponRuleModifyControlAIndex }
			STATUS current
			DESCRIPTION 
				"Description."
			::= { sleEponRuleModifyNotification 6 }

		
		-- 1.3.6.1.4.1.6296.101.20.13.3.3.7
		sleEponRuleModifyActionDel NOTIFICATION-TYPE
			OBJECTS { sleEponRuleModifyControlRequest, sleEponRuleModifyControlTimeStamp, sleEponRuleModifyControlReqResult, sleEponRuleModifyControlRuleName, sleEponRuleModifyControlCIndex, 
				sleEponRuleModifyControlAIndex }
			STATUS current
			DESCRIPTION 
				"Description."
			::= { sleEponRuleModifyNotification 7 }

		
		-- 1.3.6.1.4.1.6296.101.20.13.3.3.8
		sleEponRuleOltRuleDelete NOTIFICATION-TYPE
			OBJECTS { sleEponRuleModifyControlRequest, sleEponRuleModifyControlReqResult, sleEponRuleModifyControlOltId, sleEponRuleModifyControlTimeStamp, sleEponRuleModifyControlRuleName
				 }
			STATUS current
			DESCRIPTION 
				"Description."
			::= { sleEponRuleModifyNotification 8 }

		
		-- 1.3.6.1.4.1.6296.101.20.13.3.3.9
		sleEponRuleOltRuleAddApply NOTIFICATION-TYPE
			OBJECTS { sleEponRuleModifyControlRequest, sleEponRuleModifyControlTimeStamp, sleEponRuleModifyControlReqResult, sleEponRuleModifyControlOltId, sleEponRuleModifyControlRuleName
				 }
			STATUS current
			DESCRIPTION 
				"Description."
			::= { sleEponRuleModifyNotification 9 }

		
		-- 1.3.6.1.4.1.6296.101.20.13.3.3.10
		sleEponRuleOltRuleDelApply NOTIFICATION-TYPE
			OBJECTS { sleEponRuleModifyControlRequest, sleEponRuleModifyControlTimeStamp, sleEponRuleModifyControlReqResult, sleEponRuleModifyControlOltId, sleEponRuleModifyControlRuleName
				 }
			STATUS current
			DESCRIPTION 
				"Description."
			::= { sleEponRuleModifyNotification 10 }

		
		-- 1.3.6.1.4.1.6296.101.20.13.4
		sleEponOnuRule OBJECT IDENTIFIER ::= { sleEponRule 4 }

		
		-- 1.3.6.1.4.1.6296.101.20.13.4.1
		sleEponOnuRuleTable OBJECT-TYPE
			SYNTAX SEQUENCE OF SleEponOnuRuleEntry
			MAX-ACCESS not-accessible
			STATUS current
			DESCRIPTION
				"Description."
			::= { sleEponOnuRule 1 }

		
		-- 1.3.6.1.4.1.6296.101.20.13.4.1.1
		sleEponOnuRuleEntry OBJECT-TYPE
			SYNTAX SleEponOnuRuleEntry
			MAX-ACCESS not-accessible
			STATUS current
			DESCRIPTION
				"Epon onu rule table."
			INDEX { sleEponOnuRuleIndex }
			::= { sleEponOnuRuleTable 1 }

		
		SleEponOnuRuleEntry ::=
			SEQUENCE { 
				sleEponOnuRuleName
					OCTET STRING,
				sleEponOnuRuleIndex
					Integer32,
				sleEponOnuRuleDirection
					INTEGER,
				sleEponOnuRulePriority
					Integer32,
				sleEponOnuRuleDscp
					OCTET STRING,
				sleEponOnuRuleLinkIndex
					INTEGER,
				sleEponOnuRuleQueueIndex
					INTEGER
			 }

		-- 1.3.6.1.4.1.6296.101.20.13.4.1.1.1
		sleEponOnuRuleName OBJECT-TYPE
			SYNTAX OCTET STRING
			MAX-ACCESS read-only
			STATUS current
			DESCRIPTION
				"Epon onu rule name."
			::= { sleEponOnuRuleEntry 1 }

		
		-- 1.3.6.1.4.1.6296.101.20.13.4.1.1.2
		sleEponOnuRuleIndex OBJECT-TYPE
			SYNTAX Integer32 (1..512)
			MAX-ACCESS read-only
			STATUS current
			DESCRIPTION
				"Rule Index"
			::= { sleEponOnuRuleEntry 2 }

		
		-- 1.3.6.1.4.1.6296.101.20.13.4.1.1.3
		sleEponOnuRuleDirection OBJECT-TYPE
			SYNTAX INTEGER
				{
				dowbStream(1),
				upStream(2)
				}
			MAX-ACCESS read-only
			STATUS current
			DESCRIPTION
				"Traffic direction."
			::= { sleEponOnuRuleEntry 3 }

		
		-- 1.3.6.1.4.1.6296.101.20.13.4.1.1.4
		sleEponOnuRulePriority OBJECT-TYPE
			SYNTAX Integer32
			MAX-ACCESS read-only
			STATUS current
			DESCRIPTION
				"Priority."
			::= { sleEponOnuRuleEntry 4 }

		
		-- 1.3.6.1.4.1.6296.101.20.13.4.1.1.5
		sleEponOnuRuleDscp OBJECT-TYPE
			SYNTAX OCTET STRING
			MAX-ACCESS read-write
			STATUS current
			DESCRIPTION
				"Epon onu rule dscp."
			::= { sleEponOnuRuleEntry 5 }

		
		-- 1.3.6.1.4.1.6296.101.20.13.4.1.1.6
		sleEponOnuRuleLinkIndex OBJECT-TYPE
			SYNTAX INTEGER (0..1)
			MAX-ACCESS read-write
			STATUS current
			DESCRIPTION
				"Epon onu rule link index."
			::= { sleEponOnuRuleEntry 6 }

		
		-- 1.3.6.1.4.1.6296.101.20.13.4.1.1.7
		sleEponOnuRuleQueueIndex OBJECT-TYPE
			SYNTAX INTEGER (0..3)
			MAX-ACCESS read-write
			STATUS current
			DESCRIPTION
				"Epon onu rule queue index"
			::= { sleEponOnuRuleEntry 7 }

		
		-- 1.3.6.1.4.1.6296.101.20.13.4.2
		sleEponOnuRuleControl OBJECT IDENTIFIER ::= { sleEponOnuRule 2 }

		
		-- 1.3.6.1.4.1.6296.101.20.13.4.2.1
		sleEponOnuRuleControlRequest OBJECT-TYPE
			SYNTAX INTEGER
				{
				createOnuRule(1),
				deleteOnuRule(2)
				}
			MAX-ACCESS read-write
			STATUS current
			DESCRIPTION
				"The request of a user command."
			::= { sleEponOnuRuleControl 1 }

		
		-- 1.3.6.1.4.1.6296.101.20.13.4.2.2
		sleEponOnuRuleControlStatus OBJECT-TYPE
			SYNTAX SleControlStatusType
			MAX-ACCESS read-only
			STATUS current
			DESCRIPTION
				"The status of user command."
			::= { sleEponOnuRuleControl 2 }

		
		-- 1.3.6.1.4.1.6296.101.20.13.4.2.3
		sleEponOnuRuleControlTimer OBJECT-TYPE
			SYNTAX Gauge32
			MAX-ACCESS read-write
			STATUS current
			DESCRIPTION
				"The maximum time for the manager for a long running user command."
			::= { sleEponOnuRuleControl 3 }

		
		-- 1.3.6.1.4.1.6296.101.20.13.4.2.4
		sleEponOnuRuleControlTimeStamp OBJECT-TYPE
			SYNTAX TimeTicks
			MAX-ACCESS read-only
			STATUS current
			DESCRIPTION
				"The time stamp of the last command(end of command)."
			::= { sleEponOnuRuleControl 4 }

		
		-- 1.3.6.1.4.1.6296.101.20.13.4.2.5
		sleEponOnuRuleControlReqResult OBJECT-TYPE
			SYNTAX SleControlRequestResultType
			MAX-ACCESS read-only
			STATUS current
			DESCRIPTION
				"The result of the last user command."
			::= { sleEponOnuRuleControl 5 }

		
		-- 1.3.6.1.4.1.6296.101.20.13.4.2.6
		sleEponOnuRuleControlRuleName OBJECT-TYPE
			SYNTAX OCTET STRING
			MAX-ACCESS read-write
			STATUS current
			DESCRIPTION
				"Epon onu rule name."
			::= { sleEponOnuRuleControl 6 }

		
		-- 1.3.6.1.4.1.6296.101.20.13.4.2.7
		sleEponOnuRuleControlDscp OBJECT-TYPE
			SYNTAX INTEGER
				{
				cs01(1),
				cs23(2),
				cs45(3),
				cs67(4)
				}
			MAX-ACCESS read-write
			STATUS current
			DESCRIPTION
				"Epon onu rule dscp."
			::= { sleEponOnuRuleControl 7 }

		
		-- 1.3.6.1.4.1.6296.101.20.13.4.2.8
		sleEponOnuRuleControlLinkIndex OBJECT-TYPE
			SYNTAX INTEGER (0..1)
			MAX-ACCESS read-write
			STATUS current
			DESCRIPTION
				"Epon onu rule link index."
			::= { sleEponOnuRuleControl 8 }

		
		-- 1.3.6.1.4.1.6296.101.20.13.4.2.9
		sleEponOnuRuleControlQueueIndex OBJECT-TYPE
			SYNTAX INTEGER (0..3)
			MAX-ACCESS read-write
			STATUS current
			DESCRIPTION
				"Epon onu rule queue index"
			::= { sleEponOnuRuleControl 9 }

		
		-- 1.3.6.1.4.1.6296.101.20.13.4.3
		sleEponOnuRuleNotification OBJECT IDENTIFIER ::= { sleEponOnuRule 3 }

		
		-- 1.3.6.1.4.1.6296.101.20.13.4.3.1
		sleEponOnuRuleChanged NOTIFICATION-TYPE
			OBJECTS { sleEponOnuRuleControlRequest, sleEponOnuRuleControlTimeStamp, sleEponOnuRuleControlReqResult, sleEponOnuRuleControlRuleName }
			STATUS current
			DESCRIPTION 
				"Trap of create or delete onu rule."
			::= { sleEponOnuRuleNotification 1 }

		
		-- 1.3.6.1.4.1.6296.101.20.14
		sleEponDBA OBJECT IDENTIFIER ::= { sleEpon 14 }

		
		-- 1.3.6.1.4.1.6296.101.20.14.1
		sleEponOltDBA OBJECT IDENTIFIER ::= { sleEponDBA 1 }

		
		-- 1.3.6.1.4.1.6296.101.20.14.1.1
		sleEponOltDBATable OBJECT-TYPE
			SYNTAX SEQUENCE OF SleEponOltDBAEntry
			MAX-ACCESS not-accessible
			STATUS current
			DESCRIPTION
				"Description."
			::= { sleEponOltDBA 1 }

		
		-- 1.3.6.1.4.1.6296.101.20.14.1.1.1
		sleEponOltDBAEntry OBJECT-TYPE
			SYNTAX SleEponOltDBAEntry
			MAX-ACCESS not-accessible
			STATUS current
			DESCRIPTION
				"Description."
			INDEX { sleEponOltIndex }
			::= { sleEponOltDBATable 1 }

		
		SleEponOltDBAEntry ::=
			SEQUENCE { 
				sleEponOltDBAGlobalOltLinkOperate
					INTEGER,
				sleEponOltDBAOverGrantMonConfMonitoringInterval
					INTEGER,
				sleEponOltDBAOverGrantMonConfMaxDBAGrantSize
					INTEGER,
				sleEponOltDBAOverGrantMonConfMinGrantUtilization
					INTEGER,
				sleEponOltDBAOverGrantMonConfLeakyBucketCounterValue
					INTEGER,
				sleEponOltDBAMinShaperBandwidth
					INTEGER,
				sleEponOltDBAMinShaperBurstSize
					INTEGER,
				sleEponOltDBAMinShaperScheduleLevel
					INTEGER,
				sleEponOltDBAMinShaperWeight
					INTEGER,
				sleEponOltDBAMaxShaperBandwidth
					INTEGER,
				sleEponOltDBAMaxShaperBurstSize
					INTEGER,
				sleEponOltDBAMaxShaperScheduleLevel
					INTEGER,
				sleEponOltDBAMaxShaperWeight
					INTEGER
			 }

		-- 1.3.6.1.4.1.6296.101.20.14.1.1.1.1
		sleEponOltDBAGlobalOltLinkOperate OBJECT-TYPE
			SYNTAX INTEGER
				{
				disable(0),
				enable(1)
				}
			MAX-ACCESS read-only
			STATUS current
			DESCRIPTION
				"Global olt link options.
				enable
				disable"
			::= { sleEponOltDBAEntry 1 }

		
		-- 1.3.6.1.4.1.6296.101.20.14.1.1.1.2
		sleEponOltDBAOverGrantMonConfMonitoringInterval OBJECT-TYPE
			SYNTAX INTEGER (50..65535)
			MAX-ACCESS read-only
			STATUS current
			DESCRIPTION
				"Monitoring Interval."
			::= { sleEponOltDBAEntry 2 }

		
		-- 1.3.6.1.4.1.6296.101.20.14.1.1.1.3
		sleEponOltDBAOverGrantMonConfMaxDBAGrantSize OBJECT-TYPE
			SYNTAX INTEGER (0..65535)
			MAX-ACCESS read-only
			STATUS current
			DESCRIPTION
				"Maximum DBA grant size."
			::= { sleEponOltDBAEntry 3 }

		
		-- 1.3.6.1.4.1.6296.101.20.14.1.1.1.4
		sleEponOltDBAOverGrantMonConfMinGrantUtilization OBJECT-TYPE
			SYNTAX INTEGER (0..255)
			MAX-ACCESS read-only
			STATUS current
			DESCRIPTION
				"Minimum grant utilization."
			::= { sleEponOltDBAEntry 4 }

		
		-- 1.3.6.1.4.1.6296.101.20.14.1.1.1.5
		sleEponOltDBAOverGrantMonConfLeakyBucketCounterValue OBJECT-TYPE
			SYNTAX INTEGER (0..255)
			MAX-ACCESS read-only
			STATUS current
			DESCRIPTION
				"Leaky bucket counter value."
			::= { sleEponOltDBAEntry 5 }

		
		-- 1.3.6.1.4.1.6296.101.20.14.1.1.1.6
		sleEponOltDBAMinShaperBandwidth OBJECT-TYPE
			SYNTAX INTEGER (256..1000000)
			MAX-ACCESS read-only
			STATUS current
			DESCRIPTION
				"min shaper bandwidth"
			::= { sleEponOltDBAEntry 6 }

		
		-- 1.3.6.1.4.1.6296.101.20.14.1.1.1.7
		sleEponOltDBAMinShaperBurstSize OBJECT-TYPE
			SYNTAX INTEGER (1..256)
			MAX-ACCESS read-only
			STATUS current
			DESCRIPTION
				"min shaper burst size"
			::= { sleEponOltDBAEntry 7 }

		
		-- 1.3.6.1.4.1.6296.101.20.14.1.1.1.8
		sleEponOltDBAMinShaperScheduleLevel OBJECT-TYPE
			SYNTAX INTEGER (0..7)
			MAX-ACCESS read-only
			STATUS current
			DESCRIPTION
				"min shaper schedule level"
			::= { sleEponOltDBAEntry 8 }

		
		-- 1.3.6.1.4.1.6296.101.20.14.1.1.1.9
		sleEponOltDBAMinShaperWeight OBJECT-TYPE
			SYNTAX INTEGER (2..32)
			MAX-ACCESS read-only
			STATUS current
			DESCRIPTION
				"Min shaper weight"
			::= { sleEponOltDBAEntry 9 }

		
		-- 1.3.6.1.4.1.6296.101.20.14.1.1.1.10
		sleEponOltDBAMaxShaperBandwidth OBJECT-TYPE
			SYNTAX INTEGER (256..1000000)
			MAX-ACCESS read-only
			STATUS current
			DESCRIPTION
				"max shaper bandwidth"
			::= { sleEponOltDBAEntry 10 }

		
		-- 1.3.6.1.4.1.6296.101.20.14.1.1.1.11
		sleEponOltDBAMaxShaperBurstSize OBJECT-TYPE
			SYNTAX INTEGER (1..256)
			MAX-ACCESS read-only
			STATUS current
			DESCRIPTION
				"max shaper burst size"
			::= { sleEponOltDBAEntry 11 }

		
		-- 1.3.6.1.4.1.6296.101.20.14.1.1.1.12
		sleEponOltDBAMaxShaperScheduleLevel OBJECT-TYPE
			SYNTAX INTEGER (0..7)
			MAX-ACCESS read-only
			STATUS current
			DESCRIPTION
				"max shaper schedule level"
			::= { sleEponOltDBAEntry 12 }

		
		-- 1.3.6.1.4.1.6296.101.20.14.1.1.1.13
		sleEponOltDBAMaxShaperWeight OBJECT-TYPE
			SYNTAX INTEGER (2..32)
			MAX-ACCESS read-only
			STATUS current
			DESCRIPTION
				"max shaper weight"
			::= { sleEponOltDBAEntry 13 }

		
		-- 1.3.6.1.4.1.6296.101.20.14.1.2
		sleEponOltDBAPollingRateTable OBJECT-TYPE
			SYNTAX SEQUENCE OF SleEponOltDBAPollingRateEntry
			MAX-ACCESS not-accessible
			STATUS current
			DESCRIPTION
				"olt dba polling rate table"
			::= { sleEponOltDBA 2 }

		
		-- 1.3.6.1.4.1.6296.101.20.14.1.2.1
		sleEponOltDBAPollingRateEntry OBJECT-TYPE
			SYNTAX SleEponOltDBAPollingRateEntry
			MAX-ACCESS not-accessible
			STATUS current
			DESCRIPTION
				"Description."
			INDEX { sleEponOltIndex, sleEponOltDBADBAPollingRateLevel }
			::= { sleEponOltDBAPollingRateTable 1 }

		
		SleEponOltDBAPollingRateEntry ::=
			SEQUENCE { 
				sleEponOltDBADBAPollingRateLevel
					INTEGER,
				sleEponOltDBADBAPollingRateRate
					INTEGER
			 }

		-- 1.3.6.1.4.1.6296.101.20.14.1.2.1.1
		sleEponOltDBADBAPollingRateLevel OBJECT-TYPE
			SYNTAX INTEGER (0..7)
			MAX-ACCESS read-only
			STATUS current
			DESCRIPTION
				"Polling rate level."
			::= { sleEponOltDBAPollingRateEntry 1 }

		
		-- 1.3.6.1.4.1.6296.101.20.14.1.2.1.2
		sleEponOltDBADBAPollingRateRate OBJECT-TYPE
			SYNTAX INTEGER (0..65535)
			MAX-ACCESS read-write
			STATUS current
			DESCRIPTION
				"Polling rate rate."
			::= { sleEponOltDBAPollingRateEntry 2 }

		
		-- 1.3.6.1.4.1.6296.101.20.14.1.3
		sleEponOltDBADropDownTable OBJECT-TYPE
			SYNTAX SEQUENCE OF SleEponOltDBADropDownEntry
			MAX-ACCESS not-accessible
			STATUS current
			DESCRIPTION
				"shaper drop down and  drop down"
			::= { sleEponOltDBA 3 }

		
		-- 1.3.6.1.4.1.6296.101.20.14.1.3.1
		sleEponOltDBADropDownEntry OBJECT-TYPE
			SYNTAX SleEponOltDBADropDownEntry
			MAX-ACCESS not-accessible
			STATUS current
			DESCRIPTION
				"Description."
			INDEX { sleEponOltIndex, eEponOltDBADropDownLevel }
			::= { sleEponOltDBADropDownTable 1 }

		
		SleEponOltDBADropDownEntry ::=
			SEQUENCE { 
				eEponOltDBADropDownLevel
					INTEGER,
				sleEponOltDBAShaDropDownWeights
					INTEGER,
				sleEponOltDBADropDownWeights
					Integer32
			 }

		-- 1.3.6.1.4.1.6296.101.20.14.1.3.1.1
		eEponOltDBADropDownLevel OBJECT-TYPE
			SYNTAX INTEGER (1..7)
			MAX-ACCESS read-only
			STATUS current
			DESCRIPTION
				"the level of shaper drop down and drop down weights "
			::= { sleEponOltDBADropDownEntry 1 }

		
		-- 1.3.6.1.4.1.6296.101.20.14.1.3.1.2
		sleEponOltDBAShaDropDownWeights OBJECT-TYPE
			SYNTAX INTEGER (0..256)
			MAX-ACCESS read-write
			STATUS current
			DESCRIPTION
				"Shaper drop down weights."
			::= { sleEponOltDBADropDownEntry 2 }

		
		-- 1.3.6.1.4.1.6296.101.20.14.1.3.1.3
		sleEponOltDBADropDownWeights OBJECT-TYPE
			SYNTAX Integer32
			MAX-ACCESS read-write
			STATUS current
			DESCRIPTION
				"Drop down weights."
			::= { sleEponOltDBADropDownEntry 3 }

		
		-- 1.3.6.1.4.1.6296.101.20.14.1.4
		sleEponOltDBAControl OBJECT IDENTIFIER ::= { sleEponOltDBA 4 }

		
		-- 1.3.6.1.4.1.6296.101.20.14.1.4.1
		sleEponOltDBAControlRequest OBJECT-TYPE
			SYNTAX INTEGER
				{
				setDBAPollingRate(1),
				setDBAShaperDropDownWeights(2),
				setDBADropDownWeights(3),
				setDBALinkEnable(4),
				setDBALinkDisable(5),
				setDBAGlobalOltLinkOptions(6),
				setDBALinkGrantMonConf(7),
				setDBAMultiQueueSla(8),
				noDBAMultiQueueSla(9)
				}
			MAX-ACCESS read-write
			STATUS current
			DESCRIPTION
				"The request of a user command."
			::= { sleEponOltDBAControl 1 }

		
		-- 1.3.6.1.4.1.6296.101.20.14.1.4.2
		sleEponOltDBAControlStatus OBJECT-TYPE
			SYNTAX SleControlStatusType
			MAX-ACCESS read-only
			STATUS current
			DESCRIPTION
				"The status of user command."
			::= { sleEponOltDBAControl 2 }

		
		-- 1.3.6.1.4.1.6296.101.20.14.1.4.3
		sleEponOltDBAControlTimer OBJECT-TYPE
			SYNTAX Gauge32
			MAX-ACCESS read-write
			STATUS current
			DESCRIPTION
				"The maximum time for the manager for a long running user command."
			::= { sleEponOltDBAControl 3 }

		
		-- 1.3.6.1.4.1.6296.101.20.14.1.4.4
		sleEponOltDBAControlTimeStamp OBJECT-TYPE
			SYNTAX TimeTicks
			MAX-ACCESS read-only
			STATUS current
			DESCRIPTION
				"The time stamp of the last command(end of command)."
			::= { sleEponOltDBAControl 4 }

		
		-- 1.3.6.1.4.1.6296.101.20.14.1.4.5
		sleEponOltDBAControlReqResult OBJECT-TYPE
			SYNTAX SleControlRequestResultType
			MAX-ACCESS read-only
			STATUS current
			DESCRIPTION
				"The result of the last user command."
			::= { sleEponOltDBAControl 5 }

		
		-- 1.3.6.1.4.1.6296.101.20.14.1.4.6
		sleEponOltDBAControlOltIndex OBJECT-TYPE
			SYNTAX INTEGER (1..32)
			MAX-ACCESS read-write
			STATUS current
			DESCRIPTION
				"Olt index."
			::= { sleEponOltDBAControl 6 }

		
		-- 1.3.6.1.4.1.6296.101.20.14.1.4.7
		sleEponOltDBAControlOnuIndex OBJECT-TYPE
			SYNTAX INTEGER (1..64)
			MAX-ACCESS read-write
			STATUS current
			DESCRIPTION
				"Onu index."
			::= { sleEponOltDBAControl 7 }

		
		-- 1.3.6.1.4.1.6296.101.20.14.1.4.8
		sleEponOltDBAControlDBAPollingRateLevel OBJECT-TYPE
			SYNTAX INTEGER (0..7)
			MAX-ACCESS read-write
			STATUS current
			DESCRIPTION
				"Polling rate level."
			::= { sleEponOltDBAControl 8 }

		
		-- 1.3.6.1.4.1.6296.101.20.14.1.4.9
		sleEponOltDBAControlDBAPollingRateRate OBJECT-TYPE
			SYNTAX INTEGER (0..65535)
			MAX-ACCESS read-write
			STATUS current
			DESCRIPTION
				"Polling rate."
			::= { sleEponOltDBAControl 9 }

		
		-- 1.3.6.1.4.1.6296.101.20.14.1.4.10
		sleEponOltDBAControlShaDropDownWeightsLevel OBJECT-TYPE
			SYNTAX INTEGER (1..7)
			MAX-ACCESS read-write
			STATUS current
			DESCRIPTION
				"Shaper dropdown weights level."
			::= { sleEponOltDBAControl 10 }

		
		-- 1.3.6.1.4.1.6296.101.20.14.1.4.11
		sleEponOltDBAControlShaDropDownWeights OBJECT-TYPE
			SYNTAX INTEGER (0..256)
			MAX-ACCESS read-write
			STATUS current
			DESCRIPTION
				"Shaper drop down weights."
			::= { sleEponOltDBAControl 11 }

		
		-- 1.3.6.1.4.1.6296.101.20.14.1.4.12
		sleEponOltDBAControlDropDownWeightsLevel OBJECT-TYPE
			SYNTAX INTEGER (1..7)
			MAX-ACCESS read-write
			STATUS current
			DESCRIPTION
				"Drop down weights level."
			::= { sleEponOltDBAControl 12 }

		
		-- 1.3.6.1.4.1.6296.101.20.14.1.4.13
		sleEponOltDBAControlDropDownWeightsl OBJECT-TYPE
			SYNTAX INTEGER (0..256)
			MAX-ACCESS read-write
			STATUS current
			DESCRIPTION
				"Drop down weights."
			::= { sleEponOltDBAControl 13 }

		
		-- 1.3.6.1.4.1.6296.101.20.14.1.4.14
		sleEponOltDBAControlGlobalOltLinkOperate OBJECT-TYPE
			SYNTAX INTEGER
				{
				disable(0),
				enable(1)
				}
			MAX-ACCESS read-write
			STATUS current
			DESCRIPTION
				"Global olt link options.
				enable
				disable"
			::= { sleEponOltDBAControl 14 }

		
		-- 1.3.6.1.4.1.6296.101.20.14.1.4.15
		sleEponOltDBAControlOverGrantMonConfMonitoringInterval OBJECT-TYPE
			SYNTAX INTEGER (50..65535)
			MAX-ACCESS read-write
			STATUS current
			DESCRIPTION
				"Monitoring Interval."
			::= { sleEponOltDBAControl 15 }

		
		-- 1.3.6.1.4.1.6296.101.20.14.1.4.16
		sleEponOltDBAControlOverGrantMonConfMaxDBAGrantSize OBJECT-TYPE
			SYNTAX INTEGER (0..65535)
			MAX-ACCESS read-write
			STATUS current
			DESCRIPTION
				"Maximum DBA grant size."
			::= { sleEponOltDBAControl 16 }

		
		-- 1.3.6.1.4.1.6296.101.20.14.1.4.17
		sleEponOltDBAControlOverGrantMonConfMinGrantUtilization OBJECT-TYPE
			SYNTAX INTEGER (0..255)
			MAX-ACCESS read-write
			STATUS current
			DESCRIPTION
				"Minimum grant utilization."
			::= { sleEponOltDBAControl 17 }

		
		-- 1.3.6.1.4.1.6296.101.20.14.1.4.18
		sleEponOltDBAControlOverGrantMonConfLeakyBucketCounterValue OBJECT-TYPE
			SYNTAX INTEGER (0..255)
			MAX-ACCESS read-write
			STATUS current
			DESCRIPTION
				"Leaky bucket counter value."
			::= { sleEponOltDBAControl 18 }

		
		-- 1.3.6.1.4.1.6296.101.20.14.1.4.19
		sleEponOltDBAControlMinShaperBandwidth OBJECT-TYPE
			SYNTAX INTEGER (256..1000000)
			MAX-ACCESS read-write
			STATUS current
			DESCRIPTION
				"min shaper bandwidth"
			::= { sleEponOltDBAControl 19 }

		
		-- 1.3.6.1.4.1.6296.101.20.14.1.4.20
		sleEponOltDBAControlMinShaperBurstSize OBJECT-TYPE
			SYNTAX INTEGER (1..256)
			MAX-ACCESS read-write
			STATUS current
			DESCRIPTION
				"min shaper burst size"
			::= { sleEponOltDBAControl 20 }

		
		-- 1.3.6.1.4.1.6296.101.20.14.1.4.21
		sleEponOltDBAControlMinShaperScheduleLevel OBJECT-TYPE
			SYNTAX INTEGER (0..7)
			MAX-ACCESS read-write
			STATUS current
			DESCRIPTION
				"min shaper schedule level"
			::= { sleEponOltDBAControl 21 }

		
		-- 1.3.6.1.4.1.6296.101.20.14.1.4.22
		sleEponOltDBAControlMinShaperWeight OBJECT-TYPE
			SYNTAX INTEGER (2..32)
			MAX-ACCESS read-write
			STATUS current
			DESCRIPTION
				"min shaper weight"
			::= { sleEponOltDBAControl 22 }

		
		-- 1.3.6.1.4.1.6296.101.20.14.1.4.23
		sleEponOltDBAControlMaxShaperBandwidth OBJECT-TYPE
			SYNTAX INTEGER (256..1000000)
			MAX-ACCESS read-write
			STATUS current
			DESCRIPTION
				"max shaper bandwidth"
			::= { sleEponOltDBAControl 23 }

		
		-- 1.3.6.1.4.1.6296.101.20.14.1.4.24
		sleEponOltDBAControlMaxShaperBurstSize OBJECT-TYPE
			SYNTAX INTEGER (1..256)
			MAX-ACCESS read-write
			STATUS current
			DESCRIPTION
				"max shaper burst size"
			::= { sleEponOltDBAControl 24 }

		
		-- 1.3.6.1.4.1.6296.101.20.14.1.4.25
		sleEponOltDBAControlMaxShaperScheduleLevel OBJECT-TYPE
			SYNTAX INTEGER (0..7)
			MAX-ACCESS read-write
			STATUS current
			DESCRIPTION
				"max shaper schedule level"
			::= { sleEponOltDBAControl 25 }

		
		-- 1.3.6.1.4.1.6296.101.20.14.1.4.26
		sleEponOltDBAControlMaxShaperWeight OBJECT-TYPE
			SYNTAX INTEGER (2..32)
			MAX-ACCESS read-write
			STATUS current
			DESCRIPTION
				"max shaper weight"
			::= { sleEponOltDBAControl 26 }

		
		-- 1.3.6.1.4.1.6296.101.20.14.1.5
		sleEponOltDBANotification OBJECT IDENTIFIER ::= { sleEponOltDBA 5 }

		
		-- 1.3.6.1.4.1.6296.101.20.14.1.5.1
		sleEponOLtDBAShaperDropDownWeightsChanged NOTIFICATION-TYPE
			OBJECTS { sleEponOltDBAControlRequest, sleEponOltDBAControlTimeStamp, sleEponOltDBAControlReqResult, sleEponOltDBAControlShaDropDownWeightsLevel, sleEponOltDBAControlShaDropDownWeights
				 }
			STATUS current
			DESCRIPTION 
				"Shaper drop down weights changed."
			::= { sleEponOltDBANotification 1 }

		
		-- 1.3.6.1.4.1.6296.101.20.14.1.5.2
		sleEponOLtDBADropDownWeightsChanged NOTIFICATION-TYPE
			OBJECTS { sleEponOltDBAControlRequest, sleEponOltDBAControlTimeStamp, sleEponOltDBAControlReqResult, sleEponOltDBAControlDropDownWeightsLevel, sleEponOltDBAControlDropDownWeightsl
				 }
			STATUS current
			DESCRIPTION 
				"DBA drop down weights changed."
			::= { sleEponOltDBANotification 2 }

		
		-- 1.3.6.1.4.1.6296.101.20.14.1.5.3
		sleEponOltDBALinkChanged NOTIFICATION-TYPE
			OBJECTS { sleEponOltDBAControlRequest, sleEponOltDBAControlTimeStamp, sleEponOltDBAControlReqResult }
			STATUS current
			DESCRIPTION 
				"DBA link state changed."
			::= { sleEponOltDBANotification 3 }

		
		-- 1.3.6.1.4.1.6296.101.20.14.1.5.4
		sleEponOLtDBADGlobalOltLinkChanged NOTIFICATION-TYPE
			OBJECTS { sleEponOltDBAControlRequest, sleEponOltDBAControlTimeStamp, sleEponOltDBAControlReqResult, sleEponOltDBAControlGlobalOltLinkOperate }
			STATUS current
			DESCRIPTION 
				"Global olt link state changed trap."
			::= { sleEponOltDBANotification 4 }

		
		-- 1.3.6.1.4.1.6296.101.20.14.1.5.5
		sleEponOLtDBADOverGrantMonConfChanged NOTIFICATION-TYPE
			OBJECTS { sleEponOltDBAControlRequest, sleEponOltDBAControlTimeStamp, sleEponOltDBAControlReqResult, sleEponOltDBAControlOverGrantMonConfMonitoringInterval, sleEponOltDBAControlOverGrantMonConfMaxDBAGrantSize, 
				sleEponOltDBAControlOverGrantMonConfMinGrantUtilization, sleEponOltDBAControlOverGrantMonConfLeakyBucketCounterValue }
			STATUS current
			DESCRIPTION 
				"Olt DBA over-grant-mon-conf changed trap."
			::= { sleEponOltDBANotification 5 }

		
		-- 1.3.6.1.4.1.6296.101.20.14.1.5.6
		sleEponOltDBAPollingRateChanged NOTIFICATION-TYPE
			OBJECTS { sleEponOltDBAControlRequest, sleEponOltDBAControlTimeStamp, sleEponOltDBAControlReqResult, sleEponOltDBAControlDBAPollingRateLevel, sleEponOltDBAControlDBAPollingRateRate
				 }
			STATUS current
			DESCRIPTION 
				"Polling rate changed trap."
			::= { sleEponOltDBANotification 6 }

		
		-- 1.3.6.1.4.1.6296.101.20.14.1.5.7
		sleEponOltDBAMultiQueueSlaChanged NOTIFICATION-TYPE
			OBJECTS { sleEponOltDBAControlRequest, sleEponOltDBAControlTimeStamp, sleEponOltDBAControlReqResult, sleEponOltDBAControlOltIndex }
			STATUS current
			DESCRIPTION 
				"multicast queue sla changed trap"
			::= { sleEponOltDBANotification 7 }

		
		-- 1.3.6.1.4.1.6296.101.20.14.2
		sleEponOnuProfileDBA OBJECT IDENTIFIER ::= { sleEponDBA 2 }

		
		-- 1.3.6.1.4.1.6296.101.20.14.2.1
		sleEponOnuProfileDBALinkTable OBJECT-TYPE
			SYNTAX SEQUENCE OF SleEponOnuProfileDBALinkEntry
			MAX-ACCESS not-accessible
			STATUS current
			DESCRIPTION
				"Epon onu profile DBA link entry."
			::= { sleEponOnuProfileDBA 1 }

		
		-- 1.3.6.1.4.1.6296.101.20.14.2.1.1
		sleEponOnuProfileDBALinkEntry OBJECT-TYPE
			SYNTAX SleEponOnuProfileDBALinkEntry
			MAX-ACCESS not-accessible
			STATUS current
			DESCRIPTION
				"Description."
			INDEX { sleEponProfileIndex }
			::= { sleEponOnuProfileDBALinkTable 1 }

		
		SleEponOnuProfileDBALinkEntry ::=
			SEQUENCE { 
				sleEponOnuProfileDBAProfileName
					OCTET STRING,
				sleEponOnuProfileDBALinkSlaMinShaBandwidth
					INTEGER,
				sleEponOnuProfileDBALinkSlaMinShaBurstSize
					INTEGER,
				sleEponOnuProfileDBALinkSlaMinShaSchedulerLevel
					INTEGER,
				sleEponOnuProfileDBALinkSlaMinShaWeight
					INTEGER,
				sleEponOnuProfileDBALinkSlaMaxShaBandwidth
					INTEGER,
				sleEponOnuProfileDBALinkSlaMaxShaBurstSize
					INTEGER,
				sleEponOnuProfileDBALinkSlaMaxShaSchedulerLevel
					INTEGER,
				sleEponOnuProfileDBALinkSlaMaxShaWeight
					INTEGER,
				sleEponOnuProfileDBALinkSlaOperate
					INTEGER,
				sleEponOnuProfileDBALinkSlaPollingLevel
					INTEGER,
				sleEponOnuProfileDBALinkSlaTDMRate
					INTEGER,
				sleEponOnuProfileDBALinkSlaTDMGrantLength
					INTEGER,
				sleEponOnuProfileDBALinkOAMMaxOAMRate
					INTEGER,
				sleEponOnuProfileDBALinkOAMMinOAMRate
					INTEGER
			 }

		-- 1.3.6.1.4.1.6296.101.20.14.2.1.1.1
		sleEponOnuProfileDBAProfileName OBJECT-TYPE
			SYNTAX OCTET STRING (SIZE (1..64))
			MAX-ACCESS read-only
			STATUS current
			DESCRIPTION
				"Profile name.
				'all' means configure all the onu profile."
			::= { sleEponOnuProfileDBALinkEntry 1 }

		
		-- 1.3.6.1.4.1.6296.101.20.14.2.1.1.2
		sleEponOnuProfileDBALinkSlaMinShaBandwidth OBJECT-TYPE
			SYNTAX INTEGER (0 | 256..1000000)
			MAX-ACCESS read-only
			STATUS current
			DESCRIPTION
				"Guaranteed Bandwidth(Kbps).
				System default: 0
				"
			DEFVAL { 0 }
			::= { sleEponOnuProfileDBALinkEntry 2 }

		
		-- 1.3.6.1.4.1.6296.101.20.14.2.1.1.3
		sleEponOnuProfileDBALinkSlaMinShaBurstSize OBJECT-TYPE
			SYNTAX INTEGER (1..256 | 65535)
			MAX-ACCESS read-only
			STATUS current
			DESCRIPTION
				"Minimum Burst Size.
				System default: 65535"
			DEFVAL { 65535 }
			::= { sleEponOnuProfileDBALinkEntry 3 }

		
		-- 1.3.6.1.4.1.6296.101.20.14.2.1.1.4
		sleEponOnuProfileDBALinkSlaMinShaSchedulerLevel OBJECT-TYPE
			SYNTAX INTEGER (0..7 | 255)
			MAX-ACCESS read-only
			STATUS current
			DESCRIPTION
				"Scheduler Level.
				System default 255."
			DEFVAL { 255 }
			::= { sleEponOnuProfileDBALinkEntry 4 }

		
		-- 1.3.6.1.4.1.6296.101.20.14.2.1.1.5
		sleEponOnuProfileDBALinkSlaMinShaWeight OBJECT-TYPE
			SYNTAX INTEGER (2..32 | 65535)
			MAX-ACCESS read-only
			STATUS current
			DESCRIPTION
				"Weight
				System default: 65535."
			DEFVAL { 65535 }
			::= { sleEponOnuProfileDBALinkEntry 5 }

		
		-- 1.3.6.1.4.1.6296.101.20.14.2.1.1.6
		sleEponOnuProfileDBALinkSlaMaxShaBandwidth OBJECT-TYPE
			SYNTAX INTEGER (0 | 256..1000000)
			MAX-ACCESS read-only
			STATUS current
			DESCRIPTION
				"Guaranteed Bandwidth(Kbps).
				System default: 100000"
			DEFVAL { 100000 }
			::= { sleEponOnuProfileDBALinkEntry 6 }

		
		-- 1.3.6.1.4.1.6296.101.20.14.2.1.1.7
		sleEponOnuProfileDBALinkSlaMaxShaBurstSize OBJECT-TYPE
			SYNTAX INTEGER (1..256)
			MAX-ACCESS read-only
			STATUS current
			DESCRIPTION
				"Maximum Burst Size.
				System default: 255"
			DEFVAL { 255 }
			::= { sleEponOnuProfileDBALinkEntry 7 }

		
		-- 1.3.6.1.4.1.6296.101.20.14.2.1.1.8
		sleEponOnuProfileDBALinkSlaMaxShaSchedulerLevel OBJECT-TYPE
			SYNTAX INTEGER (0..7)
			MAX-ACCESS read-only
			STATUS current
			DESCRIPTION
				"Scheduler Level.
				System default 2."
			DEFVAL { 2 }
			::= { sleEponOnuProfileDBALinkEntry 8 }

		
		-- 1.3.6.1.4.1.6296.101.20.14.2.1.1.9
		sleEponOnuProfileDBALinkSlaMaxShaWeight OBJECT-TYPE
			SYNTAX INTEGER (2..32)
			MAX-ACCESS read-only
			STATUS current
			DESCRIPTION
				"Weight
				System default: 24."
			DEFVAL { 24 }
			::= { sleEponOnuProfileDBALinkEntry 9 }

		
		-- 1.3.6.1.4.1.6296.101.20.14.2.1.1.10
		sleEponOnuProfileDBALinkSlaOperate OBJECT-TYPE
			SYNTAX INTEGER
				{
				none(1),
				forceReport(2),
				disableOamUplift(3)
				}
			MAX-ACCESS read-only
			STATUS current
			DESCRIPTION
				"Onu profile DBA options."
			::= { sleEponOnuProfileDBALinkEntry 10 }

		
		-- 1.3.6.1.4.1.6296.101.20.14.2.1.1.11
		sleEponOnuProfileDBALinkSlaPollingLevel OBJECT-TYPE
			SYNTAX INTEGER (0..7)
			MAX-ACCESS read-only
			STATUS current
			DESCRIPTION
				"Polling Interval Select."
			::= { sleEponOnuProfileDBALinkEntry 11 }

		
		-- 1.3.6.1.4.1.6296.101.20.14.2.1.1.12
		sleEponOnuProfileDBALinkSlaTDMRate OBJECT-TYPE
			SYNTAX INTEGER (0 | 1..4000)
			MAX-ACCESS read-only
			STATUS current
			DESCRIPTION
				"TDM Rate.
				System default 0."
			DEFVAL { 0 }
			::= { sleEponOnuProfileDBALinkEntry 12 }

		
		-- 1.3.6.1.4.1.6296.101.20.14.2.1.1.13
		sleEponOnuProfileDBALinkSlaTDMGrantLength OBJECT-TYPE
			SYNTAX INTEGER (0 | 84..131072)
			MAX-ACCESS read-only
			STATUS current
			DESCRIPTION
				"TDM grant length.
				System default 0."
			DEFVAL { 0 }
			::= { sleEponOnuProfileDBALinkEntry 13 }

		
		-- 1.3.6.1.4.1.6296.101.20.14.2.1.1.14
		sleEponOnuProfileDBALinkOAMMaxOAMRate OBJECT-TYPE
			SYNTAX INTEGER (0..25)
			MAX-ACCESS read-only
			STATUS current
			DESCRIPTION
				"Maximum OAM rate.
				System default 3."
			DEFVAL { 3 }
			::= { sleEponOnuProfileDBALinkEntry 14 }

		
		-- 1.3.6.1.4.1.6296.101.20.14.2.1.1.15
		sleEponOnuProfileDBALinkOAMMinOAMRate OBJECT-TYPE
			SYNTAX INTEGER (0..10)
			MAX-ACCESS read-only
			STATUS current
			DESCRIPTION
				"Minimum OAM rate.
				System default 10."
			DEFVAL { 10 }
			::= { sleEponOnuProfileDBALinkEntry 15 }

		
		-- 1.3.6.1.4.1.6296.101.20.14.2.2
		sleEponOnuProfileDBAQueueSlaTable OBJECT-TYPE
			SYNTAX SEQUENCE OF SleEponOnuProfileDBAQueueSlaEntry
			MAX-ACCESS not-accessible
			STATUS current
			DESCRIPTION
				"Description."
			::= { sleEponOnuProfileDBA 2 }

		
		-- 1.3.6.1.4.1.6296.101.20.14.2.2.1
		sleEponOnuProfileDBAQueueSlaEntry OBJECT-TYPE
			SYNTAX SleEponOnuProfileDBAQueueSlaEntry
			MAX-ACCESS not-accessible
			STATUS current
			DESCRIPTION
				"Epon onu profile DBA queue sla entry."
			INDEX { sleEponProfileIndex, sleEponOnuProfileDBAQueueIndex }
			::= { sleEponOnuProfileDBAQueueSlaTable 1 }

		
		SleEponOnuProfileDBAQueueSlaEntry ::=
			SEQUENCE { 
				sleEponOnuProfileDBAQueueIndex
					INTEGER,
				sleEponOnuProfileDBAQueueSlaDownMinShaBandwidth
					INTEGER,
				sleEponOnuProfileDBAQueueSlaDownMinShaBurstSize
					INTEGER,
				sleEponOnuProfileDBAQueueSlaDownMinShaSchedulerLevel
					INTEGER,
				sleEponOnuProfileDBAQueueSlaDownMinShaWeight
					INTEGER,
				sleEponOnuProfileDBAQueueSlaDownMaxShaBandwidth
					INTEGER,
				sleEponOnuProfileDBAQueueSlaDownMaxShaBurstSize
					INTEGER,
				sleEponOnuProfileDBAQueueSlaDownMaxShaSchedulerLevel
					INTEGER,
				sleEponOnuProfileDBAQueueSlaDownMaxShaWeight
					INTEGER,
				sleEponOnuProfileDBAQueueSlaUpMinShaBandwidth
					INTEGER,
				sleEponOnuProfileDBAQueueSlaUpMinShaBurstSize
					INTEGER,
				sleEponOnuProfileDBAQueueSlaUpMinShaSchedulerLevel
					INTEGER,
				sleEponOnuProfileDBAQueueSlaUpMinShaWeight
					INTEGER,
				sleEponOnuProfileDBAQueueSlaUpMaxShaBandwidth
					INTEGER,
				sleEponOnuProfileDBAQueueSlaUpMaxShaBurstSize
					INTEGER,
				sleEponOnuProfileDBAQueueSlaUpMaxShaSchedulerLevel
					INTEGER,
				sleEponOnuProfileDBAQueueSlaUpMaxShaWeight
					INTEGER
			 }

		-- 1.3.6.1.4.1.6296.101.20.14.2.2.1.1
		sleEponOnuProfileDBAQueueIndex OBJECT-TYPE
			SYNTAX INTEGER (0..3)
			MAX-ACCESS read-only
			STATUS current
			DESCRIPTION
				"Queue index."
			::= { sleEponOnuProfileDBAQueueSlaEntry 1 }

		
		-- 1.3.6.1.4.1.6296.101.20.14.2.2.1.2
		sleEponOnuProfileDBAQueueSlaDownMinShaBandwidth OBJECT-TYPE
			SYNTAX INTEGER (0 | 256..1000000)
			MAX-ACCESS read-only
			STATUS current
			DESCRIPTION
				"Queue sla downstream shaper minimum bandwidth.
				System default 0."
			DEFVAL { 0 }
			::= { sleEponOnuProfileDBAQueueSlaEntry 2 }

		
		-- 1.3.6.1.4.1.6296.101.20.14.2.2.1.3
		sleEponOnuProfileDBAQueueSlaDownMinShaBurstSize OBJECT-TYPE
			SYNTAX INTEGER (1..256 | 65535)
			MAX-ACCESS read-only
			STATUS current
			DESCRIPTION
				"Queue sla downstream shaper minimum burst size.
				System default 65535."
			DEFVAL { 65535 }
			::= { sleEponOnuProfileDBAQueueSlaEntry 3 }

		
		-- 1.3.6.1.4.1.6296.101.20.14.2.2.1.4
		sleEponOnuProfileDBAQueueSlaDownMinShaSchedulerLevel OBJECT-TYPE
			SYNTAX INTEGER (0..7 | 255)
			MAX-ACCESS read-only
			STATUS current
			DESCRIPTION
				"Queue sla downstream shaper minimum scheduer level.
				System default 255."
			DEFVAL { 255 }
			::= { sleEponOnuProfileDBAQueueSlaEntry 4 }

		
		-- 1.3.6.1.4.1.6296.101.20.14.2.2.1.5
		sleEponOnuProfileDBAQueueSlaDownMinShaWeight OBJECT-TYPE
			SYNTAX INTEGER (2..32 | 65535)
			MAX-ACCESS read-only
			STATUS current
			DESCRIPTION
				"Queue sla downstream shaper minimum weight.
				System default 65535."
			DEFVAL { 65535 }
			::= { sleEponOnuProfileDBAQueueSlaEntry 5 }

		
		-- 1.3.6.1.4.1.6296.101.20.14.2.2.1.6
		sleEponOnuProfileDBAQueueSlaDownMaxShaBandwidth OBJECT-TYPE
			SYNTAX INTEGER (256..1000000)
			MAX-ACCESS read-only
			STATUS current
			DESCRIPTION
				"Queue sla downstream shaper maximum bandwidth.
				System default 100000"
			DEFVAL { 100000 }
			::= { sleEponOnuProfileDBAQueueSlaEntry 6 }

		
		-- 1.3.6.1.4.1.6296.101.20.14.2.2.1.7
		sleEponOnuProfileDBAQueueSlaDownMaxShaBurstSize OBJECT-TYPE
			SYNTAX INTEGER (1..256)
			MAX-ACCESS read-only
			STATUS current
			DESCRIPTION
				"Queue sla downstream shaper maximum burst size.
				System default 255."
			DEFVAL { 255 }
			::= { sleEponOnuProfileDBAQueueSlaEntry 7 }

		
		-- 1.3.6.1.4.1.6296.101.20.14.2.2.1.8
		sleEponOnuProfileDBAQueueSlaDownMaxShaSchedulerLevel OBJECT-TYPE
			SYNTAX INTEGER (0..7)
			MAX-ACCESS read-only
			STATUS current
			DESCRIPTION
				"Queue sla downstream shaper maximum scheduler level.
				System default 2."
			DEFVAL { 2 }
			::= { sleEponOnuProfileDBAQueueSlaEntry 8 }

		
		-- 1.3.6.1.4.1.6296.101.20.14.2.2.1.9
		sleEponOnuProfileDBAQueueSlaDownMaxShaWeight OBJECT-TYPE
			SYNTAX INTEGER (2..32)
			MAX-ACCESS read-only
			STATUS current
			DESCRIPTION
				"Queue sla downstream shaper maximum weight.
				System default 24."
			DEFVAL { 24 }
			::= { sleEponOnuProfileDBAQueueSlaEntry 9 }

		
		-- 1.3.6.1.4.1.6296.101.20.14.2.2.1.10
		sleEponOnuProfileDBAQueueSlaUpMinShaBandwidth OBJECT-TYPE
			SYNTAX INTEGER (0 | 256..1000000)
			MAX-ACCESS read-only
			STATUS current
			DESCRIPTION
				"Queue sla upstream shaper minimum bandwidth.
				System default 0."
			DEFVAL { 0 }
			::= { sleEponOnuProfileDBAQueueSlaEntry 10 }

		
		-- 1.3.6.1.4.1.6296.101.20.14.2.2.1.11
		sleEponOnuProfileDBAQueueSlaUpMinShaBurstSize OBJECT-TYPE
			SYNTAX INTEGER (1..256 | 65535)
			MAX-ACCESS read-only
			STATUS current
			DESCRIPTION
				"Queue sla upstream shaper minimum bandwidth.
				System default 65535."
			DEFVAL { 65535 }
			::= { sleEponOnuProfileDBAQueueSlaEntry 11 }

		
		-- 1.3.6.1.4.1.6296.101.20.14.2.2.1.12
		sleEponOnuProfileDBAQueueSlaUpMinShaSchedulerLevel OBJECT-TYPE
			SYNTAX INTEGER (0..7 | 255)
			MAX-ACCESS read-write
			STATUS current
			DESCRIPTION
				"Queue sla upstream shaper minimum scheduler level.
				System default 255."
			DEFVAL { 255 }
			::= { sleEponOnuProfileDBAQueueSlaEntry 12 }

		
		-- 1.3.6.1.4.1.6296.101.20.14.2.2.1.13
		sleEponOnuProfileDBAQueueSlaUpMinShaWeight OBJECT-TYPE
			SYNTAX INTEGER (2..32 | 65535)
			MAX-ACCESS read-only
			STATUS current
			DESCRIPTION
				"Queue sla upstream shaper minimum weight.
				System default 65535."
			DEFVAL { 65535 }
			::= { sleEponOnuProfileDBAQueueSlaEntry 13 }

		
		-- 1.3.6.1.4.1.6296.101.20.14.2.2.1.14
		sleEponOnuProfileDBAQueueSlaUpMaxShaBandwidth OBJECT-TYPE
			SYNTAX INTEGER (256..1000000)
			MAX-ACCESS read-write
			STATUS current
			DESCRIPTION
				"Queue sla upstream shaper maximum bandwidth.
				System default 100000."
			DEFVAL { 100000 }
			::= { sleEponOnuProfileDBAQueueSlaEntry 14 }

		
		-- 1.3.6.1.4.1.6296.101.20.14.2.2.1.15
		sleEponOnuProfileDBAQueueSlaUpMaxShaBurstSize OBJECT-TYPE
			SYNTAX INTEGER (1..256)
			MAX-ACCESS read-only
			STATUS current
			DESCRIPTION
				"Queue sla upstream shaper maximum burst size.
				System default 255."
			DEFVAL { 255 }
			::= { sleEponOnuProfileDBAQueueSlaEntry 15 }

		
		-- 1.3.6.1.4.1.6296.101.20.14.2.2.1.16
		sleEponOnuProfileDBAQueueSlaUpMaxShaSchedulerLevel OBJECT-TYPE
			SYNTAX INTEGER (0..7)
			MAX-ACCESS read-write
			STATUS current
			DESCRIPTION
				"Queue sla upstream shaper maximum scheduler level.
				System default 2."
			DEFVAL { 2 }
			::= { sleEponOnuProfileDBAQueueSlaEntry 16 }

		
		-- 1.3.6.1.4.1.6296.101.20.14.2.2.1.17
		sleEponOnuProfileDBAQueueSlaUpMaxShaWeight OBJECT-TYPE
			SYNTAX INTEGER (2..32)
			MAX-ACCESS read-only
			STATUS current
			DESCRIPTION
				"Queue sla upstream shaper maximum weight.
				System default 24."
			DEFVAL { 24 }
			::= { sleEponOnuProfileDBAQueueSlaEntry 17 }

		
		-- 1.3.6.1.4.1.6296.101.20.14.2.3
		sleEponOnuProfileDBAControl OBJECT IDENTIFIER ::= { sleEponOnuProfileDBA 3 }

		
		-- 1.3.6.1.4.1.6296.101.20.14.2.3.1
		sleEponOnuProfileDBAControlRequest OBJECT-TYPE
			SYNTAX INTEGER
				{
				setPonOnuProfileDBALinkSla(1),
				noPonOnuProfileDBALinkSla(2),
				setPonOnuProfileDBAQueueSla(3),
				noPonOnuProfileDBAQueueSla(4),
				noPonOnuProfileDBAQueueSlaAll(5),
				setPonOnuProfileDBALinkOAMRate(6),
				noPonOnuProfileDBALinkOAMRate(7)
				}
			MAX-ACCESS read-write
			STATUS current
			DESCRIPTION
				"The request of a user command."
			::= { sleEponOnuProfileDBAControl 1 }

		
		-- 1.3.6.1.4.1.6296.101.20.14.2.3.2
		sleEponOnuProfileDBAControlStatus OBJECT-TYPE
			SYNTAX SleControlStatusType
			MAX-ACCESS read-write
			STATUS current
			DESCRIPTION
				"The status of user command."
			::= { sleEponOnuProfileDBAControl 2 }

		
		-- 1.3.6.1.4.1.6296.101.20.14.2.3.3
		sleEponOnuProfileDBAControlTimer OBJECT-TYPE
			SYNTAX Gauge32
			MAX-ACCESS read-write
			STATUS current
			DESCRIPTION
				"The maximum time for the manager for a long running user command."
			::= { sleEponOnuProfileDBAControl 3 }

		
		-- 1.3.6.1.4.1.6296.101.20.14.2.3.4
		sleEponOnuProfileDBAControlTimeStamp OBJECT-TYPE
			SYNTAX TimeTicks
			MAX-ACCESS read-write
			STATUS current
			DESCRIPTION
				"The time stamp of the last command(end of command)."
			::= { sleEponOnuProfileDBAControl 4 }

		
		-- 1.3.6.1.4.1.6296.101.20.14.2.3.5
		sleEponOnuProfileDBAControlReqResult OBJECT-TYPE
			SYNTAX SleControlRequestResultType
			MAX-ACCESS read-write
			STATUS current
			DESCRIPTION
				"The result of the last user command."
			::= { sleEponOnuProfileDBAControl 5 }

		
		-- 1.3.6.1.4.1.6296.101.20.14.2.3.6
		sleEponOnuProfileDBAControlProfileName OBJECT-TYPE
			SYNTAX OCTET STRING (SIZE (1..64))
			MAX-ACCESS read-write
			STATUS current
			DESCRIPTION
				"Profile name.
				'all' means configure all the onu profile."
			::= { sleEponOnuProfileDBAControl 6 }

		
		-- 1.3.6.1.4.1.6296.101.20.14.2.3.7
		sleEponOnuProfileDBAControlLinkSlaMinShaBandwidth OBJECT-TYPE
			SYNTAX INTEGER (0 | 256..1000000)
			MAX-ACCESS read-write
			STATUS current
			DESCRIPTION
				"Guaranteed Bandwidth(Kbps).
				0 means that we will use the default value."
			DEFVAL { 0 }
			::= { sleEponOnuProfileDBAControl 7 }

		
		-- 1.3.6.1.4.1.6296.101.20.14.2.3.8
		sleEponOnuProfileDBAControlLinkSlaMinShaBurstSize OBJECT-TYPE
			SYNTAX INTEGER (1..256 | 65535)
			MAX-ACCESS read-write
			STATUS current
			DESCRIPTION
				"Minimum Burst Size.
				Default 65535."
			DEFVAL { 65535 }
			::= { sleEponOnuProfileDBAControl 8 }

		
		-- 1.3.6.1.4.1.6296.101.20.14.2.3.9
		sleEponOnuProfileDBAControlLinkSlaMinShaSchedulerLevel OBJECT-TYPE
			SYNTAX INTEGER (0..7 | 255)
			MAX-ACCESS read-write
			STATUS current
			DESCRIPTION
				"Scheduler Level.
				Default 255."
			DEFVAL { 255 }
			::= { sleEponOnuProfileDBAControl 9 }

		
		-- 1.3.6.1.4.1.6296.101.20.14.2.3.10
		sleEponOnuProfileDBAControlLinkSlaMinShaWeight OBJECT-TYPE
			SYNTAX INTEGER (2..32 | 65535)
			MAX-ACCESS read-write
			STATUS current
			DESCRIPTION
				"Weight.
				Default 65535."
			DEFVAL { 0 }
			::= { sleEponOnuProfileDBAControl 10 }

		
		-- 1.3.6.1.4.1.6296.101.20.14.2.3.11
		sleEponOnuProfileDBAControlLinkSlaMaxShaBandwidth OBJECT-TYPE
			SYNTAX INTEGER (256..1000000)
			MAX-ACCESS read-write
			STATUS current
			DESCRIPTION
				"Guaranteed Bandwidth(Kbps)."
			::= { sleEponOnuProfileDBAControl 11 }

		
		-- 1.3.6.1.4.1.6296.101.20.14.2.3.12
		sleEponOnuProfileDBAControlLinkSlaMaxShaBurstSize OBJECT-TYPE
			SYNTAX INTEGER (1..256)
			MAX-ACCESS read-write
			STATUS current
			DESCRIPTION
				"Maximum burst size."
			::= { sleEponOnuProfileDBAControl 12 }

		
		-- 1.3.6.1.4.1.6296.101.20.14.2.3.13
		sleEponOnuProfileDBAControlLinkSlaMaxShaSchedulerLevel OBJECT-TYPE
			SYNTAX INTEGER (0..7)
			MAX-ACCESS read-write
			STATUS current
			DESCRIPTION
				"Scheduler Level."
			::= { sleEponOnuProfileDBAControl 13 }

		
		-- 1.3.6.1.4.1.6296.101.20.14.2.3.14
		sleEponOnuProfileDBAControlLinkSlaMaxShaWeight OBJECT-TYPE
			SYNTAX INTEGER (2..32)
			MAX-ACCESS read-write
			STATUS current
			DESCRIPTION
				"Weight."
			::= { sleEponOnuProfileDBAControl 14 }

		
		-- 1.3.6.1.4.1.6296.101.20.14.2.3.15
		sleEponOnuProfileDBAControlLinkSlaOperate OBJECT-TYPE
			SYNTAX INTEGER
				{
				none(1),
				forceReport(2),
				disableOAMUplift(3)
				}
			MAX-ACCESS read-write
			STATUS current
			DESCRIPTION
				"Onu profile DBA options."
			::= { sleEponOnuProfileDBAControl 15 }

		
		-- 1.3.6.1.4.1.6296.101.20.14.2.3.16
		sleEponOnuProfileDBAControlLinkSlaPollingLevel OBJECT-TYPE
			SYNTAX INTEGER (0..7)
			MAX-ACCESS read-write
			STATUS current
			DESCRIPTION
				"Polling Interval Select."
			::= { sleEponOnuProfileDBAControl 16 }

		
		-- 1.3.6.1.4.1.6296.101.20.14.2.3.17
		sleEponOnuProfileDBAControlLinkSlaTDMRate OBJECT-TYPE
			SYNTAX INTEGER (0 | 1..4000)
			MAX-ACCESS read-write
			STATUS current
			DESCRIPTION
				"TDM Rate.
				0 means that we will use the default value."
			DEFVAL { 0 }
			::= { sleEponOnuProfileDBAControl 17 }

		
		-- 1.3.6.1.4.1.6296.101.20.14.2.3.18
		sleEponOnuProfileDBAControlLinkSlaTDMGrantLength OBJECT-TYPE
			SYNTAX INTEGER (0 | 84..131072)
			MAX-ACCESS read-write
			STATUS current
			DESCRIPTION
				"TDM grant length.
				0 means that we will use the default value."
			DEFVAL { 0 }
			::= { sleEponOnuProfileDBAControl 18 }

		
		-- 1.3.6.1.4.1.6296.101.20.14.2.3.19
		sleEponOnuProfileDBAControlQueueIndex OBJECT-TYPE
			SYNTAX INTEGER (0..3)
			MAX-ACCESS read-write
			STATUS current
			DESCRIPTION
				"Queue index."
			::= { sleEponOnuProfileDBAControl 19 }

		
		-- 1.3.6.1.4.1.6296.101.20.14.2.3.20
		sleEponOnuProfileDBAControlQueueSlaMinShaBandwidth OBJECT-TYPE
			SYNTAX INTEGER (256..1000000)
			MAX-ACCESS read-write
			STATUS current
			DESCRIPTION
				"Guaranteed Bandwidth(Kbps)."
			::= { sleEponOnuProfileDBAControl 20 }

		
		-- 1.3.6.1.4.1.6296.101.20.14.2.3.21
		sleEponOnuProfileDBAControlQueueSlaMinShaBurstSize OBJECT-TYPE
			SYNTAX INTEGER (1..256)
			MAX-ACCESS read-write
			STATUS current
			DESCRIPTION
				"Minimum Burst Size."
			::= { sleEponOnuProfileDBAControl 21 }

		
		-- 1.3.6.1.4.1.6296.101.20.14.2.3.22
		sleEponOnuProfileDBAControlQueueSlaMinShaSchedulerLevel OBJECT-TYPE
			SYNTAX INTEGER (0..7)
			MAX-ACCESS read-write
			STATUS current
			DESCRIPTION
				"Scheduler Level."
			::= { sleEponOnuProfileDBAControl 22 }

		
		-- 1.3.6.1.4.1.6296.101.20.14.2.3.23
		sleEponOnuProfileDBAControlQueueSlaMinShaWeight OBJECT-TYPE
			SYNTAX INTEGER (2..32)
			MAX-ACCESS read-write
			STATUS current
			DESCRIPTION
				"Weight."
			::= { sleEponOnuProfileDBAControl 23 }

		
		-- 1.3.6.1.4.1.6296.101.20.14.2.3.24
		sleEponOnuProfileDBAControlQueueSlaMaxShaBandwidth OBJECT-TYPE
			SYNTAX INTEGER (256..1000000)
			MAX-ACCESS read-write
			STATUS current
			DESCRIPTION
				"Guaranteed Bandwidth(Kbps)."
			::= { sleEponOnuProfileDBAControl 24 }

		
		-- 1.3.6.1.4.1.6296.101.20.14.2.3.25
		sleEponOnuProfileDBAControlQueueSlaMaxShaBurstSize OBJECT-TYPE
			SYNTAX INTEGER (1..256)
			MAX-ACCESS read-write
			STATUS current
			DESCRIPTION
				"Maximum burst size."
			::= { sleEponOnuProfileDBAControl 25 }

		
		-- 1.3.6.1.4.1.6296.101.20.14.2.3.26
		sleEponOnuProfileDBAControlQueueSlaMaxShaSchedulerLevel OBJECT-TYPE
			SYNTAX INTEGER (0..7)
			MAX-ACCESS read-write
			STATUS current
			DESCRIPTION
				"Scheduler Level."
			::= { sleEponOnuProfileDBAControl 26 }

		
		-- 1.3.6.1.4.1.6296.101.20.14.2.3.27
		sleEponOnuProfileDBAControlQueueSlaMaxShaWeight OBJECT-TYPE
			SYNTAX INTEGER (2..32)
			MAX-ACCESS read-write
			STATUS current
			DESCRIPTION
				"Weight."
			::= { sleEponOnuProfileDBAControl 27 }

		
		-- 1.3.6.1.4.1.6296.101.20.14.2.3.28
		sleEponOnuProfileDBAControlQueueSlaOperate OBJECT-TYPE
			SYNTAX INTEGER
				{
				upstream(1),
				downstream(2)
				}
			MAX-ACCESS read-write
			STATUS current
			DESCRIPTION
				"Direction of Egress Shaping."
			::= { sleEponOnuProfileDBAControl 28 }

		
		-- 1.3.6.1.4.1.6296.101.20.14.2.3.29
		sleEponOnuProfileDBAControlLinkOAMMaxRate OBJECT-TYPE
			SYNTAX INTEGER (0..25)
			MAX-ACCESS read-write
			STATUS current
			DESCRIPTION
				"Maximum OAM rate."
			::= { sleEponOnuProfileDBAControl 29 }

		
		-- 1.3.6.1.4.1.6296.101.20.14.2.3.30
		sleEponOnuProfileDBAControlLinkOAMMinRate OBJECT-TYPE
			SYNTAX INTEGER (0..10)
			MAX-ACCESS read-write
			STATUS current
			DESCRIPTION
				"Minimum OAM rate."
			::= { sleEponOnuProfileDBAControl 30 }

		
		-- 1.3.6.1.4.1.6296.101.20.14.2.4
		sleEponOnuProfileDBANotification OBJECT IDENTIFIER ::= { sleEponOnuProfileDBA 4 }

		
		-- 1.3.6.1.4.1.6296.101.20.14.2.4.1
		sleEponOnuProfileDBALinkSlaChanged NOTIFICATION-TYPE
			OBJECTS { sleEponOnuProfileDBAControlRequest, sleEponOnuProfileDBAControlTimeStamp, sleEponOnuProfileDBAControlReqResult, sleEponOnuProfileDBAControlProfileName }
			STATUS current
			DESCRIPTION 
				"Set ONU profile DBA link sla trap."
			::= { sleEponOnuProfileDBANotification 1 }

		
		-- 1.3.6.1.4.1.6296.101.20.14.2.4.2
		sleEponOnuProfileDBAQueueSlaChanged NOTIFICATION-TYPE
			OBJECTS { sleEponOnuProfileDBAControlRequest, sleEponOnuProfileDBAControlTimeStamp, sleEponOnuProfileDBAControlReqResult, sleEponOnuProfileDBAControlProfileName, sleEponOnuProfileDBAControlQueueIndex
				 }
			STATUS current
			DESCRIPTION 
				"Onu profile DBA queue sla changed trap."
			::= { sleEponOnuProfileDBANotification 2 }

		
		-- 1.3.6.1.4.1.6296.101.20.14.2.4.3
		sleEponOnuProfileDBALinkOAMRateChanged NOTIFICATION-TYPE
			OBJECTS { sleEponOnuProfileDBAControlRequest, sleEponOnuProfileDBAControlTimeStamp, sleEponOnuProfileDBAControlReqResult, sleEponOnuProfileDBAControlProfileName, sleEponOnuProfileDBAControlLinkOAMMaxRate, 
				sleEponOnuProfileDBAControlLinkOAMMinRate }
			STATUS current
			DESCRIPTION 
				"Onu profile DBA link OAM changed trap."
			::= { sleEponOnuProfileDBANotification 3 }

		
		-- 1.3.6.1.4.1.6296.101.20.14.2.5
		sleEponOnuProfileDBAMutilLLidLinkTable OBJECT-TYPE
			SYNTAX SEQUENCE OF SleEponOnuProfileDBAMutilLLidLinkEntry
			MAX-ACCESS not-accessible
			STATUS current
			DESCRIPTION
				"Epon onu profile DBA link entry."
			::= { sleEponOnuProfileDBA 5 }

		
		-- 1.3.6.1.4.1.6296.101.20.14.2.5.1
		sleEponOnuProfileDBAMutilLLidLinkEntry OBJECT-TYPE
			SYNTAX SleEponOnuProfileDBAMutilLLidLinkEntry
			MAX-ACCESS not-accessible
			STATUS current
			DESCRIPTION
				"Description."
			INDEX { sleEponProfileIndex }
			::= { sleEponOnuProfileDBAMutilLLidLinkTable 1 }

		
		SleEponOnuProfileDBAMutilLLidLinkEntry ::=
			SEQUENCE { 
				sleEponOnuProfileDBAMultiLLidProfileName
					OCTET STRING,
				sleEponOnuProfileDBAMultiLLidLinkSlaMinShaBandwidth
					INTEGER,
				sleEponOnuProfileDBAMultiLLidLinkSlaMinShaBurstSize
					INTEGER,
				sleEponOnuProfileDBAMultiLLidLinkSlaMinShaSchedulerLevel
					INTEGER,
				sleEponOnuProfileDBAMultiLLidLinkSlaMinShaWeight
					INTEGER,
				sleEponOnuProfileDBAMultiLLidLinkSlaMaxShaBandwidth
					INTEGER,
				sleEponOnuProfileDBAMultiLLidLinkSlaMaxShaBurstSize
					INTEGER,
				sleEponOnuProfileDBAMultiLLidLinkSlaMaxShaSchedulerLevel
					INTEGER,
				sleEponOnuProfileDBAMultiLLidLinkSlaMaxShaWeight
					INTEGER,
				sleEponOnuProfileDBAMultiLLidLinkSlaOperate
					INTEGER,
				sleEponOnuProfileDBAMultiLLidLinkSlaPollingLevel
					INTEGER,
				sleEponOnuProfileDBAMultiLLidLinkSlaTDMRate
					INTEGER,
				sleEponOnuProfileDBAMultiLLidLinkSlaTDMGrantLength
					INTEGER,
				sleEponOnuProfileDBAMultiLLidLinkOAMMaxOAMRate
					INTEGER,
				sleEponOnuProfileDBAMultiLLidLinkOAMMinOAMRate
					INTEGER
			 }

		-- 1.3.6.1.4.1.6296.101.20.14.2.5.1.1
		sleEponOnuProfileDBAMultiLLidProfileName OBJECT-TYPE
			SYNTAX OCTET STRING (SIZE (1..64))
			MAX-ACCESS read-only
			STATUS current
			DESCRIPTION
				"Profile name.
				'all' means configure all the onu profile."
			::= { sleEponOnuProfileDBAMutilLLidLinkEntry 1 }

		
		-- 1.3.6.1.4.1.6296.101.20.14.2.5.1.2
		sleEponOnuProfileDBAMultiLLidLinkSlaMinShaBandwidth OBJECT-TYPE
			SYNTAX INTEGER (0 | 256..1000000)
			MAX-ACCESS read-only
			STATUS current
			DESCRIPTION
				"Guaranteed Bandwidth(Kbps).
				System default: 0
				"
			DEFVAL { 0 }
			::= { sleEponOnuProfileDBAMutilLLidLinkEntry 2 }

		
		-- 1.3.6.1.4.1.6296.101.20.14.2.5.1.3
		sleEponOnuProfileDBAMultiLLidLinkSlaMinShaBurstSize OBJECT-TYPE
			SYNTAX INTEGER (1..256 | 65535)
			MAX-ACCESS read-only
			STATUS current
			DESCRIPTION
				"Minimum Burst Size.
				System default: 65535"
			DEFVAL { 65535 }
			::= { sleEponOnuProfileDBAMutilLLidLinkEntry 3 }

		
		-- 1.3.6.1.4.1.6296.101.20.14.2.5.1.4
		sleEponOnuProfileDBAMultiLLidLinkSlaMinShaSchedulerLevel OBJECT-TYPE
			SYNTAX INTEGER (0..7 | 255)
			MAX-ACCESS read-only
			STATUS current
			DESCRIPTION
				"Scheduler Level.
				System default 255."
			DEFVAL { 255 }
			::= { sleEponOnuProfileDBAMutilLLidLinkEntry 4 }

		
		-- 1.3.6.1.4.1.6296.101.20.14.2.5.1.5
		sleEponOnuProfileDBAMultiLLidLinkSlaMinShaWeight OBJECT-TYPE
			SYNTAX INTEGER (2..32 | 65535)
			MAX-ACCESS read-only
			STATUS current
			DESCRIPTION
				"Weight
				System default: 65535."
			DEFVAL { 65535 }
			::= { sleEponOnuProfileDBAMutilLLidLinkEntry 5 }

		
		-- 1.3.6.1.4.1.6296.101.20.14.2.5.1.6
		sleEponOnuProfileDBAMultiLLidLinkSlaMaxShaBandwidth OBJECT-TYPE
			SYNTAX INTEGER (0 | 256..1000000)
			MAX-ACCESS read-only
			STATUS current
			DESCRIPTION
				"Guaranteed Bandwidth(Kbps).
				System default: 100000"
			DEFVAL { 100000 }
			::= { sleEponOnuProfileDBAMutilLLidLinkEntry 6 }

		
		-- 1.3.6.1.4.1.6296.101.20.14.2.5.1.7
		sleEponOnuProfileDBAMultiLLidLinkSlaMaxShaBurstSize OBJECT-TYPE
			SYNTAX INTEGER (1..256)
			MAX-ACCESS read-only
			STATUS current
			DESCRIPTION
				"Maximum Burst Size.
				System default: 255"
			DEFVAL { 255 }
			::= { sleEponOnuProfileDBAMutilLLidLinkEntry 7 }

		
		-- 1.3.6.1.4.1.6296.101.20.14.2.5.1.8
		sleEponOnuProfileDBAMultiLLidLinkSlaMaxShaSchedulerLevel OBJECT-TYPE
			SYNTAX INTEGER (0..7)
			MAX-ACCESS read-only
			STATUS current
			DESCRIPTION
				"Scheduler Level.
				System default 2."
			DEFVAL { 2 }
			::= { sleEponOnuProfileDBAMutilLLidLinkEntry 8 }

		
		-- 1.3.6.1.4.1.6296.101.20.14.2.5.1.9
		sleEponOnuProfileDBAMultiLLidLinkSlaMaxShaWeight OBJECT-TYPE
			SYNTAX INTEGER (2..32)
			MAX-ACCESS read-only
			STATUS current
			DESCRIPTION
				"Weight
				System default: 24."
			DEFVAL { 24 }
			::= { sleEponOnuProfileDBAMutilLLidLinkEntry 9 }

		
		-- 1.3.6.1.4.1.6296.101.20.14.2.5.1.10
		sleEponOnuProfileDBAMultiLLidLinkSlaOperate OBJECT-TYPE
			SYNTAX INTEGER
				{
				none(1),
				forceReport(2),
				disableOamUplift(3)
				}
			MAX-ACCESS read-only
			STATUS current
			DESCRIPTION
				"Onu profile DBA options."
			::= { sleEponOnuProfileDBAMutilLLidLinkEntry 10 }

		
		-- 1.3.6.1.4.1.6296.101.20.14.2.5.1.11
		sleEponOnuProfileDBAMultiLLidLinkSlaPollingLevel OBJECT-TYPE
			SYNTAX INTEGER (0..7)
			MAX-ACCESS read-only
			STATUS current
			DESCRIPTION
				"Polling Interval Select."
			::= { sleEponOnuProfileDBAMutilLLidLinkEntry 11 }

		
		-- 1.3.6.1.4.1.6296.101.20.14.2.5.1.12
		sleEponOnuProfileDBAMultiLLidLinkSlaTDMRate OBJECT-TYPE
			SYNTAX INTEGER (0 | 1..4000)
			MAX-ACCESS read-only
			STATUS current
			DESCRIPTION
				"TDM Rate.
				System default 0."
			DEFVAL { 0 }
			::= { sleEponOnuProfileDBAMutilLLidLinkEntry 12 }

		
		-- 1.3.6.1.4.1.6296.101.20.14.2.5.1.13
		sleEponOnuProfileDBAMultiLLidLinkSlaTDMGrantLength OBJECT-TYPE
			SYNTAX INTEGER (0 | 84..131072)
			MAX-ACCESS read-only
			STATUS current
			DESCRIPTION
				"TDM grant length.
				System default 0."
			DEFVAL { 0 }
			::= { sleEponOnuProfileDBAMutilLLidLinkEntry 13 }

		
		-- 1.3.6.1.4.1.6296.101.20.14.2.5.1.14
		sleEponOnuProfileDBAMultiLLidLinkOAMMaxOAMRate OBJECT-TYPE
			SYNTAX INTEGER (0..25)
			MAX-ACCESS read-only
			STATUS current
			DESCRIPTION
				"Maximum OAM rate.
				System default 3."
			DEFVAL { 3 }
			::= { sleEponOnuProfileDBAMutilLLidLinkEntry 14 }

		
		-- 1.3.6.1.4.1.6296.101.20.14.2.5.1.15
		sleEponOnuProfileDBAMultiLLidLinkOAMMinOAMRate OBJECT-TYPE
			SYNTAX INTEGER (0..10)
			MAX-ACCESS read-only
			STATUS current
			DESCRIPTION
				"Minimum OAM rate.
				System default 10."
			DEFVAL { 10 }
			::= { sleEponOnuProfileDBAMutilLLidLinkEntry 15 }

		
		-- 1.3.6.1.4.1.6296.101.20.14.2.6
		sleEponOnuProfileDBAMultiLLidQueueSlaTable OBJECT-TYPE
			SYNTAX SEQUENCE OF SleEponOnuProfileDBAMultiLLidQueueSlaEntry
			MAX-ACCESS not-accessible
			STATUS current
			DESCRIPTION
				"Description."
			::= { sleEponOnuProfileDBA 6 }

		
		-- 1.3.6.1.4.1.6296.101.20.14.2.6.1
		sleEponOnuProfileDBAMultiLLidQueueSlaEntry OBJECT-TYPE
			SYNTAX SleEponOnuProfileDBAMultiLLidQueueSlaEntry
			MAX-ACCESS not-accessible
			STATUS current
			DESCRIPTION
				"Epon onu profile DBA queue sla entry."
			INDEX { sleEponProfileIndex, sleEponOnuProfileDBAQueueIndex }
			::= { sleEponOnuProfileDBAMultiLLidQueueSlaTable 1 }

		
		SleEponOnuProfileDBAMultiLLidQueueSlaEntry ::=
			SEQUENCE { 
				sleEponOnuProfileDBAMultiLLidQueueIndex
					INTEGER,
				sleEponOnuProfileDBAMultiLLidQueueSlaDownMinShaBandwidth
					INTEGER,
				sleEponOnuProfileDBAMultiLLidQueueSlaDownMinShaBurstSize
					INTEGER,
				sleEponOnuProfileDBAMultiLLidQueueSlaDownMinShaSchedulerLevel
					INTEGER,
				sleEponOnuProfileDBAMultiLLidQueueSlaDownMinShaWeight
					INTEGER,
				sleEponOnuProfileDBAMutiLLidQueueSlaDownMaxShaBandwidth
					INTEGER,
				sleEponOnuProfileDBAMultiLLidQueueSlaDownMaxShaBurstSize
					INTEGER,
				sleEponOnuProfileDBAMultiLLidQueueSlaDownMaxShaSchedulerLevel
					INTEGER,
				sleEponOnuProfileDBAMultiLLidQueueSlaDownMaxShaWeight
					INTEGER,
				sleEponOnuProfileDBAMultiLLidQueueSlaUpMinShaBandwidth
					INTEGER,
				sleEponOnuProfileDBAMultiLLidQueueSlaUpMinShaBurstSize
					INTEGER,
				sleEponOnuProfileDBAMultiLLidQueueSlaUpMinShaSchedulerLevel
					INTEGER,
				sleEponOnuProfileDBAMultiLLidQueueSlaUpMinShaWeight
					INTEGER,
				sleEponOnuProfileDBAMultiLLidQueueSlaUpMaxShaBandwidth
					INTEGER,
				sleEponOnuProfileDBAMultiLLidQueueSlaUpMaxShaBurstSize
					INTEGER,
				sleEponOnuProfileDBAMultiLLidQueueSlaUpMaxShaSchedulerLevel
					INTEGER,
				sleEponOnuProfileDBAMultiLLidQueueSlaUpMaxShaWeight
					INTEGER
			 }

		-- 1.3.6.1.4.1.6296.101.20.14.2.6.1.1
		sleEponOnuProfileDBAMultiLLidQueueIndex OBJECT-TYPE
			SYNTAX INTEGER (0..3)
			MAX-ACCESS read-only
			STATUS current
			DESCRIPTION
				"Queue index."
			::= { sleEponOnuProfileDBAMultiLLidQueueSlaEntry 1 }

		
		-- 1.3.6.1.4.1.6296.101.20.14.2.6.1.2
		sleEponOnuProfileDBAMultiLLidQueueSlaDownMinShaBandwidth OBJECT-TYPE
			SYNTAX INTEGER (0 | 256..1000000)
			MAX-ACCESS read-only
			STATUS current
			DESCRIPTION
				"Queue sla downstream shaper minimum bandwidth.
				System default 0."
			DEFVAL { 0 }
			::= { sleEponOnuProfileDBAMultiLLidQueueSlaEntry 2 }

		
		-- 1.3.6.1.4.1.6296.101.20.14.2.6.1.3
		sleEponOnuProfileDBAMultiLLidQueueSlaDownMinShaBurstSize OBJECT-TYPE
			SYNTAX INTEGER (1..256 | 65535)
			MAX-ACCESS read-only
			STATUS current
			DESCRIPTION
				"Queue sla downstream shaper minimum burst size.
				System default 65535."
			DEFVAL { 65535 }
			::= { sleEponOnuProfileDBAMultiLLidQueueSlaEntry 3 }

		
		-- 1.3.6.1.4.1.6296.101.20.14.2.6.1.4
		sleEponOnuProfileDBAMultiLLidQueueSlaDownMinShaSchedulerLevel OBJECT-TYPE
			SYNTAX INTEGER (0..7 | 255)
			MAX-ACCESS read-only
			STATUS current
			DESCRIPTION
				"Queue sla downstream shaper minimum scheduer level.
				System default 255."
			DEFVAL { 255 }
			::= { sleEponOnuProfileDBAMultiLLidQueueSlaEntry 4 }

		
		-- 1.3.6.1.4.1.6296.101.20.14.2.6.1.5
		sleEponOnuProfileDBAMultiLLidQueueSlaDownMinShaWeight OBJECT-TYPE
			SYNTAX INTEGER (2..32 | 65535)
			MAX-ACCESS read-only
			STATUS current
			DESCRIPTION
				"Queue sla downstream shaper minimum weight.
				System default 65535."
			DEFVAL { 65535 }
			::= { sleEponOnuProfileDBAMultiLLidQueueSlaEntry 5 }

		
		-- 1.3.6.1.4.1.6296.101.20.14.2.6.1.6
		sleEponOnuProfileDBAMutiLLidQueueSlaDownMaxShaBandwidth OBJECT-TYPE
			SYNTAX INTEGER (256..1000000)
			MAX-ACCESS read-only
			STATUS current
			DESCRIPTION
				"Queue sla downstream shaper maximum bandwidth.
				System default 100000"
			DEFVAL { 100000 }
			::= { sleEponOnuProfileDBAMultiLLidQueueSlaEntry 6 }

		
		-- 1.3.6.1.4.1.6296.101.20.14.2.6.1.7
		sleEponOnuProfileDBAMultiLLidQueueSlaDownMaxShaBurstSize OBJECT-TYPE
			SYNTAX INTEGER (1..256)
			MAX-ACCESS read-only
			STATUS current
			DESCRIPTION
				"Queue sla downstream shaper maximum burst size.
				System default 255."
			DEFVAL { 255 }
			::= { sleEponOnuProfileDBAMultiLLidQueueSlaEntry 7 }

		
		-- 1.3.6.1.4.1.6296.101.20.14.2.6.1.8
		sleEponOnuProfileDBAMultiLLidQueueSlaDownMaxShaSchedulerLevel OBJECT-TYPE
			SYNTAX INTEGER (0..7)
			MAX-ACCESS read-only
			STATUS current
			DESCRIPTION
				"Queue sla downstream shaper maximum scheduler level.
				System default 2."
			DEFVAL { 2 }
			::= { sleEponOnuProfileDBAMultiLLidQueueSlaEntry 8 }

		
		-- 1.3.6.1.4.1.6296.101.20.14.2.6.1.9
		sleEponOnuProfileDBAMultiLLidQueueSlaDownMaxShaWeight OBJECT-TYPE
			SYNTAX INTEGER (2..32)
			MAX-ACCESS read-only
			STATUS current
			DESCRIPTION
				"Queue sla downstream shaper maximum weight.
				System default 24."
			DEFVAL { 24 }
			::= { sleEponOnuProfileDBAMultiLLidQueueSlaEntry 9 }

		
		-- 1.3.6.1.4.1.6296.101.20.14.2.6.1.10
		sleEponOnuProfileDBAMultiLLidQueueSlaUpMinShaBandwidth OBJECT-TYPE
			SYNTAX INTEGER (0 | 256..1000000)
			MAX-ACCESS read-only
			STATUS current
			DESCRIPTION
				"Queue sla upstream shaper minimum bandwidth.
				System default 0."
			DEFVAL { 0 }
			::= { sleEponOnuProfileDBAMultiLLidQueueSlaEntry 10 }

		
		-- 1.3.6.1.4.1.6296.101.20.14.2.6.1.11
		sleEponOnuProfileDBAMultiLLidQueueSlaUpMinShaBurstSize OBJECT-TYPE
			SYNTAX INTEGER (1..256 | 65535)
			MAX-ACCESS read-only
			STATUS current
			DESCRIPTION
				"Queue sla upstream shaper minimum bandwidth.
				System default 65535."
			DEFVAL { 65535 }
			::= { sleEponOnuProfileDBAMultiLLidQueueSlaEntry 11 }

		
		-- 1.3.6.1.4.1.6296.101.20.14.2.6.1.12
		sleEponOnuProfileDBAMultiLLidQueueSlaUpMinShaSchedulerLevel OBJECT-TYPE
			SYNTAX INTEGER (0..7 | 255)
			MAX-ACCESS read-write
			STATUS current
			DESCRIPTION
				"Queue sla upstream shaper minimum scheduler level.
				System default 255."
			DEFVAL { 255 }
			::= { sleEponOnuProfileDBAMultiLLidQueueSlaEntry 12 }

		
		-- 1.3.6.1.4.1.6296.101.20.14.2.6.1.13
		sleEponOnuProfileDBAMultiLLidQueueSlaUpMinShaWeight OBJECT-TYPE
			SYNTAX INTEGER (2..32 | 65535)
			MAX-ACCESS read-only
			STATUS current
			DESCRIPTION
				"Queue sla upstream shaper minimum weight.
				System default 65535."
			DEFVAL { 65535 }
			::= { sleEponOnuProfileDBAMultiLLidQueueSlaEntry 13 }

		
		-- 1.3.6.1.4.1.6296.101.20.14.2.6.1.14
		sleEponOnuProfileDBAMultiLLidQueueSlaUpMaxShaBandwidth OBJECT-TYPE
			SYNTAX INTEGER (256..1000000)
			MAX-ACCESS read-write
			STATUS current
			DESCRIPTION
				"Queue sla upstream shaper maximum bandwidth.
				System default 100000."
			DEFVAL { 100000 }
			::= { sleEponOnuProfileDBAMultiLLidQueueSlaEntry 14 }

		
		-- 1.3.6.1.4.1.6296.101.20.14.2.6.1.15
		sleEponOnuProfileDBAMultiLLidQueueSlaUpMaxShaBurstSize OBJECT-TYPE
			SYNTAX INTEGER (1..256)
			MAX-ACCESS read-only
			STATUS current
			DESCRIPTION
				"Queue sla upstream shaper maximum burst size.
				System default 255."
			DEFVAL { 255 }
			::= { sleEponOnuProfileDBAMultiLLidQueueSlaEntry 15 }

		
		-- 1.3.6.1.4.1.6296.101.20.14.2.6.1.16
		sleEponOnuProfileDBAMultiLLidQueueSlaUpMaxShaSchedulerLevel OBJECT-TYPE
			SYNTAX INTEGER (0..7)
			MAX-ACCESS read-write
			STATUS current
			DESCRIPTION
				"Queue sla upstream shaper maximum scheduler level.
				System default 2."
			DEFVAL { 2 }
			::= { sleEponOnuProfileDBAMultiLLidQueueSlaEntry 16 }

		
		-- 1.3.6.1.4.1.6296.101.20.14.2.6.1.17
		sleEponOnuProfileDBAMultiLLidQueueSlaUpMaxShaWeight OBJECT-TYPE
			SYNTAX INTEGER (2..32)
			MAX-ACCESS read-only
			STATUS current
			DESCRIPTION
				"Queue sla upstream shaper maximum weight.
				System default 24."
			DEFVAL { 24 }
			::= { sleEponOnuProfileDBAMultiLLidQueueSlaEntry 17 }

		
		-- 1.3.6.1.4.1.6296.101.20.14.2.7
		sleEponOnuProfileDBAMultiLLidControl OBJECT IDENTIFIER ::= { sleEponOnuProfileDBA 7 }

		
		-- 1.3.6.1.4.1.6296.101.20.14.2.7.1
		sleEponOnuProfileDBAMultiLLidControlRequest OBJECT-TYPE
			SYNTAX INTEGER
				{
				setPonOnuProfileDBAMultillidLinkSla(1),
				noPonOnuProfileDBAMultillidLinkSla(2),
				setPonOnuProfileDBAMultillidQueueSla(3),
				noPonOnuProfileDBAMultillidQueueSla(4),
				noPonOnuProfileDBAMultillidQueueSlaAll(5),
				setPonOnuProfileDBAMultillidLinkOAMRate(6),
				noPonOnuProfileDBAMultillidLinkOAMRate(7)
				}
			MAX-ACCESS read-write
			STATUS current
			DESCRIPTION
				"The request of a user command."
			::= { sleEponOnuProfileDBAMultiLLidControl 1 }

		
		-- 1.3.6.1.4.1.6296.101.20.14.2.7.2
		sleEponOnuProfileDBAMultiLLidControlStatus OBJECT-TYPE
			SYNTAX SleControlStatusType
			MAX-ACCESS read-write
			STATUS current
			DESCRIPTION
				"The status of user command."
			::= { sleEponOnuProfileDBAMultiLLidControl 2 }

		
		-- 1.3.6.1.4.1.6296.101.20.14.2.7.3
		sleEponOnuProfileDBAMultiLLidControlTimer OBJECT-TYPE
			SYNTAX Gauge32
			MAX-ACCESS read-write
			STATUS current
			DESCRIPTION
				"The maximum time for the manager for a long running user command."
			::= { sleEponOnuProfileDBAMultiLLidControl 3 }

		
		-- 1.3.6.1.4.1.6296.101.20.14.2.7.4
		sleEponOnuProfileDBAMultiLLidControlTimeStamp OBJECT-TYPE
			SYNTAX TimeTicks
			MAX-ACCESS read-write
			STATUS current
			DESCRIPTION
				"The time stamp of the last command(end of command)."
			::= { sleEponOnuProfileDBAMultiLLidControl 4 }

		
		-- 1.3.6.1.4.1.6296.101.20.14.2.7.5
		sleEponOnuProfileDBAMultiLLidControlReqResult OBJECT-TYPE
			SYNTAX SleControlRequestResultType
			MAX-ACCESS read-write
			STATUS current
			DESCRIPTION
				"The result of the last user command."
			::= { sleEponOnuProfileDBAMultiLLidControl 5 }

		
		-- 1.3.6.1.4.1.6296.101.20.14.2.7.6
		sleEponOnuProfileDBAMultiLLidControlProfileName OBJECT-TYPE
			SYNTAX OCTET STRING (SIZE (1..64))
			MAX-ACCESS read-write
			STATUS current
			DESCRIPTION
				"Profile name.
				'all' means configure all the onu profile."
			::= { sleEponOnuProfileDBAMultiLLidControl 6 }

		
		-- 1.3.6.1.4.1.6296.101.20.14.2.7.7
		sleEponOnuProfileDBAMultiLLidControlLinkSlaMinShaBandwidth OBJECT-TYPE
			SYNTAX INTEGER (0 | 256..1000000)
			MAX-ACCESS read-write
			STATUS current
			DESCRIPTION
				"Guaranteed Bandwidth(Kbps).
				0 means that we will use the default value."
			DEFVAL { 0 }
			::= { sleEponOnuProfileDBAMultiLLidControl 7 }

		
		-- 1.3.6.1.4.1.6296.101.20.14.2.7.8
		sleEponOnuProfileDBAMultiLLidControlLinkSlaMinShaBurstSize OBJECT-TYPE
			SYNTAX INTEGER (1..256 | 65535)
			MAX-ACCESS read-write
			STATUS current
			DESCRIPTION
				"Minimum Burst Size.
				Default 65535."
			DEFVAL { 65535 }
			::= { sleEponOnuProfileDBAMultiLLidControl 8 }

		
		-- 1.3.6.1.4.1.6296.101.20.14.2.7.9
		sleEponOnuProfileDBAMultiLLidControlLinkSlaMinShaSchedulerLevel OBJECT-TYPE
			SYNTAX INTEGER (0..7 | 255)
			MAX-ACCESS read-write
			STATUS current
			DESCRIPTION
				"Scheduler Level.
				Default 255."
			DEFVAL { 255 }
			::= { sleEponOnuProfileDBAMultiLLidControl 9 }

		
		-- 1.3.6.1.4.1.6296.101.20.14.2.7.10
		sleEponOnuProfileDBAMultiLLidControlLinkSlaMinShaWeight OBJECT-TYPE
			SYNTAX INTEGER (2..32 | 65535)
			MAX-ACCESS read-write
			STATUS current
			DESCRIPTION
				"Weight.
				Default 65535."
			DEFVAL { 0 }
			::= { sleEponOnuProfileDBAMultiLLidControl 10 }

		
		-- 1.3.6.1.4.1.6296.101.20.14.2.7.11
		sleEponOnuProfileDBAMultiLLidControlLinkSlaMaxShaBandwidth OBJECT-TYPE
			SYNTAX INTEGER (256..1000000)
			MAX-ACCESS read-write
			STATUS current
			DESCRIPTION
				"Guaranteed Bandwidth(Kbps)."
			::= { sleEponOnuProfileDBAMultiLLidControl 11 }

		
		-- 1.3.6.1.4.1.6296.101.20.14.2.7.12
		sleEponOnuProfileDBAMultiLLidControlLinkSlaMaxShaBurstSize OBJECT-TYPE
			SYNTAX INTEGER (1..256)
			MAX-ACCESS read-write
			STATUS current
			DESCRIPTION
				"Maximum burst size."
			::= { sleEponOnuProfileDBAMultiLLidControl 12 }

		
		-- 1.3.6.1.4.1.6296.101.20.14.2.7.13
		sleEponOnuProfileDBAMultiLLidControlLinkSlaMaxShaSchedulerLevel OBJECT-TYPE
			SYNTAX INTEGER (0..7)
			MAX-ACCESS read-write
			STATUS current
			DESCRIPTION
				"Scheduler Level."
			::= { sleEponOnuProfileDBAMultiLLidControl 13 }

		
		-- 1.3.6.1.4.1.6296.101.20.14.2.7.14
		sleEponOnuProfileDBAMultiLLidControlLinkSlaMaxShaWeight OBJECT-TYPE
			SYNTAX INTEGER (2..32)
			MAX-ACCESS read-write
			STATUS current
			DESCRIPTION
				"Weight."
			::= { sleEponOnuProfileDBAMultiLLidControl 14 }

		
		-- 1.3.6.1.4.1.6296.101.20.14.2.7.15
		sleEponOnuProfileDBAMultiLLidControlLinkSlaOperate OBJECT-TYPE
			SYNTAX INTEGER
				{
				none(1),
				forceReport(2),
				disableOAMUplift(3)
				}
			MAX-ACCESS read-write
			STATUS current
			DESCRIPTION
				"Onu profile DBA options."
			::= { sleEponOnuProfileDBAMultiLLidControl 15 }

		
		-- 1.3.6.1.4.1.6296.101.20.14.2.7.16
		sleEponOnuProfileDBAMultiLLIdControlLinkSlaPollingLevel OBJECT-TYPE
			SYNTAX INTEGER (0..7)
			MAX-ACCESS read-write
			STATUS current
			DESCRIPTION
				"Polling Interval Select."
			::= { sleEponOnuProfileDBAMultiLLidControl 16 }

		
		-- 1.3.6.1.4.1.6296.101.20.14.2.7.17
		sleEponOnuProfileDBAlMultiLLidControLinkSlaTDMRate OBJECT-TYPE
			SYNTAX INTEGER (0 | 1..4000)
			MAX-ACCESS read-write
			STATUS current
			DESCRIPTION
				"TDM Rate.
				0 means that we will use the default value."
			DEFVAL { 0 }
			::= { sleEponOnuProfileDBAMultiLLidControl 17 }

		
		-- 1.3.6.1.4.1.6296.101.20.14.2.7.18
		sleEponOnuProfileDBAMultiLLidControlLinkSlaTDMGrantLength OBJECT-TYPE
			SYNTAX INTEGER (0 | 84..131072)
			MAX-ACCESS read-write
			STATUS current
			DESCRIPTION
				"TDM grant length.
				0 means that we will use the default value."
			DEFVAL { 0 }
			::= { sleEponOnuProfileDBAMultiLLidControl 18 }

		
		-- 1.3.6.1.4.1.6296.101.20.14.2.7.19
		sleEponOnuProfileDBAMultiLLidControlQueueIndex OBJECT-TYPE
			SYNTAX INTEGER (0..3)
			MAX-ACCESS read-write
			STATUS current
			DESCRIPTION
				"Queue index."
			::= { sleEponOnuProfileDBAMultiLLidControl 19 }

		
		-- 1.3.6.1.4.1.6296.101.20.14.2.7.20
		sleEponOnuProfileDBAMultiLLidControlQueueSlaMinShaBandwidth OBJECT-TYPE
			SYNTAX INTEGER (256..1000000)
			MAX-ACCESS read-write
			STATUS current
			DESCRIPTION
				"Guaranteed Bandwidth(Kbps)."
			::= { sleEponOnuProfileDBAMultiLLidControl 20 }

		
		-- 1.3.6.1.4.1.6296.101.20.14.2.7.21
		sleEponOnuProfileDBAMultiLLidControlQueueSlaMinShaBurstSize OBJECT-TYPE
			SYNTAX INTEGER (1..256)
			MAX-ACCESS read-write
			STATUS current
			DESCRIPTION
				"Minimum Burst Size."
			::= { sleEponOnuProfileDBAMultiLLidControl 21 }

		
		-- 1.3.6.1.4.1.6296.101.20.14.2.7.22
		sleEponOnuProfileDBAMultiLLidControlQueueSlaMinShaSchedulerLevel OBJECT-TYPE
			SYNTAX INTEGER (0..7)
			MAX-ACCESS read-write
			STATUS current
			DESCRIPTION
				"Scheduler Level."
			::= { sleEponOnuProfileDBAMultiLLidControl 22 }

		
		-- 1.3.6.1.4.1.6296.101.20.14.2.7.23
		sleEponOnuProfileDBAMultiLLidControlQueueSlaMinShaWeight OBJECT-TYPE
			SYNTAX INTEGER (2..32)
			MAX-ACCESS read-write
			STATUS current
			DESCRIPTION
				"Weight."
			::= { sleEponOnuProfileDBAMultiLLidControl 23 }

		
		-- 1.3.6.1.4.1.6296.101.20.14.2.7.24
		sleEponOnuProfileDBAMultiLLidControlQueueSlaMaxShaBandwidth OBJECT-TYPE
			SYNTAX INTEGER (256..1000000)
			MAX-ACCESS read-write
			STATUS current
			DESCRIPTION
				"Guaranteed Bandwidth(Kbps)."
			::= { sleEponOnuProfileDBAMultiLLidControl 24 }

		
		-- 1.3.6.1.4.1.6296.101.20.14.2.7.25
		sleEponOnuProfileDBAMultiLLidControlQueueSlaMaxShaBurstSize OBJECT-TYPE
			SYNTAX INTEGER (1..256)
			MAX-ACCESS read-write
			STATUS current
			DESCRIPTION
				"Maximum burst size."
			::= { sleEponOnuProfileDBAMultiLLidControl 25 }

		
		-- 1.3.6.1.4.1.6296.101.20.14.2.7.26
		sleEponOnuProfileDBAMultiLLidControlQueueSlaMaxShaSchedulerLevel OBJECT-TYPE
			SYNTAX INTEGER (0..7)
			MAX-ACCESS read-write
			STATUS current
			DESCRIPTION
				"Scheduler Level."
			::= { sleEponOnuProfileDBAMultiLLidControl 26 }

		
		-- 1.3.6.1.4.1.6296.101.20.14.2.7.27
		sleEponOnuProfileDBAMultiLLidControlQueueSlaMaxShaWeight OBJECT-TYPE
			SYNTAX INTEGER (2..32)
			MAX-ACCESS read-write
			STATUS current
			DESCRIPTION
				"Weight."
			::= { sleEponOnuProfileDBAMultiLLidControl 27 }

		
		-- 1.3.6.1.4.1.6296.101.20.14.2.7.28
		sleEponOnuProfileDBAMultiLLIdControlQueueSlaOperate OBJECT-TYPE
			SYNTAX INTEGER
				{
				upstream(1),
				downstream(2)
				}
			MAX-ACCESS read-write
			STATUS current
			DESCRIPTION
				"Direction of Egress Shaping."
			::= { sleEponOnuProfileDBAMultiLLidControl 28 }

		
		-- 1.3.6.1.4.1.6296.101.20.14.2.7.29
		sleEponOnuProfileDBAMultiLLidControlLinkOAMMaxRate OBJECT-TYPE
			SYNTAX INTEGER (0..25)
			MAX-ACCESS read-write
			STATUS current
			DESCRIPTION
				"Maximum OAM rate."
			::= { sleEponOnuProfileDBAMultiLLidControl 29 }

		
		-- 1.3.6.1.4.1.6296.101.20.14.2.7.30
		sleEponOnuProfileDBAMultiLLidControlLinkOAMMinRate OBJECT-TYPE
			SYNTAX INTEGER (0..10)
			MAX-ACCESS read-write
			STATUS current
			DESCRIPTION
				"Minimum OAM rate."
			::= { sleEponOnuProfileDBAMultiLLidControl 30 }

		
		-- 1.3.6.1.4.1.6296.101.20.14.2.8
		sleEponOnuProfileDBAMultiLLidNotification OBJECT IDENTIFIER ::= { sleEponOnuProfileDBA 8 }

		
		-- 1.3.6.1.4.1.6296.101.20.14.2.8.1
		sleEponOnuProfileDBAMultiLLidLinkSlaChanged NOTIFICATION-TYPE
			OBJECTS { sleEponOnuProfileDBAMultiLLidControlRequest, sleEponOnuProfileDBAMultiLLidControlTimeStamp, sleEponOnuProfileDBAMultiLLidControlReqResult, sleEponOnuProfileDBAMultiLLidControlProfileName }
			STATUS current
			DESCRIPTION 
				"Set ONU profile DBA link sla trap."
			::= { sleEponOnuProfileDBAMultiLLidNotification 1 }

		
		-- 1.3.6.1.4.1.6296.101.20.14.2.8.2
		sleEponOnuProfileDBAMultiLLidQueueSlaChanged NOTIFICATION-TYPE
			OBJECTS { sleEponOnuProfileDBAMultiLLidControlRequest, sleEponOnuProfileDBAMultiLLidControlTimeStamp, sleEponOnuProfileDBAMultiLLidControlReqResult, sleEponOnuProfileDBAMultiLLidControlProfileName, sleEponOnuProfileDBAMultiLLidControlQueueIndex
				 }
			STATUS current
			DESCRIPTION 
				"Onu profile DBA queue sla changed trap."
			::= { sleEponOnuProfileDBAMultiLLidNotification 2 }

		
		-- 1.3.6.1.4.1.6296.101.20.14.2.8.3
		sleEponOnuProfileDBAMultiLLidLinkOAMRateChanged NOTIFICATION-TYPE
			OBJECTS { sleEponOnuProfileDBAMultiLLidControlRequest, sleEponOnuProfileDBAMultiLLidControlTimeStamp, sleEponOnuProfileDBAMultiLLidControlReqResult, sleEponOnuProfileDBAMultiLLidControlProfileName, sleEponOnuProfileDBAMultiLLidControlLinkOAMMaxRate, 
				sleEponOnuProfileDBAMultiLLidControlLinkOAMMinRate }
			STATUS current
			DESCRIPTION 
				"Onu profile DBA link OAM changed trap."
			::= { sleEponOnuProfileDBAMultiLLidNotification 3 }

		
		-- 1.3.6.1.4.1.6296.101.20.15
		sleEponDomain OBJECT IDENTIFIER ::= { sleEpon 15 }

		
		-- 1.3.6.1.4.1.6296.101.20.15.1
		sleEponDomainTable OBJECT-TYPE
			SYNTAX SEQUENCE OF SleEponDomainEntry
			MAX-ACCESS not-accessible
			STATUS current
			DESCRIPTION
				"Description."
			::= { sleEponDomain 1 }

		
		-- 1.3.6.1.4.1.6296.101.20.15.1.1
		sleEponDomainEntry OBJECT-TYPE
			SYNTAX SleEponDomainEntry
			MAX-ACCESS not-accessible
			STATUS current
			DESCRIPTION
				"Description."
			INDEX { sleEponOltIndex, sleEponDomainVlanID }
			::= { sleEponDomainTable 1 }

		
		SleEponDomainEntry ::=
			SEQUENCE { 
				sleEponDomainVlanID
					INTEGER,
				sleEponDomainUnTaggedPorts
					OCTET STRING,
				sleEponDomainMultiUnTaggedPorts
					OCTET STRING
			 }

		-- 1.3.6.1.4.1.6296.101.20.15.1.1.1
		sleEponDomainVlanID OBJECT-TYPE
			SYNTAX INTEGER (1..4094 | 4098)
			MAX-ACCESS read-only
			STATUS current
			DESCRIPTION
				"Pon olt/onu vlan index,4098 is the default vlanid."
			::= { sleEponDomainEntry 1 }

		
		-- 1.3.6.1.4.1.6296.101.20.15.1.1.2
		sleEponDomainUnTaggedPorts OBJECT-TYPE
			SYNTAX OCTET STRING
			MAX-ACCESS read-only
			STATUS current
			DESCRIPTION
				"the port map of vlan ,'.' is not add in vlan,'u' is untagged port,'t' is tagged port.
				"
			::= { sleEponDomainEntry 2 }

		
		-- 1.3.6.1.4.1.6296.101.20.15.1.1.3
		sleEponDomainMultiUnTaggedPorts OBJECT-TYPE
			SYNTAX OCTET STRING
			MAX-ACCESS read-only
			STATUS current
			DESCRIPTION
				"the port map of vlan ,'.' is not add in vlan,'u' is untagged port,'t' is tagged port.
				"
			::= { sleEponDomainEntry 3 }

		
		-- 1.3.6.1.4.1.6296.101.20.15.2
		sleEponDomainControl OBJECT IDENTIFIER ::= { sleEponDomain 2 }

		
		-- 1.3.6.1.4.1.6296.101.20.15.2.1
		sleEponDomainControlRequest OBJECT-TYPE
			SYNTAX INTEGER
				{
				setEponCreateVlan(1),
				setEponDestroyVlan(2),
				setEponVlanAdd(3),
				setEponDefaultVlanAdd(4),
				setEponVlanDel(5),
				setEponDefaultVlanDel(6),
				setEponVlanMultiAdd(7),
				setEponDefaultVlanMultiAdd(8),
				setEponVlanMultiDel(9),
				setEponDefaultVlanMultiDel(10)
				}
			MAX-ACCESS read-write
			STATUS current
			DESCRIPTION
				"The request of a user command."
			::= { sleEponDomainControl 1 }

		
		-- 1.3.6.1.4.1.6296.101.20.15.2.2
		sleEponDomainControlStatus OBJECT-TYPE
			SYNTAX SleControlStatusType
			MAX-ACCESS read-only
			STATUS current
			DESCRIPTION
				"The status of user command."
			::= { sleEponDomainControl 2 }

		
		-- 1.3.6.1.4.1.6296.101.20.15.2.3
		sleEponDomainControlTimer OBJECT-TYPE
			SYNTAX Gauge32
			MAX-ACCESS read-write
			STATUS current
			DESCRIPTION
				"The maximum time for the manager for a long running user command."
			::= { sleEponDomainControl 3 }

		
		-- 1.3.6.1.4.1.6296.101.20.15.2.4
		sleEponDomainControlTimeStamp OBJECT-TYPE
			SYNTAX TimeTicks
			MAX-ACCESS read-only
			STATUS current
			DESCRIPTION
				"The time stamp of the last command(end of command)."
			::= { sleEponDomainControl 4 }

		
		-- 1.3.6.1.4.1.6296.101.20.15.2.5
		sleEponDomainControlReqResult OBJECT-TYPE
			SYNTAX SleControlRequestResultType
			MAX-ACCESS read-only
			STATUS current
			DESCRIPTION
				"The result of the last user command."
			::= { sleEponDomainControl 5 }

		
		-- 1.3.6.1.4.1.6296.101.20.15.2.6
		sleEponDomainControlOltIndex OBJECT-TYPE
			SYNTAX INTEGER (1..64)
			MAX-ACCESS read-write
			STATUS current
			DESCRIPTION
				"OLT index."
			::= { sleEponDomainControl 6 }

		
		-- 1.3.6.1.4.1.6296.101.20.15.2.7
		sleEponDomainControlOnuIndex OBJECT-TYPE
			SYNTAX INTEGER (1..64)
			MAX-ACCESS read-write
			STATUS current
			DESCRIPTION
				"ONU index"
			::= { sleEponDomainControl 7 }

		
		-- 1.3.6.1.4.1.6296.101.20.15.2.8
		sleEponDomainControlVlanID OBJECT-TYPE
			SYNTAX INTEGER (1..4096)
			MAX-ACCESS read-write
			STATUS current
			DESCRIPTION
				"OLT vlan index,default vlan ID 4098."
			::= { sleEponDomainControl 8 }

		
		-- 1.3.6.1.4.1.6296.101.20.15.2.9
		sleEponDomainControlUnTaggedPorts OBJECT-TYPE
			SYNTAX INTEGER
				{
				tag(0),
				untag(1)
				}
			MAX-ACCESS read-write
			STATUS current
			DESCRIPTION
				"Portlist for members of this Vlan they will send only untagged frames.
				The octet string is a list of pairs of octets each identify
				an sleBridgePortIndex. The least significant byte is the second
				octet.
				"
			::= { sleEponDomainControl 9 }

		
		-- 1.3.6.1.4.1.6296.101.20.15.3
		sleEponDomainNotification OBJECT IDENTIFIER ::= { sleEponDomain 3 }

		
		-- 1.3.6.1.4.1.6296.101.20.15.3.1
		sleEponDomainVlanCreate NOTIFICATION-TYPE
			OBJECTS { sleEponDomainControlReqResult, sleEponDomainControlRequest, sleEponDomainControlTimeStamp, sleEponDomainControlVlanID }
			STATUS current
			DESCRIPTION 
				"Description."
			::= { sleEponDomainNotification 1 }

		
		-- 1.3.6.1.4.1.6296.101.20.15.3.2
		sleEponDomainDestroyVlan NOTIFICATION-TYPE
			OBJECTS { sleEponDomainControlReqResult, sleEponDomainControlRequest, sleEponDomainControlTimeStamp, sleEponDomainControlVlanID }
			STATUS current
			DESCRIPTION 
				"Description."
			::= { sleEponDomainNotification 2 }

		
		-- 1.3.6.1.4.1.6296.101.20.15.3.3
		sleEponDomainVlanAdd NOTIFICATION-TYPE
			OBJECTS { sleEponDomainControlReqResult, sleEponDomainControlRequest, sleEponDomainControlTimeStamp, sleEponDomainControlOnuIndex, sleEponDomainControlVlanID
				 }
			STATUS current
			DESCRIPTION 
				"Description."
			::= { sleEponDomainNotification 3 }

		
		-- 1.3.6.1.4.1.6296.101.20.15.3.4
		sleEponDomainDefaultVlanAdd NOTIFICATION-TYPE
			OBJECTS { sleEponDomainControlReqResult, sleEponDomainControlRequest, sleEponDomainControlTimeStamp, sleEponDomainControlOnuIndex, sleEponDomainControlVlanID
				 }
			STATUS current
			DESCRIPTION 
				"Description."
			::= { sleEponDomainNotification 4 }

		
		-- 1.3.6.1.4.1.6296.101.20.15.3.5
		sleEponDomainVlanDel NOTIFICATION-TYPE
			OBJECTS { sleEponDomainControlReqResult, sleEponDomainControlRequest, sleEponDomainControlTimeStamp, sleEponDomainControlOnuIndex, sleEponDomainControlVlanID
				 }
			STATUS current
			DESCRIPTION 
				"Description."
			::= { sleEponDomainNotification 5 }

		
		-- 1.3.6.1.4.1.6296.101.20.15.3.6
		sleEponDomainDefaultVlanDel NOTIFICATION-TYPE
			OBJECTS { sleEponDomainControlReqResult, sleEponDomainControlRequest, sleEponDomainControlTimeStamp, sleEponDomainControlOnuIndex, sleEponDomainControlVlanID
				 }
			STATUS current
			DESCRIPTION 
				"Description."
			::= { sleEponDomainNotification 6 }

		
		-- 1.3.6.1.4.1.6296.101.20.15.3.7
		sleEponDomainVlanMultiAdd NOTIFICATION-TYPE
			OBJECTS { sleEponDomainControlReqResult, sleEponDomainControlRequest, sleEponDomainControlTimeStamp, sleEponDomainControlOnuIndex, sleEponDomainControlVlanID
				 }
			STATUS current
			DESCRIPTION 
				"Description."
			::= { sleEponDomainNotification 7 }

		
		-- 1.3.6.1.4.1.6296.101.20.15.3.8
		sleEponDomainDefaultVlanMultiAdd NOTIFICATION-TYPE
			OBJECTS { sleEponDomainControlReqResult, sleEponDomainControlRequest, sleEponDomainControlTimeStamp, sleEponDomainControlOnuIndex, sleEponDomainControlVlanID
				 }
			STATUS current
			DESCRIPTION 
				"Description."
			::= { sleEponDomainNotification 8 }

		
		-- 1.3.6.1.4.1.6296.101.20.15.3.9
		sleEponDomainVlanMultiDel NOTIFICATION-TYPE
			OBJECTS { sleEponDomainControlReqResult, sleEponDomainControlRequest, sleEponDomainControlTimeStamp, sleEponDomainControlOnuIndex, sleEponDomainControlVlanID
				 }
			STATUS current
			DESCRIPTION 
				"Description."
			::= { sleEponDomainNotification 9 }

		
		-- 1.3.6.1.4.1.6296.101.20.15.3.10
		sleEponDomainDefaultVlanMultiDel NOTIFICATION-TYPE
			OBJECTS { sleEponDomainControlReqResult, sleEponDomainControlRequest, sleEponDomainControlTimeStamp, sleEponDomainControlOnuIndex, sleEponDomainControlVlanID
				 }
			STATUS current
			DESCRIPTION 
				"Description."
			::= { sleEponDomainNotification 10 }

		
		-- 1.3.6.1.4.1.6296.101.20.16
		sleEponOltRedundancy OBJECT IDENTIFIER ::= { sleEpon 16 }

		
		-- 1.3.6.1.4.1.6296.101.20.16.1
		sleEponOltRedundancyTable OBJECT-TYPE
			SYNTAX SEQUENCE OF SleEponOltRedundancyEntry
			MAX-ACCESS not-accessible
			STATUS current
			DESCRIPTION
				"Description."
			::= { sleEponOltRedundancy 1 }

		
		-- 1.3.6.1.4.1.6296.101.20.16.1.1
		sleEponOltRedundancyEntry OBJECT-TYPE
			SYNTAX SleEponOltRedundancyEntry
			MAX-ACCESS not-accessible
			STATUS current
			DESCRIPTION
				"Description."
			INDEX { sleEponOltRedundancyMaste }
			::= { sleEponOltRedundancyTable 1 }

		
		SleEponOltRedundancyEntry ::=
			SEQUENCE { 
				sleEponOltRedundancyMaste
					Integer32,
				sleEponOltRedundancyGroupID
					INTEGER,
				sleEponOltRedundancyTrunkID
					Integer32,
				sleEponOltRedundancyMasteStatus
					INTEGER,
				sleEponOltRedundancySlave
					Integer32,
				sleEponOltRedundancySlaveStatus
					INTEGER,
				sleEponOltRedundancyWtrValue
					Integer32,
				sleEponOltRedundancyRemainTime
					Integer32,
				sleEponOltRedundancyLastReason
					INTEGER,
				sleEponOltRedundancyHoldOffTime
					Integer32
			 }

		-- 1.3.6.1.4.1.6296.101.20.16.1.1.1
		sleEponOltRedundancyMaste OBJECT-TYPE
			SYNTAX Integer32 (1..24)
			MAX-ACCESS read-only
			STATUS current
			DESCRIPTION
				"Redundancy Master OLT_ID."
			::= { sleEponOltRedundancyEntry 1 }

		
		-- 1.3.6.1.4.1.6296.101.20.16.1.1.2
		sleEponOltRedundancyGroupID OBJECT-TYPE
			SYNTAX INTEGER (1..4)
			MAX-ACCESS read-only
			STATUS current
			DESCRIPTION
				"Redundancy Group ID (1-4)."
			::= { sleEponOltRedundancyEntry 2 }

		
		-- 1.3.6.1.4.1.6296.101.20.16.1.1.3
		sleEponOltRedundancyTrunkID OBJECT-TYPE
			SYNTAX Integer32 (0..13 | 255)
			MAX-ACCESS read-only
			STATUS current
			DESCRIPTION
				"Redundancy trunk ID 0-13,disable is 255."
			::= { sleEponOltRedundancyEntry 3 }

		
		-- 1.3.6.1.4.1.6296.101.20.16.1.1.4
		sleEponOltRedundancyMasteStatus OBJECT-TYPE
			SYNTAX INTEGER
				{
				none(0),
				active(1),
				standby(2),
				pending(3),
				unknown(4),
				active_los(5),
				standby_los(6)
				}
			MAX-ACCESS read-only
			STATUS current
			DESCRIPTION
				"Redundancy Master status."
			::= { sleEponOltRedundancyEntry 4 }

		
		-- 1.3.6.1.4.1.6296.101.20.16.1.1.5
		sleEponOltRedundancySlave OBJECT-TYPE
			SYNTAX Integer32
			MAX-ACCESS read-only
			STATUS current
			DESCRIPTION
				"Redundancy Slave OLT_ID."
			::= { sleEponOltRedundancyEntry 5 }

		
		-- 1.3.6.1.4.1.6296.101.20.16.1.1.6
		sleEponOltRedundancySlaveStatus OBJECT-TYPE
			SYNTAX INTEGER
				{
				none(0),
				active(1),
				standby(2),
				pending(3),
				unknown(4),
				active_los(5),
				standby_los(6)
				}
			MAX-ACCESS read-only
			STATUS current
			DESCRIPTION
				"Redundancy Slave status."
			::= { sleEponOltRedundancyEntry 6 }

		
		-- 1.3.6.1.4.1.6296.101.20.16.1.1.7
		sleEponOltRedundancyWtrValue OBJECT-TYPE
			SYNTAX Integer32 (1..60)
			MAX-ACCESS read-only
			STATUS current
			DESCRIPTION
				"WTR Value(Unit:min,1-60), -1 is invalid value."
			::= { sleEponOltRedundancyEntry 7 }

		
		-- 1.3.6.1.4.1.6296.101.20.16.1.1.8
		sleEponOltRedundancyRemainTime OBJECT-TYPE
			SYNTAX Integer32
			MAX-ACCESS read-write
			STATUS current
			DESCRIPTION
				"Remain time Value(Unit:sec)"
			::= { sleEponOltRedundancyEntry 8 }

		
		-- 1.3.6.1.4.1.6296.101.20.16.1.1.9
		sleEponOltRedundancyLastReason OBJECT-TYPE
			SYNTAX INTEGER
				{
				none(0),
				manualSwitch(1),
				losOfActive(2),
				slotRemoved(3),
				slotRestart(4),
				autoDetect(5),
				unknown(6)
				}
			MAX-ACCESS read-only
			STATUS current
			DESCRIPTION
				"Olt Redundancy Last Reason."
			::= { sleEponOltRedundancyEntry 9 }

		
		-- 1.3.6.1.4.1.6296.101.20.16.1.1.10
		sleEponOltRedundancyHoldOffTime OBJECT-TYPE
			SYNTAX Integer32 (0..10)
			MAX-ACCESS read-write
			STATUS current
			DESCRIPTION
				"Holdoff time range:0-10(default:0ms)."
			::= { sleEponOltRedundancyEntry 10 }

		
		-- 1.3.6.1.4.1.6296.101.20.16.2
		sleEponOltRedundancyControl OBJECT IDENTIFIER ::= { sleEponOltRedundancy 2 }

		
		-- 1.3.6.1.4.1.6296.101.20.16.2.1
		sleEponOltRedundancyControlRequest OBJECT-TYPE
			SYNTAX INTEGER
				{
				setEponOltRedundancy(1),
				noEponOltRedundancy(2),
				setEponOltSwitchoverForceGroup(3),
				setEponOltRedundancyHoldOffTime(4)
				}
			MAX-ACCESS read-write
			STATUS current
			DESCRIPTION
				"The request of a user command."
			::= { sleEponOltRedundancyControl 1 }

		
		-- 1.3.6.1.4.1.6296.101.20.16.2.2
		sleEponOltRedundancyControlStatus OBJECT-TYPE
			SYNTAX SleControlStatusType
			MAX-ACCESS read-only
			STATUS current
			DESCRIPTION
				"The status of user command."
			::= { sleEponOltRedundancyControl 2 }

		
		-- 1.3.6.1.4.1.6296.101.20.16.2.3
		sleEponOltRedundancyControlTimer OBJECT-TYPE
			SYNTAX Gauge32
			MAX-ACCESS read-write
			STATUS current
			DESCRIPTION
				"The maximum time for the manager for a long running user command."
			::= { sleEponOltRedundancyControl 3 }

		
		-- 1.3.6.1.4.1.6296.101.20.16.2.4
		sleEponOltRedundancyControlTimeStamp OBJECT-TYPE
			SYNTAX TimeTicks
			MAX-ACCESS read-only
			STATUS current
			DESCRIPTION
				"The time stamp of the last command(end of command)."
			::= { sleEponOltRedundancyControl 4 }

		
		-- 1.3.6.1.4.1.6296.101.20.16.2.5
		sleEponOltRedundancyControlReqResult OBJECT-TYPE
			SYNTAX SleControlRequestResultType
			MAX-ACCESS read-only
			STATUS current
			DESCRIPTION
				"The result of the last user command."
			::= { sleEponOltRedundancyControl 5 }

		
		-- 1.3.6.1.4.1.6296.101.20.16.2.6
		sleEponOltRedundancyControlGroupID OBJECT-TYPE
			SYNTAX INTEGER (1..4)
			MAX-ACCESS read-write
			STATUS current
			DESCRIPTION
				"Redundancy Group ID (1-4)."
			::= { sleEponOltRedundancyControl 6 }

		
		-- 1.3.6.1.4.1.6296.101.20.16.2.7
		sleEponOltRedundancyControlTrunkID OBJECT-TYPE
			SYNTAX INTEGER (0..13 | 255)
			MAX-ACCESS read-write
			STATUS current
			DESCRIPTION
				"Redundancy trunk ID 0-13,disable is 255."
			::= { sleEponOltRedundancyControl 7 }

		
		-- 1.3.6.1.4.1.6296.101.20.16.2.8
		sleEponOltRedundancyControlMaster OBJECT-TYPE
			SYNTAX INTEGER
			MAX-ACCESS read-write
			STATUS current
			DESCRIPTION
				"Redundancy Master OLT_ID."
			::= { sleEponOltRedundancyControl 8 }

		
		-- 1.3.6.1.4.1.6296.101.20.16.2.9
		sleEponOltRedundancyControlSlave OBJECT-TYPE
			SYNTAX INTEGER
			MAX-ACCESS read-write
			STATUS current
			DESCRIPTION
				"Redundancy Slave OLT_ID."
			::= { sleEponOltRedundancyControl 9 }

		
		-- 1.3.6.1.4.1.6296.101.20.16.2.10
		sleEponOltRedundancyControlWtrValue OBJECT-TYPE
			SYNTAX INTEGER (1..60)
			MAX-ACCESS read-write
			STATUS current
			DESCRIPTION
				"WTR value."
			::= { sleEponOltRedundancyControl 10 }

		
		-- 1.3.6.1.4.1.6296.101.20.16.2.11
		sleEponOltRedundancyControlHoldOffTime OBJECT-TYPE
			SYNTAX Integer32 (0..10)
			MAX-ACCESS read-write
			STATUS current
			DESCRIPTION
				"Holdoff time range:0-10(default:0ms)."
			::= { sleEponOltRedundancyControl 11 }

		
		-- 1.3.6.1.4.1.6296.101.20.16.3
		sleEponOltRedundancyNotification OBJECT IDENTIFIER ::= { sleEponOltRedundancy 3 }

		
		-- 1.3.6.1.4.1.6296.101.20.16.3.1
		sleEponOltRedundancyChanged NOTIFICATION-TYPE
			OBJECTS { sleEponOltRedundancyControlWtrValue, sleEponOltRedundancyControlSlave, sleEponOltRedundancyControlMaster, sleEponOltRedundancyControlTrunkID, sleEponOltRedundancyControlGroupID, 
				sleEponOltRedundancyReqResult, sleEponOltRedundancyTimeStamp, sleEponOltRedundancyRequest }
			STATUS current
			DESCRIPTION 
				"Description."
			::= { sleEponOltRedundancyNotification 1 }

		
		-- 1.3.6.1.4.1.6296.101.20.16.3.2
		sleEponOltRedundancySwitchoverForceGroup NOTIFICATION-TYPE
			OBJECTS { sleEponOltRedundancyRequest, sleEponOltRedundancyReqResult, sleEponOltRedundancyTimeStamp, sleEponOltRedundancyControlGroupID }
			STATUS current
			DESCRIPTION 
				"Description."
			::= { sleEponOltRedundancyNotification 2 }

		
		-- 1.3.6.1.4.1.6296.101.20.16.3.3
		sleEponOltRedundancyHoldOffTimeChanged NOTIFICATION-TYPE
			OBJECTS { sleEponOltRedundancyControlRequest, sleEponOltRedundancyControlTimeStamp, sleEponOltRedundancyControlReqResult, sleEponOltRedundancyControlGroupID, sleEponOltRedundancyControlHoldOffTime
				 }
			STATUS current
			DESCRIPTION 
				"Description."
			::= { sleEponOltRedundancyNotification 3 }

		
		-- 1.3.6.1.4.1.6296.101.20.17
		sleEponGroup OBJECT-GROUP
			OBJECTS { sleEponOltControlRequest, sleEponOltControlStatus, sleEponOltControlTimer, sleEponOltControlTimeStamp, sleEponOltControlReqResult, 
				sleEponOltControlOltIndex, sleEponOltControlRegMode, sleEponOltControlEncryptionPolicy, sleEponOltControlP2pAccessControl, sleEponOltControlDbaInternal, 
				sleEponOltControlDbaCycle, sleEponOltControlDbaDiscoveryFrequency, sleEponOltControlDbaDiscoveryLength, sleEponOnuControlRequest, sleEponOnuControlStatus, 
				sleEponOnuControlTimer, sleEponOnuControlTimeStamp, sleEponOnuControlReqResult, sleEponOnuControlOltIndex, sleEponOnuControlMacAddress, 
				sleEponOnuControlRegMode, sleEponOnuControlDescription, sleEponOnuControlProfile, sleEponProfileControlRequest, sleEponProfileControlStatus, 
				sleEponProfileControlTimer, sleEponProfileControlTimeStamp, sleEponProfileControlReqResult, sleEponProfileControlName, sleEponProfileControlDPDownMaxBandwidth, 
				sleEponProfileControlDPDownMaxBurstSize, sleEponProfileControlDPP2pMaxBandwidth, sleEponProfileControlDPP2pMaxBurstSize, sleEponProfileControlSlaGuaranteedBandwidth, sleEponProfileControlSlaPlatoClass, 
				sleEponProfileControlSlaPlatoGuaranteedBandwidth1m, sleEponProfileControlSlaPlatoGuaranteedBandwdith64k, sleEponProfileControlSlaPlatoBestEffortBandwidth1m, sleEponProfileControlSlaPlatoBestEffortBandwidth64k, sleEponProfileControlSlaPlatoDelayLevel, 
				sleEponAlarmControlRequest, sleEponAlarmControlStatus, sleEponAlarmControlTimer, sleEponAlarmControlTimeStamp, sleEponAlarmControlReqResult, 
				sleEponAlarmControlOltIndex, sleEponAlarmControlBadEncryption, sleEponAlarmControlDyingGasp, sleEponAlarmControlLlidMismatch, sleEponAlarmControlOnuRegistrationError, 
				sleEponOnuControlOnuIndex, sleEponOnuControlOnuStatus, sleEponStatsOltControlRequest, sleEponStatsOltControlStatus, sleEponStatsOltControlTimer, 
				sleEponStatsOltControlTimeStamp, sleEponStatsOltControlReqResult, sleEponStatsOltControlOltIndex, sleEponStatsOltControlChannelIndex, sleEponOnuControlLoopbackProvision, 
				sleEponOltControlOltStatus, sleEponAlarmControlTooManyOnuRegistration, sleEponProfileQueueControlRequest, sleEponProfileQueueControlStatus, sleEponProfileQueueControlTimer, 
				sleEponProfileQueueControlTimeStamp, sleEponProfileQueueControlReqResult, sleEponProfileQueueControlProfileIndex, sleEponProfileQueueControlQueueIndex, sleEponProfileQueueControlQPUpQueue, 
				sleEponProfileQueueControlQPUpMaxBandwidth, sleEponProfileQueueControlQPUpMAxBurstSize, sleEponProfileQueueControlQPDownQueue, sleEponProfileQueueControlQPDownMaxBandwidth, sleEponProfileQueueControlQPDownMAxBurstSize, 
				sleEponOltControlProfile, sleEponProfilePortControlRequest, sleEponProfilePortControlStatus, sleEponProfilePortControlTimer, sleEponProfilePortControlTimeStamp, 
				sleEponProfilePortControlReqResult, sleEponProfilePortControlAdminStatus, sleEponProfilePortControlNego, sleEponProfilePortControlSpeed, sleEponProfilePortControlMaxHost, 
				sleEponProfileVlanControlRequest, sleEponProfileVlanControlStatus, sleEponProfileVlanControlTimer, sleEponProfileVlanControlTimeStamp, sleEponProfileVlanControlReqResult, 
				sleEponProfileVlanControlVlanIndex, sleEponProfileVlanControlVlanEgressPorts, sleEponProfileVlanControlVlanUntaggedPorts, sleEponProfilePortControlPvid, sleEponProfilePortControlEgressRateLimit, 
				sleEponProfilePortControlIngressRateLimit, sleEponProfilePortControlIngressRateLimitMode, sleEponOnuPortControlReqResult, sleEponOnuPortControlOltIndex, sleEponOnuPortControlOnuIndex, 
				sleEponOnuPortControlPortIndex, sleEponOnuPortControlRequest, sleEponOnuPortControlStatus, sleEponOnuPortControlTimer, sleEponOnuPortControlTimeStamp, 
				sleEponOnuClassificationControlRequest, sleEponOnuClassificationControlStatus, sleEponOnuClassificationControlTimer, sleEponOnuClassificationControlTimeStamp, sleEponOnuClassificationControlProtoTypeNum, 
				sleEponOnuClassificationControlL3Addr, sleEponOnuClassificationControlReqResult, sleEponOnuClassificationControlName, sleEponOnuClassificationControlTrafficDirection, sleEponOnuClassificationControlLayer, 
				sleEponOnuClassificationControlEtherType, sleEponProfileVlanControlProfileIndex, sleEponProfileClassificationControlQueue, sleEponProfileClassificationControlReqResult, sleEponProfileClassificationControlProfileIndex, 
				sleEponProfileClassificationControlClassificationIndex, sleEponProfileClassificationControlMatchAction, sleEponProfileClassificationControlRequest, sleEponProfileClassificationControlStatus, sleEponProfileClassificationControlTimer, 
				sleEponProfileClassificationControlTimeStamp, sleEponOltIndex, sleEponOltRegMode, sleEponOltStatus, sleEponOltEncryptionPolicy, 
				sleEponOltP2pAccessControl, sleEponOltDbaInternal, sleEponOltDbaCycle, sleEponOltDbaDiscoveryFrequency, sleEponOltDbaDiscoveryLength, 
				sleEponOltProfile, sleEponOltTxFault, sleEponOltLossOfSignal, sleEponOltAdminRegMode, sleEponOltSC, 
				sleEponOltSCAutoOnuBlock, sleEponOltControlSC, sleEponOltControlSCAutoOnuBlock, sleEponOltControlUpgradeFilename, sleEponOnuIndex, 
				sleEponOnuLlid, sleEponOnuRegMode, sleEponOnuStatus, sleEponOnuMacAddress, sleEponOnuRtt, 
				sleEponOnuDescription, sleEponOnuProfile, sleEponOnuLoopbackProvision, sleEponOnuVendor, sleEponOnuFirmwareRev, 
				sleEponOnuControlTxPowerOffTimer, sleEponOnuVlanIndex, sleEponOnuVlanEgressPorts, sleEponOnuVlanUntaggedPorts, sleEponOnuPortIndex, 
				sleEponOnuPortAdminStatus, sleEponOnuPortOperStatus, sleEponOnuPortNego, sleEponOnuPortSpeed, sleEponOnuPortDuplex, 
				sleEponOnuPortMaxHost, sleEponOnuPortPvid, sleEponOnuPortIngressRateLimitMode, sleEponOnuPortIngressRateLimit, sleEponOnuPortEgressRateLimit, 
				sleEponOnuPortFlowControl, sleEponOnuFdbMacAddress, sleEponOnuFdbType, sleEponOnuFdbPermission, sleEponOnuFdbControlRequest, 
				sleEponOnuFdbControlStatus, sleEponOnuFdbControlTimer, sleEponOnuFdbControlTimeStamp, sleEponOnuFdbControlReqResult, sleEponOnuFdbControlOltIndex, 
				sleEponOnuFdbControlOnuIndex, sleEponOnuFdbControlType, sleEponOnuUserMacIndex, sleEponOnuUserMacMacAddress, sleEponOnuUserMacUsedTime, 
				sleEponProfileIndex, sleEponProfileName, sleEponProfileDPDownMaxBandwidth, sleEponProfileDPDownMaxBurstSize, sleEponProfileDPP2pMaxBandwidth, 
				sleEponProfileDPP2pMaxBurstSize, sleEponProfileSlaGuaranteedBandwidth, sleEponProfileSlaBestEffortBandwidth, sleEponProfileSlaPlatoClass, sleEponProfileSlaPlatoMinBandwidth1m, 
				sleEponProfileSlaPlatoMinBandwdith64k, sleEponProfileSlaPlatoMaxBandwidth1m, sleEponProfileSlaPlatoMaxBandwidth64k, sleEponProfileSlaPlatoDelayLevel, sleEponProfileIgmpFilter, 
				sleEponProfileIgmpSnooping, sleEponProfileSTPenable, sleEponProfileControlExtendMtu, sleEponProfileControlIgmpFilter, sleEponProfileControlSnooping, 
				sleEponProfileControlSTPenable, sleEponProfileQueueIndex, sleEponProfileQueueQPUpQueue, sleEponProfileQueueQPUpMaxBandwidth, sleEponProfileQueueQPUpMAxBurstSize, 
				sleEponProfileQueueQPDownQueue, sleEponProfileQueueQPDownMaxBandwidth, sleEponProfileQueueQPDownMAxBurstSize, sleEponProfileQueueQLimitUpBlockSize, sleEponProfileQueueQLimitDownBlockSize, 
				sleEponProfileQueueControlLimitFlag, sleEponProfileQueueControlBlockSize0, sleEponProfileQueueControlBlockSize1, sleEponProfileQueueControlBlockSize2, sleEponProfileQueueControlBlockSize3, 
				sleEponProfileVlanIndex, sleEponProfileVlanEgressPorts, sleEponProfileVlanUntaggedPorts, sleEponProfilePortIndex, sleEponProfilePortAdminStatus, 
				sleEponProfilePortNego, sleEponProfilePortSpeed, sleEponProfilePortduplex, sleEponProfilePortMaxHost, sleEponProfilePortPvid, 
				sleEponProfilePortIngressRateLimitMode, sleEponProfilePortIngressRateLimit, sleEponProfilePortEgressRateLimit, sleEponProfilePortFlowControl, sleEponProfilePortControlFlowControl, 
				sleEponProfileClassificationIndex, sleEponProfileClassificationMatchAction, sleEponProfileClassificationQueue, sleEponAlarmBadEncryption, sleEponAlarmDyingGasp, 
				sleEponAlarmLlidMismatch, sleEponAlarmOnuRegistrationError, sleEponAlarmTooManyOnuRegistration, sleEponStatsOltInOctets, sleEponStatsOltInPkts, 
				sleEponStatsOltInPause, sleEponStatsOltInErroredFrame, sleEponStatsOltInUnicastPkts, sleEponstatsOltInBroadcastPkts, sleEponStatsOltInMulticastPkts, 
				sleEponStatsOltOutOctets, sleEponStatsOltOutPkts, sleEponStatsOltOutPause, sleEponStatsOltOutDropped, sleEponStatsOltOutUnicastPkts, 
				sleEponstatsOltOutBroadcastPkts, sleEponStatsOltOutMulticastPkts, sleEponStatsOltPonInOctets, sleEponStatsOltPonInPkts, sleEponStatsOltPonInPause, 
				sleEponStatsOltPonInErroredFrame, sleEponStatsOltPonInUnicastPkts, sleEponstatsOltPonInBroadcastPkts, sleEponStatsOltPonInMulticastPkts, sleEponStatsOltPonOutOctets, 
				sleEponStatsOltPonOutPkts, sleEponStatsOltPonOutPause, sleEponStatsOltPonOutDropped, sleEponStatsOltPonOutUnicastPkts, sleEponstatsOltPonOutBroadcastPkts, 
				sleEponStatsOltPonOutMulticastPkts, sleEponStatsOltChannelInOctets, sleEponStatsOltChannelInDataOctets, sleEponStatsOltChannelInPkts, sleEponStatsOltChannelInMulticastPkts, 
				sleEponStatsOltChannelInBroadcastPkts, sleEponStatsOltChannelInErrorOctets, sleEponStatsOltChannelInErrorPkts, sleEponStatsOltChannelOutOctets, sleEponStatsOltChannelOutPkts, 
				sleEponStatsOltChannelOutPolicerDroppedPkts, sleEponStatsOltChannelOutMismatchDroppedPkts, sleEponStatsOltChannelOutMulticastPkts, sleEponStatsOltChannelOutBroadcastPkts, sleEponStatsOltChannelFCS, 
				sleEponStatsOltChannelInRangeLengthErrors, sleEponStatsOltChannelFrameTooLongErrors, sleEponStatsOltChannelInUnicastPkts, sleEponStatsOltChannelOutUnicastPkts, sleEponStatsOnuPortInOctets, 
				sleEponStatsOnuPortInPkts, sleEponStatsOnuPortInUcastPkts, sleEponStatsOnuPortInBcastPkts, sleEponStatsOnuPortInMcastPkts, sleEponStatsOnuPortOutOctets, 
				sleEponStatsOnuPortOutPkts, sleEponStatsOnuPortOutUcastPkts, sleEponStatsOnuPortOutBcastPkts, sleEponStatsOnuPortOutMcastPkts, sleEponOnuClassificationIndex, 
				sleEponOnuClassificationName, sleEponOnuClassificationTrafficDirection, sleEponOnuClassificationLayer, sleEponOnuClassificationEtherType, sleEponOnuClassificationProtoTypeNum, 
				sleEponOnuClassificationL3Addr, sleEponOnuClassificationL4Num, sleEponVlanOltVlanMode, sleEponVlanOltVlanNestedStack, sleEponVlanOltVlanPrefix, 
				sleEponVlanOltVlanSuffix, sleEponVlanOltVlanTag, sleEponVlanOltVlanEtherType, sleEponVlanOltVlanControlRequest, sleEponVlanOltVlanControlStatus, 
				sleEponVlanOltVlanControlTimer, sleEponVlanOltVlanControlTimeStamp, sleEponVlanOltVlanControlReqResult, sleEponVlanOltVlanControlOltIndex, sleEponVlanOltVlanControlOnuIndex, 
				sleEponVlanOltVlanControlMode, sleEponVlanOltVlanControlNestedStack, sleEponVlanOltVlanControlPrefix, sleEponVlanOltVlanControlSuffix, sleEponVlanOltVlanControlVlanTag, 
				sleEponVlanOltVlanControlEtherType, sleEponVlanOnuVlanUpVlanTag, sleEponVlanOnuVlanUpEtherType, sleEponVlanOnuVlanUpPriority, sleEponVlanOnuVlanDownVlanTag, 
				sleEponVlanOnuVlanDownPriority, sleEponVlanOnuVlanControlRequest, sleEponVlanOnuVlanControlStatus, sleEponVlanOnuVlanControlTimer, sleEponVlanOnuVlanControlTimeStamp, 
				sleEponVlanOnuVlanControlReqResult, sleEponVlanOnuVlanControlOltIndex, sleEponVlanOnuVlanControlOnuIndex, sleEponVlanOnuVlanControlUpVlanTag, sleEponVlanOnuVlanControlUpEtherType, 
				sleEponVlanOnuVlanControlUpPriority, sleEponVlanOnuVlanControlDownPriority, sleEponProfileControlIndex, sleEponOnuControlUpgradePath, sleEponProfileControlSlaBestEffortBandwidth, 
				sleEponProfilePortControlProfileIndex, sleEponProfilePortControlPortIndex, sleEponProfilePortControlDuplex, sleEponOnuClassificationControlL4Num, sleEponVlanOnuVlanControlDownVlanTag, 
				sleEponVlanOnuVlanUpMode, sleEponVlanOnuVlanDownMode, sleEponVlanOnuVlanControlUpMode, sleEponProfileQueueControlBlockSize4, sleEponProfileQueueControlBlockSize5, 
				sleEponProfileQueueControlBlockSize6, sleEponProfileQueueControlBlockSize7, sleEponVlanOnuVlanControlDownMode, sleEponProfileUNIQueueUpMaxBandwidth, sleEponProfileUNIQueueUpMaxBurstSize, 
				sleEponProfileUNIQueueDownMaxBandwidth, sleEponProfileUNIQueueDownMaxBurstSize, sleEponProfileUNIQueueControlRequest, sleEponProfileUNIQueueControlStatus, sleEponProfileUNIQueueControlTimer, 
				sleEponProfileUNIQueueControlTimeStamp, sleEponProfileUNIQueueControlReqResult, sleEponProfileUNIQueueControlProfileIndex, sleEponProfileUNIQueueControlUpMaxBandwidth, sleEponProfileUNIQueueControlUpMaxBurstSize, 
				sleEponProfileUNIQueueControlDownMaxBandwidth, sleEponProfileUNIQueueControlDownMaxBurstSize, sleEponPTimeStatsPortSaveTime, sleEponPTimeStatsPortHourInOctets, sleEponPTimeStatsPortHourOutOctets, 
				sleEponPTimeStatsPortDayInOctets, sleEponPTimeStatsPortDayOutOctets, sleEponPTimeStatsOltSaveTime, sleEponPTimeStatsOltHourInOctets, sleEponPTimeStatsOltHourOutOctets, 
				sleEponPTimeStatsOltDayInOctets, sleEponPTimeStatsOltDayOutOctets, sleEponPTimeStatsOnuSaveTime, sleEponPTimeStatsOnuHourInOctets, sleEponPTimeStatsOnuHourOutOctets, 
				sleEponPTimeStatsOnuDayInOctets, sleEponPTimeStatsOnuDayOutOctets, sleEponPTimeStatsControlRequest, sleEponPTimeStatsControlStatus, sleEponPTimeStatsControlTimer, 
				sleEponPTimeStatsControlTimeStamp, sleEponPTimeStatsControlReqResult, sleEponPTimeStatsServiceActivity, sleEponPTimeStatsControlServiceActivity, sleEponOnuSubscriberCurrentIpAddress, 
				sleEponOnuSubscriberCurrentMacAddress, sleEponOnuSubscriberControlRequest, sleEponOnuSubscriberControlStatus, sleEponOnuSubscriberControlTimer, sleEponOnuSubscriberControlTimeStamp, 
				sleEponOnuSubscriberControlReqResult, sleEponOnuSubscriberControlOltIndex, sleEponOnuSubscriberControlOnuIndex, sleEponOnuSubscriberCurrentPort, sleEponOnuSubscriberHistoryTime, 
				sleEponOnuSubscriberHistoryIpAddress, sleEponOnuSubscriberHistoryMacAddress, sleEponOnuSubscriberHistoryPort, sleEponProfileSubscriberInfoCollection, sleEponProfileControlSubscriberInfoCollection, 
				sleEponOnuSubscriberCurrentTime, sleEponOltOperStatus, sleEponProfileLoopDetectStatus, sleEponProfileLoopDetectBlockTimer, sleEponProfileLoopDetectSendingpacket, 
				sleEponProfileControlLoopDetectStatus, sleEponProfileControlLoopDetectBlockTimer, sleEponProfileControlLoopDetectSendingpacket, sleEponBaseSlaPlatoMaxBandwdith, sleEponBaseDPShapingMaxBandwidth, 
				sleEponBasePortMaxHost, sleEponBaseControlRequest, sleEponBaseControlStatus, sleEponBaseControlTimer, sleEponBaseControlTimeStamp, 
				sleEponBaseControlReqResult, sleEponBaseControlSlaPlatoMaxBandwdith, sleEponBaseControlDPShapingMaxBandwidth, sleEponBaseControlPortMaxHost, sleEponBaseOnuAutoUpgrade, 
				sleEponBaseOnuAutoUpgradeRebootTime, sleEponBaseControlOnuAutoUpgrade, sleEponBaseControlOnuAutoUpgradeRebootTime, sleEponOltFirmwareRev, sleEponFirmwareType, 
				sleEponFirmwareName, sleEponFirmwareControlRequest, sleEponFirmwareControlStatus, sleEponFirmwareControlTimer, sleEponFirmwareControlTimeStamp, 
				sleEponFirmwareControlReqResult, sleEponFirmwareControlName, sleEponFirmwareControlUpgradeMethod, sleEponFirmwareControlUpgradeMode, sleEponFirmwareControlServerAddress, 
				sleEponFirmwareControlUser, sleEponFirmwareControlPasswd, sleEponOnuSipGlobalConfigIp, sleEponOnuSipGlobalConfigNetmask, sleEponOnuSipGlobalConfigGateway, 
				sleEponOnuSipGlobalConfigVid, sleEponOnuControlSipGlobalConfigIp, sleEponOnuControlSipGlobalConfigNetmask, sleEponOnuControlSipGlobalConfigGateway, sleEponOnuControlSipGlobalConfigVid, 
				sleEponProfileSipMgPort, sleEponProfileSipProxyServer, sleEponProfileSipProxyServerPort, sleEponProfileSipBackupProxyServer, sleEponProfileSipBackupProxyServerPort, 
				sleEponProfileSipActiveServer, sleEponProfileSipRegisterServer, sleEponProfileSipRegisterServerPort, sleEponProfileSipBackupRegisterServer, sleEponProfileSipBackupRegisterServerPort, 
				sleEponProfileSipOutBindServer, sleEponProfileSipOutBindServerPort, sleEponProfileSipRegisterInterval, sleEponProfileSipHeartBeatSwitch, sleEponProfileSipHeartBeatCycle, 
				sleEponProfileSipHeartBeatCount, sleEponProfileVoiceT38enable, sleEponProfileModemControl, sleEponProfileControlSipMgPort, sleEponProfileControlSipProxyServer, 
				sleEponProfileControlSipProxyServerPort, sleEponProfileControlSipBackupProxyServer, sleEponProfileControlSipBackupProxyServerPort, sleEponProfileControlSipActiveServer, sleEponProfileControlSipRegisterServer, 
				sleEponProfileControlSipRegisterServerPort, sleEponProfileControlSipBackupRegisterServer, sleEponProfileControlSipBackupRegisterServerPort, sleEponProfileControlSipOutBindServer, sleEponProfileControlSipOutBindServerPort, 
				sleEponProfileControlSipRegisterInterval, sleEponProfileControlSipHeartBeatSwitch, sleEponProfileControlSipHeartBeatCycle, sleEponProfileControlSipHeartBeatCount, sleEponProfileControlVoiceT38enable, 
				sleEponProfileControlModemControl, sleEponOnuSipUserConfigControlTimer, sleEponOnuSipUserConfigPots, sleEponOnuSipUserConfigAccount, sleEponOnuSipUserConfigName, 
				sleEponOnuSipUserConfigPasswd, sleEponOnuSipUserConfigControlRequest, sleEponOnuSipUserConfigControlStatus, sleEponOnuSipUserConfigControlTimeStamp, sleEponOnuSipUserConfigControlReqResult, 
				sleEponOnuSipUserConfigControlOltIndex, sleEponOnuSipUserConfigControlOnuIndex, sleEponOnuSipUserConfigControlPots, sleEponOnuSipUserConfigControlAccount, sleEponOnuSipUserConfigControlName, 
				sleEponOnuSipUserConfigControlPasswd, sysDescr, ifIndex, sleEponBaseOnuAgingTime, sleEponBaseAlarmStatus, 
				sleEponBaseAlarmMode, sleEponBaseControlOnuAgingTime, sleEponBaseControlAlarmStatus, sleEponBaseControlAlarmMode, sleEponOltKeyExchangeTimeout, 
				sleEponOltRssiStatus, sleEponOltOnuRegisterCount, sleEponOltControlKeyExchangeTimeout, sleEponOltControlRssiStatus, sleEponOltP2PIndex, 
				sleEponOltP2PEnable, sleEponOltP2POnuID1, sleEponOltP2POnuID2, sleEponOltP2PControlRequest, sleEponOltP2PControlStatus, 
				sleEponOltP2PControlTimer, sleEponOltP2PControlTimeStamp, sleEponOltP2PControlReqResult, sleEponOltP2PControlOltIndex, sleEponOltP2PControlEnable, 
				sleEponOltP2PControlOnuID1, sleEponOltP2PControlOnuID2, sleEponOltDMITemper, sleEponOltDMIVoltage, sleEponOltDMITxBias, 
				sleEponOltDMITxPower, sleEponOltDMIRxPower, sleEponOnuLgPathStatus, sleEponOnuModelType, sleEponOnuSipGlobalConfigMode, 
				sleEponOnuSipGlobalUserName, sleEponOnuSipGlobalPasswd, sleEponOnuRxPower, sleEponOnuRxPowerAlarmStatus, sleEponOnuRssiInfo, 
				sleEponOnuLoopDetectUnblockStatus, sleEponOnuUpgradeStatus, sleEponOnuOltRssiStatus, sleEponOnuOltRssiInfo, sleEponOnuMultiLlid, 
				sleEponOnuMultiMacAddress, sleEponOltDBAMutilLLidLinkOperate, sleEponOnuControlSipGlobalConfigMode, sleEponOnuControlSipGlobalConfigUserName, sleEponOnuControlSipGlobalConfigUserPasswd, 
				sleEponOnuControlPingCount, sleEponOnuDMITemper, sleEponOnuDMIVoltage, sleEponOnuDMITxBias, sleEponOnuDMITxPower, 
				sleEponOnuDMIRxPower, sleEponOnuDMIThresholdWarnTemperLow, sleEponOnuDMIThresholdWarnTemperHigh, sleEponOnuDMIThresholdAlarmTemperLow, sleEponOnuDMIThresholdAlarmTemperHigh, 
				sleEponOnuDMIThresholdWarnVoltageLow, sleEponOnuDMIThresholdWarnVoltageHigh, sleEponOnuDMIThresholdAlarmVoltageLow, sleEponOnuDMIThresholdAlarmVoltageHigh, sleEponOnuDMIThresholdWarnTxbiasLow, 
				sleEponOnuDMIThresholdWarnTxbiasHigh, sleEponOnuDMIThresholdAlarmTxbiasLow, sleEponOnuDMIThresholdAlarmTxbiasHigh, sleEponOnuDMIThresholdWarnTxPowerLow, sleEponOnuDMIThresholdWarnTxPowerHigh, 
				sleEponOnuDMIThresholdAlarmTxPowerLow, sleEponOnuDMIThresholdAlarmTxPowerHigh, sleEponOnuDMIThresholdWarnRxPowerLow, sleEponOnuDMIThresholdWarnRxPowerHigh, sleEponOnuDMIThresholdAlarmRxPowerLow, 
				sleEponOnuDMIThresholdAlarmRxPowerHigh, sleEponOnuDMIThresholdControlRequest, sleEponOnuDMIThresholdControlStatus, sleEponOnuDMIThresholdControlTimer, sleEponOnuDMIThresholdControlTimeStamp, 
				sleEponOnuDMIThresholdControlReqResult, sleEponOnuDMIThresholdControlOltIndex, sleEponOnuDMIThresholdControlOnuIndex, sleEponOnuDMIThresholdControlMonitorType, sleEponOnuDMIThresholdControlMode, 
				sleEponOnuDMIThresholdControlLowThreshold, sleEponOnuDMIThresholdControlHighThreshold, sleEponOnuPortAgingTime, sleEponOnuPortForwardMode, sleEponOnuMacTableDynamicMacAddress, 
				sleEponOnuMacTableStaticMacAddress, sleEponProfileSipDNS1Server, sleEponProfileSipDNS2Server, sleEponProfileDHCPEnable, sleEponProfileMacLearnStatus, 
				sleEponProfileControlSipDNS1Server, sleEponProfileControlSipDNS2Server, sleEponProfileControlDHCPEnable, sleEponProfileControlMacLearnStatus, sleEponProfileIgmpSnoopingIndex, 
				sleEponProfileIgmpSnoopingState, sleEponProfileIgmpSnoopingMaxch, sleEponProfileIgmpSnoopingTagVlan, sleEponProfileIgmpSnoopingControlRequest, sleEponProfileIgmpSnoopingControlStatus, 
				sleEponProfileIgmpSnoopingControlTimer, sleEponProfileIgmpSnoopingControlTimeStamp, sleEponProfileIgmpSnoopingControlReqResult, sleEponProfileIgmpSnoopingControlProfileIndex, sleEponProfileIgmpSnoopingControlState, 
				sleEponProfileIgmpSnoopingControlMaxch, sleEponProfileIgmpSnoopingControlTagVlan, sleEponOnuProfileOnuRuleIndex, sleEponProfileOnuRuleName, sleEponProfileOnuRuleControlRequest, 
				sleEponProfileOnuRuleControlStatus, sleEponProfileOnuRuleControlTimer, sleEponProfileOnuRuleControlTimeStamp, sleEponProfleOnuRuleControlReqResult, sleEponProfileOnuRuleControlProfileIndex, 
				sleEponProfileOnuRuleControlName, sleEponProfilePortIsolationStatus, sleEponProfilePortMaxHostAgingTime, sleEponProfilePortControlIsolationStatus, sleEponProfilePortControlMaxHostAgingTime, 
				sleEponAlarmOpticSignalError, sleEponAlarmStandardLinkFault, sleEponAlarmLossOfSignal, sleEponAlarmTransmitFail, sleEponAlarmMacLearningOverflow, 
				sleEponAlarmLoopback, sleEponAlarmStandardDyingGasp, sleEponAlarmExternalDyingGasp, sleEponAlarmStandardCriticalEvent, sleEponAlarmExternalCriticalEvent, 
				sleEponAlarmEponStandbyLos, sleEponAlarmControlOpticSignalError, sleEponAlarmControlStandardLinkFault, sleEponAlarmControlLossOfSignal, sleEponAlarmControlTransmitFail, 
				sleEponAlarmControlMacLearningOverflow, sleEponAlarmControlLoopback, sleEponAlarmControlStandardDyingGasp, sleEponAlarmControlExternalDyingGasp, sleEponAlarmControlStandardCriticalevent, 
				sleEponAlarmControlExternalCriticalEvent, sleEponAlarmControlEponStandbyLos, sleEponStatsOltHostFrame, sleEponStatsOltInTooLongFrame, sleEponStatsOltHostFrameDropped, 
				sleEponStatsOltPonInHostFrame, sleEponStatsOltPonInTooLongFrame, sleEponStatsOltPonInHostFrameDropped, sleEponStatsOltPonInHECErrorFrame, sleEponStatsOltFromOnuInFrame, 
				sleEponStatsOltFromOnuInErrorFrame, sleEponStatsOltFromOnuInMulticastFrame, sleEponStatsOltFromOnuInBroadcastFrame, sleEponStatsOltFromOnuInReportFrame, sleEponStatsOltFromOnuInCheckSeqErrorFrame, 
				sleEponStatsOltFromOnuInRangeLenErrors, sleEponStatsOltFromOnuInTooLongFrame, sleEponStatsOltFromOnuOutFrame, sleEponStatsOltFromOnuOutFrameBytes, sleEponStatsOltFromOnuOutMulticastFrame, 
				sleEponStatsOltFromOnuOutBroadcastFrame, sleEponStatsOltFromOnuOutDBAGrantFrame, sleEponStatsOltFromOnuOutControlGrantFrame, sleEponStatsOnuPortInUndersize, sleEponStatsOnuPortInOversize, 
				sleEponStatsOnuPortInJabber, sleEponStatsOnuPortInRxError, sleEponStatsOnuPortInRxFcsError, sleEponStatsOnuUniInPkts, sleEponStatsOnuUniInBytes, 
				sleEponStatsOnuUniInErrPkts, sleEponStatsOnuUniInErrBytes, sleEponStatsOnuUniInPause, sleEponStatsOnuUniFrameLongError, sleEponStatsOnuUniOutPkts, 
				sleEponStatsOnuUniOutBytes, sleEponStatsOnuUniOutPause, sleEponStatsOnuUniOutDropPkts, sleEponStatsOnuUnInMcastPkts, sleEponStatsOnuUnInBcastPkts, 
				sleEponStatsOnuUniInDropPkts, sleEponStatsOnuUniOutMcastPkts, sleEponStatsOnuUniOutBcastPkts, sleEponStatsOnuPonInPkts, sleEponStatsOnuPonInBytes, 
				sleEponStatsOnuPonInMcastPkts, sleEponStatsOnuPonIntBcastPkts, sleEponStatsOnuPonInErrPkts, sleEponStatsOnuPonInErrBytes, sleEponStatsOnuPonInPause, 
				sleEponStatsOnuPonInHostPkts, sleEponStatsOnuPonInDropHostPkts, sleEponStatsOnuPonFrameLongError, sleEponStatsOnuPonOutPkts, sleEponStatsOnuPonOutBytes, 
				sleEponStatsOnuPonOutMcastPkts, sleEponStatsOnuPonOutBcastPkts, sleEponStatsOnuPonOutPause, sleEponStatsOnuPonOutDropPkts, sleEponStatsOnuPonOutHostPkts, 
				sleEponStatsOnuPonOutChipErrPkts, sleEponStatsOnuPonInDropPkts, sleEponOnuVoipPortStatus, sleEponOnuSipPortServiceState, sleEponOnuSipPortCodecMode, 
				sleEponRuleClauseQueue, sleEponRuleClauseQueueValue, sleEponRuleClauseLayerOperation, sleEponRuleClauseLayerValue, sleEponRuleClauseL2Mac, 
				sleEponRuleClauseL2EthertypeValue, sleEponRuleClauseNetmask, sleEponRuleClauseL3Addr, sleEponRuleClauseTcpUdpPort, sleEponRuleClauseTcpUdpPortNum, 
				sleEponRuleClauseProtoType, sleEponRuleClauseProtoTypeNum, sleEponRuleClauseVlanType, sleEponRuleClauseVlanValue, sleEponRuleClauseLinkIndexValue, 
				sleEponRuleClauseMatchMode, sleEponRuleClauseControlRequest, sleEponRuleClauseControlStatus, sleEponRuleClauseControlTimer, sleEponRuleClauseControlTimeStamp, 
				sleEponRuleClauseControlReqResult, sleEponRuleClauseControlClauseIndex, sleEponRuleClauseControlClauseMatch, sleEponRuleClauseControlQueue, sleEponRuleClauseControlQueueValue, 
				sleEponRuleClauseControlLayerOperation, sleEponRuleClauseControlLayerValue, sleEponRuleClauseControlL2Mac, sleEponRuleClauseControlL2EtherType, sleEponRuleClauseControlNetmask, 
				sleEponRuleClauseControlL3Addr, sleEponRuleClauseControlTcpUdpPort, sleEponRuleClauseControlTcpUdpPortNum, sleEponRuleClauseControlProtoType, sleEponRuleClauseControlProtoTypeNum, 
				sleEponRuleClauseControlVlanType, sleEponRuleClauseControlVlanValue, sleEponRuleClauseControlLinkIndexValue, sleEponRuleActionVlanOperate, sleEponRuleActionVlanMap, 
				sleEponRuleActionEtherType, sleEponRuleActionVlanID, sleEponRuleActionDiscardOperate, sleEponRuleActionDiscardOperateValue, sleEponRuleActionCaptureHostOperate, 
				sleEponRuleActionCaptureHostFlexibleOperate, sleEponRuleActionQueueId, sleEponRuleActionUnicastLinkDestID, sleEponRuleActionUnicastLinkDestOffset, sleEponRuleActionMulticastLinkDomID, 
				sleEponRuleActionMulticastLinkDomOffset, sleEponRuleActionCosOperate, sleEponRuleActionCosValue, sleEponRuleActionTosOperate, sleEponRuleActionTosValue, 
				sleEponRuleActionOutputOperate, sleEponRuleActionOutputValue, sleEponRuleActionOutputVlanContent, sleEponRuleActionOutputSourceFiledCopy, sleEponRuleActionQueuePendingOperate, 
				sleEponRuleActionControlRequest, sleEponRuleActionControlStatus, sleEponRuleActionControlTimer, sleEponRuleActionControlTimeStamp, sleEponRuleActionControlReqResult, 
				sleEponRuleActionControlIndex, sleEponRuleActionControlVlanOperate, sleEponRuleActionControlVlanMap, sleEponRuleActionControlEtherType, sleEponRuleActionControlVlanID, 
				sleEponRuleActionControlDiscardOperate, sleEponRuleActionControlDiscardOperateValue, sleEponRuleActionControlCaptureHostOperate, sleEponRuleActionControlCaptureHostFlexibleOperate, sleEponRuleActionControlQueueId, 
				sleEponRuleActionControlQueuependingOperate, sleEponRuleActionControlUnicastLinkDestID, sleEponRuleActionControlUnicastLinkDestOffset, sleEponRuleActionControlMulticastLinkDomID, sleEponRuleActionControlMulticastLinkDomOffset, 
				sleEponRuleActionControlCosOperate, sleEponRuleActionControlCosValue, sleEponRuleActionControlTosOperate, sleEponRuleActionControlTosValue, sleEponRuleActionControlOutputOperate, 
				sleEponRuleActionControlOutputValue, sleEponRuleActionControlOutputVlanContent, sleEponRuleActionControlOutputSourceFiledCopy, sleEponRuleModifyRuleName, sleEponRuleModifyTrafficDirection, 
				sleEponRuleModifyPriorityValue, sleEponRuleModifyCIndex, sleEponRuleModifyAIndex, sleEponRuleModifyControlRequest, sleEponRuleModifyControlStatus, 
				sleEponRuleModifyControlTimer, sleEponRuleModifyControlTimeStamp, sleEponRuleModifyControlReqResult, sleEponRuleModifyControlOltId, sleEponRuleModifyControlRuleName, 
				sleEponRuleModifyControlTrafficDirection, sleEponRuleModifyControlPriorityValue, sleEponRuleModifyControlCIndex, sleEponRuleModifyControlAIndex, sleEponOnuRuleName, 
				sleEponOnuRuleIndex, sleEponOnuRuleDirection, sleEponOnuRulePriority, sleEponOnuRuleDscp, sleEponOnuRuleLinkIndex, 
				sleEponOnuRuleQueueIndex, sleEponOnuRuleControlRequest, sleEponOnuRuleControlStatus, sleEponOnuRuleControlTimer, sleEponOnuRuleControlTimeStamp, 
				sleEponOnuRuleControlReqResult, sleEponOnuRuleControlRuleName, sleEponOnuRuleControlDscp, sleEponOnuRuleControlLinkIndex, sleEponOnuRuleControlQueueIndex, 
				sleEponOltDBAGlobalOltLinkOperate, sleEponOltDBAOverGrantMonConfMonitoringInterval, sleEponOltDBAOverGrantMonConfMaxDBAGrantSize, sleEponOltDBAOverGrantMonConfMinGrantUtilization, sleEponOltDBAOverGrantMonConfLeakyBucketCounterValue, 
				sleEponOltDBAMinShaperBandwidth, sleEponOltDBAMinShaperBurstSize, sleEponOltDBAMinShaperScheduleLevel, sleEponOltDBAMinShaperWeight, sleEponOltDBAMaxShaperBandwidth, 
				sleEponOltDBAMaxShaperBurstSize, sleEponOltDBAMaxShaperScheduleLevel, sleEponOltDBAMaxShaperWeight, sleEponOltDBADBAPollingRateLevel, sleEponOltDBADBAPollingRateRate, 
				eEponOltDBADropDownLevel, sleEponOltDBAShaDropDownWeights, sleEponOltDBADropDownWeights, sleEponOltDBAControlRequest, sleEponOltDBAControlStatus, 
				sleEponOltDBAControlTimer, sleEponOltDBAControlTimeStamp, sleEponOltDBAControlReqResult, sleEponOltDBAControlOltIndex, sleEponOltDBAControlOnuIndex, 
				sleEponOltDBAControlDBAPollingRateLevel, sleEponOltDBAControlDBAPollingRateRate, sleEponOltDBAControlShaDropDownWeightsLevel, sleEponOltDBAControlShaDropDownWeights, sleEponOltDBAControlDropDownWeightsLevel, 
				sleEponOltDBAControlDropDownWeightsl, sleEponOltDBAControlGlobalOltLinkOperate, sleEponOltDBAControlOverGrantMonConfMonitoringInterval, sleEponOltDBAControlOverGrantMonConfMaxDBAGrantSize, sleEponOltDBAControlOverGrantMonConfMinGrantUtilization, 
				sleEponOltDBAControlOverGrantMonConfLeakyBucketCounterValue, sleEponOltDBAControlMinShaperBandwidth, sleEponOltDBAControlMinShaperBurstSize, sleEponOltDBAControlMinShaperScheduleLevel, sleEponOltDBAControlMinShaperWeight, 
				sleEponOltDBAControlMaxShaperBandwidth, sleEponOltDBAControlMaxShaperBurstSize, sleEponOltDBAControlMaxShaperScheduleLevel, sleEponOltDBAControlMaxShaperWeight, sleEponOnuProfileDBAProfileName, 
				sleEponOnuProfileDBALinkSlaMinShaBandwidth, sleEponOnuProfileDBALinkSlaMinShaBurstSize, sleEponOnuProfileDBALinkSlaMinShaSchedulerLevel, sleEponOnuProfileDBALinkSlaMinShaWeight, sleEponOnuProfileDBALinkSlaMaxShaBandwidth, 
				sleEponOnuProfileDBALinkSlaMaxShaBurstSize, sleEponOnuProfileDBALinkSlaMaxShaSchedulerLevel, sleEponOnuProfileDBALinkSlaMaxShaWeight, sleEponOnuProfileDBALinkSlaOperate, sleEponOnuProfileDBALinkSlaPollingLevel, 
				sleEponOnuProfileDBALinkSlaTDMRate, sleEponOnuProfileDBALinkSlaTDMGrantLength, sleEponOnuProfileDBALinkOAMMaxOAMRate, sleEponOnuProfileDBALinkOAMMinOAMRate, sleEponOnuProfileDBAQueueIndex, 
				sleEponOnuProfileDBAQueueSlaDownMinShaBandwidth, sleEponOnuProfileDBAQueueSlaDownMinShaBurstSize, sleEponOnuProfileDBAQueueSlaDownMinShaSchedulerLevel, sleEponOnuProfileDBAQueueSlaDownMinShaWeight, sleEponOnuProfileDBAQueueSlaDownMaxShaBandwidth, 
				sleEponOnuProfileDBAQueueSlaDownMaxShaBurstSize, sleEponOnuProfileDBAQueueSlaDownMaxShaSchedulerLevel, sleEponOnuProfileDBAQueueSlaDownMaxShaWeight, sleEponOnuProfileDBAQueueSlaUpMinShaBandwidth, sleEponOnuProfileDBAQueueSlaUpMinShaBurstSize, 
				sleEponOnuProfileDBAQueueSlaUpMinShaSchedulerLevel, sleEponOnuProfileDBAQueueSlaUpMinShaWeight, sleEponOnuProfileDBAQueueSlaUpMaxShaBandwidth, sleEponOnuProfileDBAQueueSlaUpMaxShaBurstSize, sleEponOnuProfileDBAQueueSlaUpMaxShaSchedulerLevel, 
				sleEponOnuProfileDBAQueueSlaUpMaxShaWeight, sleEponOnuProfileDBAControlRequest, sleEponOnuProfileDBAControlStatus, sleEponOnuProfileDBAControlTimer, sleEponOnuProfileDBAControlTimeStamp, 
				sleEponOnuProfileDBAControlReqResult, sleEponOnuProfileDBAControlProfileName, sleEponOnuProfileDBAControlLinkSlaMinShaBandwidth, sleEponOnuProfileDBAControlLinkSlaMinShaBurstSize, sleEponOnuProfileDBAControlLinkSlaMinShaSchedulerLevel, 
				sleEponOnuProfileDBAControlLinkSlaMinShaWeight, sleEponOnuProfileDBAControlLinkSlaMaxShaBandwidth, sleEponOnuProfileDBAControlLinkSlaMaxShaBurstSize, sleEponOnuProfileDBAControlLinkSlaMaxShaSchedulerLevel, sleEponOnuProfileDBAControlLinkSlaMaxShaWeight, 
				sleEponOnuProfileDBAControlLinkSlaOperate, sleEponOnuProfileDBAControlLinkSlaPollingLevel, sleEponOnuProfileDBAControlLinkSlaTDMRate, sleEponOnuProfileDBAControlLinkSlaTDMGrantLength, sleEponOnuProfileDBAControlQueueIndex, 
				sleEponOnuProfileDBAControlQueueSlaMinShaBandwidth, sleEponOnuProfileDBAControlQueueSlaMinShaBurstSize, sleEponOnuProfileDBAControlQueueSlaMinShaSchedulerLevel, sleEponOnuProfileDBAControlQueueSlaMinShaWeight, sleEponOnuProfileDBAControlQueueSlaMaxShaBandwidth, 
				sleEponOnuProfileDBAControlQueueSlaMaxShaBurstSize, sleEponOnuProfileDBAControlQueueSlaMaxShaSchedulerLevel, sleEponOnuProfileDBAControlQueueSlaMaxShaWeight, sleEponOnuProfileDBAControlQueueSlaOperate, sleEponOnuProfileDBAControlLinkOAMMaxRate, 
				sleEponOnuProfileDBAControlLinkOAMMinRate, sleEponOnuProfileDBAMultiLLidProfileName, sleEponOnuProfileDBAMultiLLidLinkSlaMinShaBandwidth, sleEponOnuProfileDBAMultiLLidLinkSlaMinShaBurstSize, sleEponOnuProfileDBAMultiLLidLinkSlaMinShaSchedulerLevel, 
				sleEponOnuProfileDBAMultiLLidLinkSlaMinShaWeight, sleEponOnuProfileDBAMultiLLidLinkSlaMaxShaBandwidth, sleEponOnuProfileDBAMultiLLidLinkSlaMaxShaBurstSize, sleEponOnuProfileDBAMultiLLidLinkSlaMaxShaSchedulerLevel, sleEponOnuProfileDBAMultiLLidLinkSlaMaxShaWeight, 
				sleEponOnuProfileDBAMultiLLidLinkSlaOperate, sleEponOnuProfileDBAMultiLLidLinkSlaPollingLevel, sleEponOnuProfileDBAMultiLLidLinkSlaTDMRate, sleEponOnuProfileDBAMultiLLidLinkSlaTDMGrantLength, sleEponOnuProfileDBAMultiLLidLinkOAMMaxOAMRate, 
				sleEponOnuProfileDBAMultiLLidLinkOAMMinOAMRate, sleEponOnuProfileDBAMultiLLidQueueIndex, sleEponOnuProfileDBAMultiLLidQueueSlaDownMinShaBandwidth, sleEponOnuProfileDBAMultiLLidQueueSlaDownMinShaBurstSize, sleEponOnuProfileDBAMultiLLidQueueSlaDownMinShaSchedulerLevel, 
				sleEponOnuProfileDBAMultiLLidQueueSlaDownMinShaWeight, sleEponOnuProfileDBAMutiLLidQueueSlaDownMaxShaBandwidth, sleEponOnuProfileDBAMultiLLidQueueSlaDownMaxShaBurstSize, sleEponOnuProfileDBAMultiLLidQueueSlaDownMaxShaSchedulerLevel, sleEponOnuProfileDBAMultiLLidQueueSlaDownMaxShaWeight, 
				sleEponOnuProfileDBAMultiLLidQueueSlaUpMinShaBandwidth, sleEponOnuProfileDBAMultiLLidQueueSlaUpMinShaBurstSize, sleEponOnuProfileDBAMultiLLidQueueSlaUpMinShaSchedulerLevel, sleEponOnuProfileDBAMultiLLidQueueSlaUpMinShaWeight, sleEponOnuProfileDBAMultiLLidQueueSlaUpMaxShaBandwidth, 
				sleEponOnuProfileDBAMultiLLidQueueSlaUpMaxShaBurstSize, sleEponOnuProfileDBAMultiLLidQueueSlaUpMaxShaSchedulerLevel, sleEponOnuProfileDBAMultiLLidQueueSlaUpMaxShaWeight, sleEponOnuProfileDBAMultiLLidControlRequest, sleEponOnuProfileDBAMultiLLidControlStatus, 
				sleEponOnuProfileDBAMultiLLidControlTimer, sleEponOnuProfileDBAMultiLLidControlTimeStamp, sleEponOnuProfileDBAMultiLLidControlReqResult, sleEponOnuProfileDBAMultiLLidControlProfileName, sleEponOnuProfileDBAMultiLLidControlLinkSlaMinShaBandwidth, 
				sleEponOnuProfileDBAMultiLLidControlLinkSlaMinShaBurstSize, sleEponOnuProfileDBAMultiLLidControlLinkSlaMinShaSchedulerLevel, sleEponOnuProfileDBAMultiLLidControlLinkSlaMinShaWeight, sleEponOnuProfileDBAMultiLLidControlLinkSlaMaxShaBandwidth, sleEponOnuProfileDBAMultiLLidControlLinkSlaMaxShaBurstSize, 
				sleEponOnuProfileDBAMultiLLidControlLinkSlaMaxShaSchedulerLevel, sleEponOnuProfileDBAMultiLLidControlLinkSlaMaxShaWeight, sleEponOnuProfileDBAMultiLLidControlLinkSlaOperate, sleEponOnuProfileDBAMultiLLIdControlLinkSlaPollingLevel, sleEponOnuProfileDBAlMultiLLidControLinkSlaTDMRate, 
				sleEponOnuProfileDBAMultiLLidControlLinkSlaTDMGrantLength, sleEponOnuProfileDBAMultiLLidControlQueueIndex, sleEponOnuProfileDBAMultiLLidControlQueueSlaMinShaBandwidth, sleEponOnuProfileDBAMultiLLidControlQueueSlaMinShaBurstSize, sleEponOnuProfileDBAMultiLLidControlQueueSlaMinShaSchedulerLevel, 
				sleEponOnuProfileDBAMultiLLidControlQueueSlaMinShaWeight, sleEponOnuProfileDBAMultiLLidControlQueueSlaMaxShaBandwidth, sleEponOnuProfileDBAMultiLLidControlQueueSlaMaxShaBurstSize, sleEponOnuProfileDBAMultiLLidControlQueueSlaMaxShaSchedulerLevel, sleEponOnuProfileDBAMultiLLidControlQueueSlaMaxShaWeight, 
				sleEponOnuProfileDBAMultiLLIdControlQueueSlaOperate, sleEponOnuProfileDBAMultiLLidControlLinkOAMMaxRate, sleEponOnuProfileDBAMultiLLidControlLinkOAMMinRate, sleEponDomainVlanID, sleEponDomainUnTaggedPorts, 
				sleEponDomainMultiUnTaggedPorts, sleEponDomainControlRequest, sleEponDomainControlStatus, sleEponDomainControlTimer, sleEponDomainControlTimeStamp, 
				sleEponDomainControlReqResult, sleEponDomainControlOltIndex, sleEponDomainControlOnuIndex, sleEponDomainControlVlanID, sleEponDomainControlUnTaggedPorts, 
				sleEponOltRedundancyMaste, sleEponOltRedundancyGroupID, sleEponOltRedundancyTrunkID, sleEponOltRedundancyMasteStatus, sleEponOltRedundancySlave, 
				sleEponOltRedundancySlaveStatus, sleEponOltRedundancyWtrValue, sleEponOltRedundancyRemainTime, sleEponOltRedundancyLastReason, sleEponOltRedundancyHoldOffTime, 
				sleEponOltRedundancyControlRequest, sleEponOltRedundancyControlStatus, sleEponOltRedundancyControlTimer, sleEponOltRedundancyControlTimeStamp, sleEponOltRedundancyControlReqResult, 
				sleEponOltRedundancyControlGroupID, sleEponOltRedundancyControlTrunkID, sleEponOltRedundancyControlMaster, sleEponOltRedundancyControlSlave, sleEponOltRedundancyControlWtrValue, 
				sleEponOltRedundancyControlHoldOffTime, sleEponProfileExtendMtu, sleEponOnuTxPowerOffTimer }
			STATUS current
			DESCRIPTION 
				"Description."
			::= { sleEpon 17 }

		
		-- 1.3.6.1.4.1.6296.101.20.18
		sleEponNotificationGroup NOTIFICATION-GROUP
			NOTIFICATIONS { sleEponOltRegModeChanged, sleEponOltStatusChanged, sleEponOnuRegModeChanged, sleEponOnuStatusChanged, sleEponOnuRegistered, 
				sleEponOnuUpgraded, sleEponProfileCreated, sleEponProfileDestroyed, sleEponstatsOltCleared, sleEponStatsOltChannelCleared, 
				sleEponAlarmProfileChanged, sleEponOnuDeregistered, sleEponOnuProfileChanged, sleEponOnuLoopbackProvisioned, sleEponOltProfileChanged, 
				sleEponStatsAllCleared, sleEponProfileVlanCreated, sleEponProfileVlanDestroyed, sleEponProfileVlanProfileChanged, sleEponProfilePortAdminStatusChanged, 
				sleEponProfilePortNegoChanged, sleEponProfilePortSpeedChanged, sleEponProfilePortMaxHostChanged, sleEponProfilePortPvidChanged, sleEponProfilePortRateLimitChanged, 
				sleEponOnuPortReset, sleEponOnuClassificationCreated, sleEponOnuClassificationDestroyed, sleEponProfileClassificationCreated, sleEponProfileClassificationDestroyed, 
				sleEponOltSCChanged, sleEponOltUpgraded, sleEponOltReset, sleEponOnuTxPowerOffChanged, sleEponOnuFdbMacCleared, 
				sleEponProfileExtendMtuChanged, sleEponProfileIgmpChanged, sleEponProfileSTPChanged, sleEponProfileQueueModifyQueueLimit, sleEponProfilePortFlowControlChanged, 
				sleEponVlanOltVlanPrefixChanged, sleEponVlanOltVlanProfileChanged, sleEponProfileDefaultProfileCreated, sleEponProfileUNIQueueModifyQueuePolicy, sleEponPTimeStatsCleared, 
				sleEponPTimeStatsServiceActivityChanged, sleEponOnuSubscriberHistoryOltCleared, sleEponOnuSubscriberHistroyOnuCleared, sleEponProfileQueueModifyQueuePolicy, sleEponOltAttributesChanged, 
				sleEponOnuAttibutesChanged, sleEponProfileModified, sleEponProfilePortDuplexChanged, sleEponProfileLoopDetectChanged, sleEponBaseDefaultBandwidthChanged, 
				sleEponBaseDefaultMaxHost, sleEponVlanOnuVlanProfileChanged, sleEponFirmwareUpgradeProfileChanged, sleEponFirmwareDeleted, sleEponOnuSipGlobalConfigDestroyed, 
				sleEponProfileSipConfigChanged, sleEponProfileModemConfigChanged, sleEponOnuSipUserConfigDestroyed, sleEponBaseOnuAgingTimeChanged, sleEponBaseAlarmStatusChanged, 
				sleEponBaseAlarmModeChanged, sleEponOltRssiStatusChanged, sleEponOltP2PAccessControlChanged, sleEponOnuFristRegisteredOnAutoToManual, sleEponOnuProfileChangedByMac, 
				sleEponOnuDeregisteredByMac, sleEponOnuLgpauthStatusChanged, sleEponOnuSipGlobalConfigIpChanged, sleEponOnuSipGlobalConfigDhcpChanged, sleEponOnuSipGlobalConfigPPPoEChanged, 
				sleEponOnuPingTest, sleEponOnuLoopDectectUnblock, setEponOnuOltRssiOnuSingle, sleEponOnuDBAMultiLLidLink, sleEponOnuDMIMonitorThresholdChanged, 
				sleEponProfileDHCPChanged, sleEponProfileModemMacLearnChanged, sleEponProfileIgmpSnoopingChanged, sleEponProfileOnuRuleChanged, sleEponProfilePortIsolationChanged, 
				sleEponAlarmChanged, sleEponRuleClauseQueueChanged, sleEponRuleClauseLayer2Changed, sleEponRuleClauseVlanChanged, sleEponRuleClauseLayer3Changed, 
				sleEponRuleClauseTcpUdpChanged, sleEponRuleClauseProtocolChanged, sleEponRuleClauseLinkIndexChanged, sleEponRuleClauseDel, sleEponRuleActionVlanChanged, 
				sleEponRuleActionDiscardChanged, sleEponRuleActionCaptureHostChanged, sleEponRuleActionCaptureHostFlexibleChanged, sleEponRuleActionQueueChanged, sleEponRuleActionUnicastLinkChanged, 
				sleEponRuleActionMulticastLinkChanged, sleEponRuleActionNoOperation, sleEponRuleActionCosChanged, sleEponRuleActionTosChanged, sleEponRuleActionOutputChanged, 
				sleEponRuleActionQueuePendingChanged, sleEponRuleActionSleChanged, sleEponRuleActionNoRuleAction, sleEponRuleOltRuleCreate, sleEponRuleModifyPriorityChange, 
				sleEponRuleModifyTrafficDirChange, sleEponRuleModifyClauseAdd, sleEponRuleModifyActionAdd, sleEponRuleModifyClauseDel, sleEponRuleModifyActionDel, 
				sleEponRuleOltRuleDelete, sleEponRuleOltRuleAddApply, sleEponRuleOltRuleDelApply, sleEponOnuRuleChanged, sleEponOLtDBAShaperDropDownWeightsChanged, 
				sleEponOLtDBADropDownWeightsChanged, sleEponOltDBALinkChanged, sleEponOLtDBADGlobalOltLinkChanged, sleEponOLtDBADOverGrantMonConfChanged, sleEponOltDBAPollingRateChanged, 
				sleEponOltDBAMultiQueueSlaChanged, sleEponOnuProfileDBALinkSlaChanged, sleEponOnuProfileDBAQueueSlaChanged, sleEponOnuProfileDBALinkOAMRateChanged, sleEponOnuProfileDBAMultiLLidLinkSlaChanged, 
				sleEponOnuProfileDBAMultiLLidQueueSlaChanged, sleEponOnuProfileDBAMultiLLidLinkOAMRateChanged, sleEponDomainVlanCreate, sleEponDomainDestroyVlan, sleEponDomainVlanAdd, 
				sleEponDomainDefaultVlanAdd, sleEponDomainVlanDel, sleEponDomainDefaultVlanDel, sleEponDomainVlanMultiAdd, sleEponDomainDefaultVlanMultiAdd, 
				sleEponDomainVlanMultiDel, sleEponDomainDefaultVlanMultiDel, sleEponOltRedundancyChanged, sleEponOltRedundancySwitchoverForceGroup, sleEponOltRedundancyHoldOffTimeChanged, 
				sleEponProfileSubscriberChanged, sleEponBaseOnuAutoUpgradeChanged, sleEponOnuSipUserConfigChanged }
			STATUS current
			DESCRIPTION 
				"Description."
			::= { sleEpon 18 }

		
	
	END

--
-- sle-epon-mib.mib
--
